-- This file was generated by the Objective Systems ASN1C Compiler
-- (http://www.obj-sys.com).  Version: 7.4.2.3, Date: 13-Jul-2020.

TS44018Msgs DEFINITIONS AUTOMATIC TAGS ::= BEGIN

IMPORTS

AddnUpdateParams, CellIdentityValue, CiphKeySeqNum, DescrGroupOrBcastCallRef, 
   LocAreaIdent, MobileIdentity, MobileStationClassmark2, 
   MobileStationClassmark3, RoutingAreaIdent, TMGI
FROM TS24008IES 

A3G-Additional-Measurement-Parameters-Description-2-struct, 
   A3G-CSG-Description-struct, APDU-Data, APDU-Flags, APDU-ID, Application-Data
   , BA-List-Pref, BA-Range, Carrier-Indication, Cell-Channel-Description, 
   Cell-Description, Cell-Options-BCCH, Cell-Options-SACCH, 
   Cell-Selection-Parameters, Channel-Description, Channel-Description-2, 
   Channel-Description-3, Channel-Mode, Channel-Mode-2, Channel-Needed, 
   Channel-Request-Description-2, Cell-Sel-Ind-Post-Rel-TCH-SDCCH, 
   Cipher-Mode-Setting, Cipher-Response, Classmark-Enquiry-Mask, 
   CN-to-MS-transparent-information, Control-Channel-Description, Data-Identity
   , Dedicated-mode-or-TBF, Dedicated-Service-Information, DL-DCCH-Message, 
   DTM-Information-Details, Dynamic-ARFCN-Mapping, 
   E-UTRAN-Measurement-Parameters-Description-struct, 
   Enhanced-DTM-CS-Release-Indication, Extended-Measurement-Results, 
   Extended-Measurement-Frequency-List, Feature-Indicator, 
   Frequency-Channel-Sequence, Frequency-List, Frequency-Short-List, 
   GERAN-Iu-Mode-Classmark, GPRS-broadcast-information, GPRS-Resumption, 
   Group-Call-information, Group-Channel-Description, 
   Group-Channel-Description-2, Handover-Reference, 
   Handover-To-cdma2000-Command, Handover-To-UTRAN-Command, IA-Rest-Octets, 
   Individual-priorities, IPA-Rest-Octets, LLC-PDU-Container, L2-Pseudo-Length
   , IAR-Rest-Octets, IAX-Rest-Octets, NT-N-Rest-Octets, P1-Rest-Octets, 
   P2-Rest-Octets, P3-Rest-Octets, MBMS-p-t-m-Channel-Description, 
   MBMS-Session-Identity, MBMS-Session-Parameters-List, Measurement-Results, 
   Mobile-Allocation, Mobile-Time-Difference, 
   Mobile-Time-Difference-on-Hyperframe-level, Multirate-Configuration, 
   Multislot-Allocation, MPRACH-description, NCC-Permitted, 
   Neighbour-Cell-Description, Neighbour-Cell-Description-2, 
   Packet-Channel-Description, Page-Mode, PLMN-Index, Power-Command, 
   Power-Command-and-access-type, PS-Cause, RACH-Control-Parameters, 
   Random-Reference-Establishment-Cause, 
   Reduced-group-or-broadcast-call-reference, Request-Reference, 
   Restriction-Timer, RR-Packet-Downlink-Assignment, 
   RR-Packet-Downlink-Assignment-Type-2, RR-Packet-Uplink-Assignment, 
   Service-Support, SI1-Rest-Octets, SI10-Rest-Octets, 
   SI10bis-Neighbour-Cell-Info, SI10bis-Rest-Octets, SI10ter-Rest-Octets, 
   SI2bis-Rest-Octets, SI2ter-Rest-Octets, SI2quater-Rest-Octets, 
   SI2n-Rest-Octets, SI3-Rest-Octets, SI3-Rest-Octets-Data, SI4-Rest-Octets, 
   SI6-Rest-Octets, SI7-Rest-Octets, SI7-Rest-Octets-Data, SI8-Rest-Octets, 
   SI8-Rest-Octets-Data, SI9-Rest-Octets, SI13-Rest-Octets, SI16-Rest-Octets, 
   SI17-Rest-Octets, SI19-Rest-Octets, SI18-Rest-Octets, SI14-Rest-Octets, 
   SI15-Rest-Octets, SI13alt-Rest-Octets, SI21-Rest-Octets, SI22-Rest-Octets, 
   SI23-Rest-Octets, Starting-Time, Suspension-Cause, 
   Synchronization-Indication, Talker-Identity, Talker-Priority-Status, 
   Time-Difference, Timing-Advance, TLLI, TMSI, Token, Uplink-Access-Indication
   , UTRAN-Classmark, UTRAN-Freq-List, UTRAN-TDD-Description-struct, 
   VGCS-AMR-Configuration, VGCS-Ciphering-Parameters, 
   VGCS-target-mode-Indication, Wait-Indication, ExtendedTSCSet
FROM TS44018IES 

PCID-Group-IE, PSC-Group-IE, UTRAN-CSG-Measurement-Report-IE
FROM TS44060IES 

L3HdrOptions, NAS-PROTOCOL-CLASS, ProtoDiscr
FROM TS24007L3 ;

-- Productions

LHType ::= ENUMERATED { lbit(0), hbit(1) }

Emergency-Ind ::= LHType

Priority-Uplink-Access ::= LHType

SYSTEM-INFORMATION-TYPE-10 ::= SI10-Rest-Octets

SYSTEM-INFORMATION-TYPE-10bis ::= SI10bis-Rest-Octets

-- 9.1.3 Assignment Complete 
--<is3GMessage/>
AssignmentComplete ::= SEQUENCE {
   rrCause [0] INTEGER (0..255)
}

-- 9.1.4 Assignment Failure 
AssignmentFailure ::= AssignmentComplete

-- 9.1.12c Configuration Change Acknowledge 
--<is3GMessage/>
ConfigurationChangeAck ::= NULL -- message type only


-- 9.1.21b Notification/NCH 
--<is3GMessage checkContainer="true"/>
NotificationNch ::= NULL -- L2 pseudo length and message type only


-- 9.1.27 Partial Release Complete 
--<is3GMessage/>
PartialReleaseComplete ::= NULL -- message type only


-- 9.1.34a System Information Type 2quater 
--<is3GMessage imperativeOnly="true"/>
SystemInformationType2quater ::= NULL -- L2 pseudo length and message type only


-- 9.1.34b System Information Type 2n 
--<is3GMessage imperativeOnly="true"/>
SystemInformationType2n ::= NULL -- L2 pseudo length and message type only


-- 9.1.41 System Information Type 7 
--<is3GMessage imperativeOnly="true"/>
SystemInformationType7 ::= NULL -- L2 pseudo length and message type only


-- 9.1.42 System Information Type 8 
--<is3GMessage imperativeOnly="true"/>
SystemInformationType8 ::= NULL -- L2 pseudo length and message type only


-- 9.1.43a System Information Type 13 
--<is3GMessage imperativeOnly="true"/>
SystemInformationType13 ::= NULL -- L2 pseudo length and message type only


-- 9.1.43d System Information Type 16 
--<is3GMessage imperativeOnly="true"/>
SystemInformationType16 ::= NULL -- L2 pseudo length and message type only


-- 9.1.43e System Information Type 17 
--<is3GMessage imperativeOnly="true"/>
SystemInformationType17 ::= NULL -- L2 pseudo length and message type only


-- 9.1.43f System Information Type 19 
--<is3GMessage imperativeOnly="true"/>
SystemInformationType19 ::= NULL -- L2 pseudo length and message type only


-- 9.1.43g System Information Type 18 
--<is3GMessage imperativeOnly="true"/>
SystemInformationType18 ::= NULL -- L2 pseudo length and message type only


-- 9.1.43h System Information Type 20 
--<is3GMessage imperativeOnly="true"/>
SystemInformationType20 ::= NULL -- L2 pseudo length and message type only


-- 9.1.43i System Information Type 14 
--<is3GMessage checkContainer="true">
SystemInformationType14 ::= NULL -- L2 pseudo length and message type only


-- 9.1.43j System Information Type 15 
--<is3GMessage imperativeOnly="true"/>
SystemInformationType15 ::= NULL -- L2 pseudo length and message type only


-- 9.1.43k System Information Type 13alt 
--<is3GMessage imperativeOnly="true"/>
SystemInformationType13alt ::= NULL -- L2 pseudo length and message type only


-- 9.1.43m System Information Type 21 
--<is3GMessage imperativeOnly="true"/>
SystemInformationType21 ::= NULL -- L2 pseudo length and message type only


-- 9.1.43n System Information Type 22 
--<is3GMessage imperativeOnly="true"/>
SystemInformationType22 ::= NULL -- L2 pseudo length and message type only


-- 9.1.43o System Information Type 23 
--<is3GMessage imperativeOnly="true"/>
SystemInformationType23 ::= NULL -- L2 pseudo length and message type only


A3G-ADDITIONAL-MEASUREMENT-Parameters-Description-2-struct ::= SEQUENCE {
   fdd-reporting-threshold-2 [0] INTEGER (0..63) OPTIONAL
}

A3G-MEASUREMENT-PARAMETERS-Description-struct ::= SEQUENCE {
   qsearch-C [0] INTEGER (0..15),
   spare1 [1] INTEGER (0..1) DEFAULT 1,
   fdd-rep-quant [2] INTEGER (0..1),
   fdd-multirat-reporting [3] INTEGER (0..3) OPTIONAL,
   component-5 [4] SEQUENCE {
      fdd-reporting-offset [0] INTEGER (0..7),
      fdd-reporting-threshold [1] INTEGER (0..7)
   } OPTIONAL,
   tdd-multirat-reporting [5] INTEGER (0..3) OPTIONAL,
   component-7 [6] SEQUENCE {
      tdd-reporting-offset [0] INTEGER (0..7),
      tdd-reporting-threshold [1] INTEGER (0..7)
   } OPTIONAL,
   cdma2000-multirat-reporting [7] INTEGER (0..3) OPTIONAL,
   component-9 [8] SEQUENCE {
      cdma2000-reporting-offset [0] INTEGER (0..7),
      cdma2000-reporting-threshold [1] INTEGER (0..7)
   } OPTIONAL
}

Repeated-UTRAN-Measurement-Control-Parameters-struct ::= SEQUENCE {
   utran-frequency-index-list [0] SEQUENCE OF INTEGER (0..31),
   measurement-Control-UTRAN [1] INTEGER (0..1)
}

A3G-Measurement-Control-Parameters-Description-struct ::= SEQUENCE {
   default-Measurement-Control-UTRAN [0] INTEGER (0..1) OPTIONAL,
   repeated-UTRAN-Measurement-Control-Parameters-list [1] SEQUENCE OF 
      Repeated-UTRAN-Measurement-Control-Parameters-struct
}

Repeated-UTRAN-FDD-Neighbour-Cells-struct ::= SEQUENCE {
   zerobit [0] INTEGER (0) DEFAULT 0,
   fdd-arfcn [1] INTEGER (0..16383),
   fdd-Indic0 [2] INTEGER (0..1),
   nr-of-fdd-cells [3] INTEGER (0..31),
   fdd-CELL-INFORMATION-Field [4] BIT STRING 
}

UTRAN-FDD-Description-struct ::= SEQUENCE {
   bandwidth-FDD [0] INTEGER (0..7) OPTIONAL,
   repeated-UTRAN-FDD-Neighbour-Cells-list [1] SEQUENCE OF 
      Repeated-UTRAN-FDD-Neighbour-Cells-struct
}

Repeated-UTRAN-TDD-Neighbour-Cells-struct ::= SEQUENCE {
   zerobit [0] INTEGER (0) DEFAULT 0,
   tdd-arfcn [1] INTEGER (0..16383),
   tdd-Indic0 [2] INTEGER (0..1),
   nr-of-tdd-cells [3] INTEGER (0..31),
   tdd-CELL-INFORMATION-Field [4] BIT STRING 
}

UTRAN-TDD-Description-struct ::= SEQUENCE {
   bandwidth-TDD [0] INTEGER (0..7) OPTIONAL,
   repeated-UTRAN-TDD-Neighbour-Cells-list [1] SEQUENCE OF 
      Repeated-UTRAN-TDD-Neighbour-Cells-struct
}

CDMA2000-Description-struct ::= SEQUENCE {
   cdma2000-frequency-band [0] INTEGER (0..31),
   cdma2000-frequency [1] INTEGER (0..2047),
   number-cdma2000-cells [2] INTEGER (0..31),
   component-4 [3] SEQUENCE (SIZE (0..31)) OF SEQUENCE {
      pilot-PN-offset [0] INTEGER (0..511),
      component-2 [1] EXPLICIT CHOICE {
         choice-1 [0] SEQUENCE {
            td-mode [0] INTEGER (0..3),
            td-power-level [1] INTEGER (0..7)
         },
         choice-2 [1] SEQUENCE {
            qof [0] INTEGER (0..3),
            walsh-len-a [1] INTEGER (0..7),
            aux-pilot-walsh [2] BIT STRING  (SIZE (6..13))
         },
         choice-3 [2] SEQUENCE {
            qof [0] INTEGER (0..3),
            walsh-len-b [1] INTEGER (0..7),
            aux-td-walsh [2] BIT STRING  (SIZE (6..13)),
            aux-td-power-level [3] INTEGER (0..3),
            td-mode [4] INTEGER (0..3)
         },
         choice-4 [3] SEQUENCE {
            sr3-prim-pilot [0] INTEGER (0..3),
            sr3-pilot-power1 [1] INTEGER (0..7),
            sr3-pilot-power2 [2] INTEGER (0..7)
         },
         choice-5 [4] SEQUENCE {
            sr3-prim-pilot [0] INTEGER (0..3),
            sr3-pilot-power1 [1] INTEGER (0..7),
            sr3-pilot-power2 [2] INTEGER (0..7),
            qof [3] INTEGER (0..3),
            walsh-len-c [4] INTEGER (0..7),
            aux-walsh-len [5] BIT STRING  (SIZE (6..13)),
            component-7 [6] SEQUENCE {
               qof1 [0] INTEGER (0..3),
               walsh-length1 [1] INTEGER (0..7),
               aux-pilot-walsh1 [2] BIT STRING  (SIZE (6..13))
            } OPTIONAL,
            component-8 [7] SEQUENCE {
               qof2 [0] INTEGER (0..3),
               walsh-length2 [1] INTEGER (0..7),
               aux-pilot-walsh2 [2] BIT STRING  (SIZE (6..13))
            } OPTIONAL
         }
      } OPTIONAL
   }
}

A3G-Neighbour-Cell-Description-struct ::= SEQUENCE {
   a3G-Wait [0] INTEGER (0..7) OPTIONAL,
   index-Start-3G [1] INTEGER (0..127) OPTIONAL,
   absolute-Index-Start-EMR [2] INTEGER (0..127) OPTIONAL,
   utran-FDD-Description [3] UTRAN-FDD-Description-struct OPTIONAL,
   utran-TDD-Description [4] UTRAN-TDD-Description-struct OPTIONAL,
   cdma2000-Description [5] CDMA2000-Description-struct OPTIONAL
}

A3G-Supplementary-Parameters-Description-struct ::= SEQUENCE {
   utran-Start [0] INTEGER (0..1),
   utran-Stop [1] INTEGER (0..1),
   a3G-Measurement-Control-Parameters-Description [2] 
      A3G-Measurement-Control-Parameters-Description-struct OPTIONAL
}

BSIC-Description-struct ::= SEQUENCE {
   ba-Index-Start-BSIC [0] INTEGER (0..31) OPTIONAL,
   bsic [1] INTEGER (0..63),
   number-Remaining-BSIC [2] INTEGER (0..127),
   component-4 [3] SEQUENCE (SIZE (0..127)) OF SEQUENCE {
      frequency-Scrolling [0] INTEGER (0..1),
      bsic [1] INTEGER (0..63)
   }
}

E-UTRAN-CSG-Description-struct ::= SEQUENCE OF SEQUENCE {
   csg-pci-split [0] PCID-Group-IE,
   e-utran-frequency-index-list [1] SEQUENCE OF INTEGER (0..7)
}

Repeated-E-UTRAN-Measurement-Control-Parameters-struct ::= SEQUENCE {
   e-utran-frequency-index-list [0] SEQUENCE OF INTEGER (0..7),
   measurement-Control-E-UTRAN [1] INTEGER (0..1)
}

E-UTRAN-Measurement-Control-Parameters-Description-struct ::= SEQUENCE {
   default-Measurement-Control-E-UTRAN [0] INTEGER (0..1) OPTIONAL,
   repeated-E-UTRAN-Measurement-Control-Parameters-list [1] SEQUENCE OF 
      Repeated-E-UTRAN-Measurement-Control-Parameters-struct
}

E-UTRAN-Measurement-Report-struct ::= SEQUENCE {
   n-e-utran [0] INTEGER (0..3),
   component-2 [1] SEQUENCE (SIZE (1..4)) OF SEQUENCE {
      e-utran-frequency-index [0] INTEGER (0..7),
      cell-identity [1] INTEGER (0..511),
      reporting-quantity [2] INTEGER (0..63)
   }
}

Repeated-E-UTRAN-Neighbour-Cells-struct ::= SEQUENCE {
   earfcn [0] INTEGER (0..65535),
   earfcn-list [1] SEQUENCE OF INTEGER (0..65535),
   measurement-Bandwidth [2] INTEGER (0..7) OPTIONAL
}

Repeated-E-UTRAN-Not-Allowed-Cells-struct ::= SEQUENCE {
   not-Allowed-Cells [0] PCID-Group-IE,
   e-utran-frequency-index-list [1] SEQUENCE OF INTEGER (0..7)
}

E-UTRAN-Parameters-Description-struct ::= SEQUENCE {
   e-UTRAN-Start [0] INTEGER (0..1),
   e-UTRAN-Stop [1] INTEGER (0..1),
   e-UTRAN-Measurement-Parameters-Description [2] 
      E-UTRAN-Measurement-Parameters-Description-struct OPTIONAL,
   repeated-E-UTRAN-Neighbour-Cells-list [3] SEQUENCE OF 
      Repeated-E-UTRAN-Neighbour-Cells-struct,
   repeated-E-UTRAN-Not-Allowed-Cells-list [4] SEQUENCE OF 
      Repeated-E-UTRAN-Not-Allowed-Cells-struct,
   e-UTRAN-Measurement-Control-Parameters-Description [5] 
      E-UTRAN-Measurement-Control-Parameters-Description-struct OPTIONAL
}

Serving-cell-data-struct ::= SEQUENCE {
   dtx-used [0] INTEGER (0..1),
   rxlev-val [1] INTEGER (0..63),
   rx-qual-full [2] INTEGER (0..7),
   mean-bep [3] INTEGER (0..31),
   cv-bep [4] INTEGER (0..7),
   nbr-rcvd-blocks [5] INTEGER (0..31)
}

Repeated-Invalid-BSIC-Information-struct ::= SEQUENCE {
   bcch-freq-ncell [0] INTEGER (0..31),
   bsic [1] INTEGER (0..63),
   rxlev-ncell [2] INTEGER (0..63)
}

Enhanced-Measurement-report ::= SEQUENCE {
   ba-used [0] INTEGER (0..1),
   a3G-BA-USED [1] INTEGER (0..1),
   bsic-Seen [2] INTEGER (0..1),
   scale [3] INTEGER (0..1),
   serving-cell-data [4] Serving-cell-data-struct OPTIONAL,
   repeated-Invalid-BSIC-Information-list [5] SEQUENCE OF 
      Repeated-Invalid-BSIC-Information-struct,
   component-7 [6] SEQUENCE OF SEQUENCE {
      reporting-quantity [0] INTEGER (0..63) OPTIONAL
   } OPTIONAL,
   component-8 [7] SEQUENCE {
      bitmap-length [0] INTEGER (0..127),
      component-2 [1] SEQUENCE (SIZE (1..128)) OF SEQUENCE {
         reporting-quantity [0] INTEGER (0..63) OPTIONAL
      },
      e-UTRAN-Measurement-Report [2] E-UTRAN-Measurement-Report-struct OPTIONAL
         ,
      component-4 [3] SEQUENCE {
         utran-CSG-Measurement-Report [0] UTRAN-CSG-Measurement-Report-IE
             OPTIONAL,
         si23-ba-used [1] INTEGER (0..1) OPTIONAL
      } OPTIONAL
   } OPTIONAL
}

MEASUREMENT-PARAMETERS-Description-struct ::= SEQUENCE {
   multiband-reporting [0] INTEGER (0..3) OPTIONAL,
   serving-band-reporting [1] INTEGER (0..3) OPTIONAL,
   scale-ord [2] INTEGER (0..3),
   component-4 [3] SEQUENCE {
      a900-REPORTING-OFFSET [0] INTEGER (0..7),
      a900-REPORTING-THRESHOLD [1] INTEGER (0..7)
   } OPTIONAL,
   component-5 [4] SEQUENCE {
      a1800-REPORTING-OFFSET [0] INTEGER (0..7),
      a1800-REPORTING-THRESHOLD [1] INTEGER (0..7)
   } OPTIONAL,
   component-6 [5] SEQUENCE {
      a400-REPORTING-OFFSET [0] INTEGER (0..7),
      a400-REPORTING-THRESHOLD [1] INTEGER (0..7)
   } OPTIONAL,
   component-7 [6] SEQUENCE {
      a1900-REPORTING-OFFSET [0] INTEGER (0..7),
      a1900-REPORTING-THRESHOLD [1] INTEGER (0..7)
   } OPTIONAL,
   component-8 [7] SEQUENCE {
      a850-REPORTING-OFFSET [0] INTEGER (0..7),
      a850-REPORTING-THRESHOLD [1] INTEGER (0..7)
   } OPTIONAL
}

RTD6-Struct ::= SEQUENCE OF INTEGER (0..63)

RTD12-Struct ::= SEQUENCE OF INTEGER (0..4095)

Real-Time-Difference-Description-struct ::= SEQUENCE {
   component-1 [0] SEQUENCE {
      ba-Index-Start-RTD [0] INTEGER (0..31) OPTIONAL,
      rtd-Struct [1] RTD6-Struct,
      rtd-Struct-list [2] SEQUENCE OF RTD6-Struct
   } OPTIONAL,
   component-2 [1] SEQUENCE {
      ba-Index-Start-RTD [0] INTEGER (0..31) OPTIONAL,
      rtd-Struct [1] RTD12-Struct,
      rtd-Struct-list [2] SEQUENCE OF RTD12-Struct
   } OPTIONAL
}

REPORT-PRIORITY-Description-struct ::= SEQUENCE {
   number-Cells [0] INTEGER (0..127),
   rep-priority [1] BIT STRING  (SIZE (0..127))
}

UTRAN-CSG-Cells-Reporting-Description-struct ::= SEQUENCE {
   component-1 [0] SEQUENCE {
      utran-csg-fdd-reporting-threshold [0] INTEGER (0..7),
      utran-csg-fdd-reporting-threshold-2 [1] INTEGER (0..63)
   } OPTIONAL,
   utran-csg-tdd-reporting-threshold [1] INTEGER (0..7) OPTIONAL
}

Measurement-information ::= SEQUENCE {
   ba-ind [0] INTEGER (0..1),
   a3G-BA-IND [1] INTEGER (0..1),
   mp-change-mark [2] INTEGER (0..1),
   mi-index [3] INTEGER (0..15),
   mi-count [4] INTEGER (0..15),
   pwrc [5] INTEGER (0..1),
   report-type [6] INTEGER (0..1),
   reporting-rate [7] INTEGER (0..1),
   invalid-bsic-reporting [8] INTEGER (0..1),
   real-Time-Difference-Description [9] Real-Time-Difference-Description-struct
       OPTIONAL,
   bsic-Description [10] BSIC-Description-struct OPTIONAL,
   report-PRIORITY-Description [11] REPORT-PRIORITY-Description-struct OPTIONAL
      ,
   measurement-Parameters-Description [12] 
      MEASUREMENT-PARAMETERS-Description-struct OPTIONAL,
   component-14 [13] SEQUENCE {
      extension-length [0] INTEGER (0..255),
      bit [1] BIT STRING  (SIZE (1..256))
   } OPTIONAL,
   a3G-Neighbour-Cell-Description [14] A3G-Neighbour-Cell-Description-struct
       OPTIONAL,
   a3G-MEASUREMENT-Parameters-Description [15] 
      A3G-MEASUREMENT-PARAMETERS-Description-struct OPTIONAL,
   component-17 [16] SEQUENCE {
      a3G-ADDITIONAL-MEASUREMENT-Parameters-Description-2 [0] 
         A3G-Additional-Measurement-Parameters-Description-2-struct OPTIONAL,
      component-2 [1] SEQUENCE {
         component-1 [0] SEQUENCE {
            a700-REPORTING-OFFSET [0] INTEGER (0..7),
            a700-REPORTING-THRESHOLD [1] INTEGER (0..7)
         } OPTIONAL,
         component-2 [1] SEQUENCE {
            a810-REPORTING-OFFSET [0] INTEGER (0..7),
            a810-REPORTING-THRESHOLD [1] INTEGER (0..7)
         } OPTIONAL,
         component-3 [2] SEQUENCE {
            a3G-Supplementary-Parameters-Description [0] 
               A3G-Supplementary-Parameters-Description-struct OPTIONAL,
            e-UTRAN-Parameters-Description [1] 
               E-UTRAN-Parameters-Description-struct OPTIONAL,
            e-UTRAN-CSG-Description [2] E-UTRAN-CSG-Description-struct OPTIONAL
               ,
            component-4 [3] SEQUENCE {
               a3G-CSG-Description [0] A3G-CSG-Description-struct OPTIONAL,
               utran-CSG-Cells-Reporting-Description [1] 
                  UTRAN-CSG-Cells-Reporting-Description-struct OPTIONAL
            } OPTIONAL
         } OPTIONAL
      } OPTIONAL
   } OPTIONAL
}

Paging-Information ::= SEQUENCE {
   mobile-identity [0] EXPLICIT MobileIdentity,
   channel-first [1] INTEGER (0..3),
   eMLPP-priority [2] INTEGER (0..7) OPTIONAL
}

NOTIFICATION-FACCH ::= SEQUENCE {
   component-1 [0] EXPLICIT CHOICE {
      group-Call-information [0] Group-Call-information,
      paging-Information [1] Paging-Information
   },
   component-2 [1] SEQUENCE {
      component-1 [0] SEQUENCE {
         cell-global-count [0] INTEGER (0..3),
         b22-count [1] INTEGER (0..1)
      } OPTIONAL,
      vstk-rand [1] BIT STRING  (SIZE (36)) OPTIONAL
   } OPTIONAL,
   component-3 [2] SEQUENCE {
      priority-Uplink-Access [0] Priority-Uplink-Access,
      emergency-Ind [1] Emergency-Ind,
      amr-Config [2] INTEGER (0..15) OPTIONAL,
      paging-Cause [3] INTEGER (0..3) OPTIONAL,
      component-5 [4] SEQUENCE {
         sms-Data-Confidentiality-Ind [0] INTEGER (0..1),
         sms-Guaranteed-Privacy-Ind [1] INTEGER (0..1)
      } OPTIONAL
   } OPTIONAL
}

NOTIFY-APPLICATION-DATA ::= SEQUENCE {
   application-data [0] BIT STRING  (SIZE (72)),
   data-identity [1] INTEGER (0..255),
   component-3 [2] SEQUENCE {
      msisdn-length [0] INTEGER (0..15),
      msisdn [1] BIT STRING  (SIZE (0..120))
   } OPTIONAL
}

Non-Segmented-SMS-Description-struct ::= SEQUENCE {
   length [0] INTEGER (0..255),
   sms-Reference-Number [1] INTEGER (0..15),
   sms-Final-Content [2] BIT STRING  (SIZE (0..255))
}

SYSTEM-INFORMATION-TYPE-10ter ::= SEQUENCE {
   cell-Channel-Description [0] BIT STRING  (SIZE (128)),
   si10ter-Rest-Octets [1] SI10ter-Rest-Octets
}

Segmented-SMS-Description-struct ::= SEQUENCE {
   sms-Reference-Number [0] INTEGER (0..15),
   segment-Number [1] INTEGER (0..15),
   component-3 [2] EXPLICIT CHOICE {
      sms-Content [0] BIT STRING ,
      choice-2 [1] SEQUENCE {
         length [0] INTEGER (0..255),
         sms-Final-Content [1] BIT STRING  (SIZE (0..255))
      }
   }
}

UPLINK-FREE ::= SEQUENCE {
   uplink-Access-Request [0] LHType,
   uplink-Identity-Code [1] INTEGER (0..63) OPTIONAL,
   component-3 [2] SEQUENCE {
      emergency-Ind [0] INTEGER (0..1) OPTIONAL
   } OPTIONAL
}

New-Group-Channel-Description ::= SEQUENCE {
   channel-Description [0] INTEGER (0..16777215),
   component-2 [1] EXPLICIT CHOICE {
      mobile-Allocation [0] Mobile-Allocation,
      frequency-Short-List [1] BIT STRING  (SIZE (64))
   } OPTIONAL
}

VBS-VGCS-RECONFIGURE ::= SEQUENCE {
   new-Group-Channel-Description [0] New-Group-Channel-Description,
   starting-Time [1] INTEGER (0..65535),
   additional-Segment [2] INTEGER (0..1)
}

VBS-VGCS-RECONFIGURE2 ::= SEQUENCE {
   new-Cell-Channel-Description [0] BIT STRING  (SIZE (128)),
   starting-Time [1] INTEGER (0..65535)
}

VGCS-ADDITIONAL-INFO ::= SEQUENCE {
   talker-identity-length [0] INTEGER (0..31),
   filler-bits [1] INTEGER (0..7),
   talker-identity [2] BIT STRING  (SIZE (0..248))
}

Validity-Information ::= SEQUENCE {
   validity-bitmap [0] INTEGER (0..7) OPTIONAL
}

VGCS-Neighbour-Cell-Information ::= SEQUENCE {
   si10bis-Sequence [0] INTEGER (0..3),
   component-2 [1] SEQUENCE OF SEQUENCE {
      bsic [0] INTEGER (0..63) OPTIONAL,
      validity-Information [1] Validity-Information
   },
   si10bis-Neighbour-Cell-Info-list [2] SEQUENCE OF SI10bis-Neighbour-Cell-Info
}

VGCS-SMS-INFORMATION ::= CHOICE {
   non-Segmented-SMS-Description [0] Non-Segmented-SMS-Description-struct,
   segmented-SMS-Description [1] Segmented-SMS-Description-struct
}

-- Messages sent on DCCH downlink, in unacknowledged mode
--rr-short-PD is always 0 and short-layer-2-header is also always 0.  They
--should be auxiliary fields, but I don't think have a way to make them that.
RR-Short-PD-PDU ::= SEQUENCE {
   rr-short-PD [0] INTEGER (0..1) DEFAULT 0,
   msgType [1] RR-SHORT-CLASS.&msgType ({RR-Short-PD-Messages}) (0..31),
   short-layer-2-header [2] INTEGER (0..3) DEFAULT 0,
   data [3] EXPLICIT RR-SHORT-CLASS.&Value ({RR-Short-PD-Messages}{@msgType})
}

--9.1.1 Additional assignment
--<is3GMessage/>
AdditionalAssignment ::= SEQUENCE {
   channel-description [0] Channel-Description,
   --<iei format="tlv">72</iei>
   mobile-allocation [1] Mobile-Allocation OPTIONAL,
   --<iei format="tv" length="3">7C</iei>
   starting-time [2] Starting-Time OPTIONAL,
   ...,
   [[ 12:
      extTSCSet [3] ExtendedTSCSet OPTIONAL
   ]]
}

-- 9.1.53 Application Information 
--<is3GMessage/>
ApplicationInformation ::= SEQUENCE {
   apduFlags [0] APDU-Flags,
   apduId [1] APDU-ID,
   apduData [2] APDU-Data
}

-- 9.1.2 Assignment Command 
--<is3GMessage/>
AssignmentCommand ::= SEQUENCE {
   descFirstChannelAfterTime [0] Channel-Description-2,
   powerCommand [1] Power-Command,
   --<iei format="tlv">5</iei>
   freqListAfterTime [2] Frequency-List OPTIONAL,
   --<iei format="tv" length="17">62</iei>
   cellChannelDesc [3] EXPLICIT Cell-Channel-Description OPTIONAL,
   --<iei format="tlv">10</iei>
   descMultislotConfig [4] Multislot-Allocation OPTIONAL,
   --<iei format="tv" length="2">63</iei>
   modeFirstChannel [5] Channel-Mode OPTIONAL,
   --<iei format="tv" length="2">11</iei>
   modeChannelSet2 [6] Channel-Mode OPTIONAL,
   --<iei format="tv" length="2">13</iei>
   modeChannelSet3 [7] Channel-Mode OPTIONAL,
   --<iei format="tv" length="2">14</iei>
   modeChannelSet4 [8] Channel-Mode OPTIONAL,
   --<iei format="tv" length="2">15</iei>
   modeChannelSet5 [9] Channel-Mode OPTIONAL,
   --<iei format="tv" length="2">16</iei>
   modeChannelSet6 [10] Channel-Mode OPTIONAL,
   --<iei format="tv" length="2">17</iei>
   modeChannelSet7 [11] Channel-Mode OPTIONAL,
   --<iei format="tv" length="2">18</iei>
   modeChannelSet8 [12] Channel-Mode OPTIONAL,
   --<iei format="tv" length="4">64</iei>
   descSecondChannelAfterTime [13] Channel-Description OPTIONAL,
   --<iei format="tv" length="2">66</iei>
   modeSecondChannel [14] Channel-Mode-2 OPTIONAL,
   --<iei format="tlv">72</iei>
   mobileAllocationAfterTime [15] Mobile-Allocation OPTIONAL,
   --<iei format="tv" length="3">7C</iei>
   startingTime [16] Starting-Time OPTIONAL,
   --<iei format="tlv">19</iei>
   frequencyListBeforeTime [17] Frequency-List OPTIONAL,
   --<iei format="tv" length="4">1C</iei>
   descFirstChannelBeforeTime [18] Channel-Description-2 OPTIONAL,
   --<iei format="tv" length="4">1D</iei>
   descSecondChannelBeforeTime [19] Channel-Description OPTIONAL,
   --<iei format="tv" length="10">1E</iei>
   frequencyChannelSequenceBeforeTime [20] Frequency-Channel-Sequence OPTIONAL,
   --<iei format="tlv">21</iei>
   mobileAllocationBeforeTime [21] Mobile-Allocation OPTIONAL,
   --<iei format="tv" length="1">9</iei>
   cipherModeSetting [22] Cipher-Mode-Setting OPTIONAL,
   --<iei format="tlv">1</iei>
   vgcsTargetModeIndication [23] VGCS-target-mode-Indication OPTIONAL,
   --<iei format="tlv">3</iei>
   multiRateConfig [24] Multirate-Configuration OPTIONAL,
   --<iei format="tlv">4</iei>
   vgcsCipheringParameters [25] VGCS-Ciphering-Parameters OPTIONAL,
   ...,
   [[ 12:
      extTSCSetAfterTime [26] ExtendedTSCSet OPTIONAL,
      extTSCSetBeforeTime [27] ExtendedTSCSet OPTIONAL
   ]]
}

-- 9.1.5 Channel Mode Modify 
--<is3GMessage/>
ChannelModeModify ::= SEQUENCE {
   channelDescription [0] Channel-Description-2,
   channelMode [1] Channel-Mode,
   --<iei format="tlv">1</iei>
   vgcsTargetModeIndication [2] VGCS-target-mode-Indication OPTIONAL,
   --<iei format="tlv">3</iei>
   multiRateConfig [3] Multirate-Configuration OPTIONAL,
   --<iei format="tlv">4</iei>
   vgcsCipheringParams [4] VGCS-Ciphering-Parameters OPTIONAL,
   ...,
   [[ 12:
      extTSCSetAfterTime [5] ExtendedTSCSet OPTIONAL
   ]]
}

-- 9.1.7 Channel Release 
--<is3GMessage/>
ChannelRelease ::= SEQUENCE {
   rrCause [0] INTEGER (0..255),
   --<iei format="tlv">73</iei>
   baRange [1] BA-Range OPTIONAL,
   --<iei format="tlv">74</iei>
   groupChannelDescription [2] Group-Channel-Description OPTIONAL,
   --<iei format="tv" length="1">8</iei>
   groupCipherKeyNumber [3] INTEGER (0..15) OPTIONAL,
   --<iei format="tv" length="1">C</iei>
   gprsResumption [4] GPRS-Resumption OPTIONAL,
   --<iei format="tlv">75</iei>
   baListPref [5] BA-List-Pref OPTIONAL,
   --<iei format="tlv">76</iei>
   utranFreqList [6] UTRAN-Freq-List OPTIONAL,
   --<iei format="tv" length="17">62</iei>
   cellChannelDesc [7] EXPLICIT Cell-Channel-Description OPTIONAL,
   --<iei format="tlv">77</iei>
   cellSelIndAfterRelease [8] Cell-Sel-Ind-Post-Rel-TCH-SDCCH OPTIONAL,
   --<iei format="tv" length="1">A</iei>
   enhancedDtmCsReleaseInd [9] Enhanced-DTM-CS-Release-Indication OPTIONAL,
   --<iei format="tlv">4</iei>
   vgcsCipheringParams [10] VGCS-Ciphering-Parameters OPTIONAL,
   --<iei format="tlv">78</iei>
   groupChannelDesc2 [11] Group-Channel-Description-2 OPTIONAL,
   --<iei format="tlv">79</iei>
   talkerId [12] Talker-Identity OPTIONAL,
   --<iei format="tlv">7A</iei>
   talkerPriorityStatus [13] Talker-Priority-Status OPTIONAL,
   --<iei format="tlv">7B</iei>
   vgcsAmrConfig [14] VGCS-AMR-Configuration OPTIONAL,
   --<iei format="tlv">7C</iei>
   individualPriorities [15] Individual-priorities OPTIONAL
}

-- 9.1.9 Ciphering Mode Command 
--<is3GMessage/>
CipheringModeCommand ::= SEQUENCE {
   cipherResponse [0] Cipher-Response,
   cipheringMOdeSetting [1] Cipher-Mode-Setting
}

-- 9.1.12 Classmark Enquiry 
--<is3GMessage/>
ClassmarkEnquiry ::= SEQUENCE {
   --<iei format="tlv">10</iei>
   classmarkEnquiryMask [0] Classmark-Enquiry-Mask OPTIONAL
}

-- 9.1.12b Configuration Change Command 
--<is3GMessage/>
ConfigurationChangeCommand ::= SEQUENCE {
   descriptionMultislotConfig [0] Multislot-Allocation,
   --<iei format="tv" length="2">63</iei>
   modeChannelSet1 [1] Channel-Mode OPTIONAL,
   --<iei format="tv" length="2">11</iei>
   modeChannelSet2 [2] Channel-Mode OPTIONAL,
   --<iei format="tv" length="2">13</iei>
   modeChannelSet3 [3] Channel-Mode OPTIONAL,
   --<iei format="tv" length="2">14</iei>
   modeChannelSet4 [4] Channel-Mode OPTIONAL,
   --<iei format="tv" length="2">15</iei>
   modeChannelSet5 [5] Channel-Mode OPTIONAL,
   --<iei format="tv" length="2">16</iei>
   modeChannelSet6 [6] Channel-Mode OPTIONAL,
   --<iei format="tv" length="2">17</iei>
   modeChannelSet7 [7] Channel-Mode OPTIONAL,
   --<iei format="tv" length="2">18</iei>
   modeChannelSet8 [8] Channel-Mode OPTIONAL
}

-- 9.1.44b Data Indication 
--<is3GMessage/>
DataIndication ::= SEQUENCE {
   mobileIdentity [0] TMSI,
   applicationData [1] Application-Data,
   dataIdentity [2] Data-Identity
}

-- 9.1.12e DtmAssignmentCommand 
--<is3GMessage/>
DtmAssignmentCommand ::= SEQUENCE {
   csPowerCommand [0] Power-Command,
   descrCsChannel [1] Channel-Description,
   gprsBroadcastInfo [2] GPRS-broadcast-information,
   --<iei format="tv" length="17">10</iei>
   cellChannelDescription [3] EXPLICIT Cell-Channel-Description OPTIONAL,
   --<iei format="tv" length="2">11</iei>
   channelMode [4] Channel-Mode OPTIONAL,
   --<iei format="tlv">12</iei>
   frequencyList [5] Frequency-List OPTIONAL,
   --<iei format="tlv">13</iei>
   mobileAllocation [6] Mobile-Allocation OPTIONAL,
   --<iei format="tlv">15</iei>
   descrUplinkPacketChannelAssignment [7] RR-Packet-Uplink-Assignment OPTIONAL,
   --<iei format="tlv">16</iei>
   descrDownlinkPacketChannelAssignment [8] RR-Packet-Downlink-Assignment
       OPTIONAL,
   --<iei format="tlv">17</iei>
   multiRateConfig [9] Multirate-Configuration OPTIONAL,
   --<iei format="tv" length="1">9</iei>
   cipheringMOdeSetting [10] Cipher-Mode-Setting OPTIONAL,
   --<iei format="tlv">18</iei>
   mobileAllocationC2 [11] Mobile-Allocation OPTIONAL,
   --<iei format="tlv">19</iei>
   frequencyListC2 [12] Frequency-List OPTIONAL,
   --<iei format="tlv">20</iei>
   descrDownlinkPacketChannelAssignmentType2 [13] 
      RR-Packet-Downlink-Assignment-Type-2 OPTIONAL,
   --<iei format="tlv">21</iei>
   channelDescrC2 [14] Channel-Description-3 OPTIONAL,
   ...,
   [[ 12:
      extTSCSetAfterTime [15] ExtendedTSCSet OPTIONAL
   ]]
}

-- 9.1.12g DTM Information 
--<is3GMessage/>
DtmInformation ::= SEQUENCE {
   routingAreaIdentification [0] RoutingAreaIdent,
   dtmInfoDetails [1] DTM-Information-Details
}

-- 9.1.12h DTM Reject 
--<is3GMessage/>
DtmReject ::= SEQUENCE {
   dtmWaitIndication [0] Wait-Indication
}

-- 9.1.13 Frequency Redefinition 
--<is3GMessage/>
FrequencyRedefinition ::= SEQUENCE {
   channelDescr [0] Channel-Description,
   mobileAllocation [1] Mobile-Allocation,
   startingTime [2] Starting-Time,
   --<iei format="tv" length="17">62</iei>
   cellChannelDescr [3] EXPLICIT Cell-Channel-Description OPTIONAL,
   --<iei format="tv" length="1">9</iei>
   carrierIndication [4] Carrier-Indication OPTIONAL,
   --<iei format="tlv">11</iei>
   mobileAllocationC2 [5] Mobile-Allocation OPTIONAL,
   --<iei format="tv" length="3">12</iei>
   channelDescriptionC2 [6] Channel-Description-3 OPTIONAL,
   ...,
   [[ 12:
      extTSCSetAfterTime [7] ExtendedTSCSet OPTIONAL
   ]]
}

-- 9.6.1 GPRS Information 
--<is3GMessage/>
GprsInformation ::= SEQUENCE {
   tlli [0] TLLI,
   llcPDU [1] LLC-PDU-Container
}

-- 9.1.15 Handover Command 
--<is3GMessage/>
HandoverCommand ::= SEQUENCE {
   cellDescr [0] Cell-Description,
   descrFirstChannelAfterTime [1] Channel-Description-2,
   handoverReference [2] Handover-Reference,
   powerCommandAndAccessType [3] Power-Command-and-access-type,
   --<iei format="tv" length="1">D</iei>
   synchronizationIndication [4] Synchronization-Indication OPTIONAL,
   --<iei format="tv" length="10">2</iei>
   freqShortListAfterTime [5] Frequency-Short-List OPTIONAL,
   --<iei format="tlv">5</iei>
   freqListAfterTime [6] Frequency-List OPTIONAL,
   --<iei format="tv" length="17">62</iei>
   cellChannelDescr [7] EXPLICIT Cell-Channel-Description OPTIONAL,
   --<iei format="tlv">10</iei>
   descrMultislotConfig [8] Multislot-Allocation OPTIONAL,
   --<iei format="tv" length="2">63</iei>
   modeFirstChannel [9] Channel-Mode OPTIONAL,
   --<iei format="tv" length="2">11</iei>
   modeChannelSet2 [10] Channel-Mode OPTIONAL,
   --<iei format="tv" length="2">13</iei>
   modeChannelSet3 [11] Channel-Mode OPTIONAL,
   --<iei format="tv" length="2">14</iei>
   modeChannelSet4 [12] Channel-Mode OPTIONAL,
   --<iei format="tv" length="2">15</iei>
   modeChannelSet5 [13] Channel-Mode OPTIONAL,
   --<iei format="tv" length="2">16</iei>
   modeChannelSet6 [14] Channel-Mode OPTIONAL,
   --<iei format="tv" length="2">17</iei>
   modeChannelSet7 [15] Channel-Mode OPTIONAL,
   --<iei format="tv" length="2">18</iei>
   modeChannelSet8 [16] Channel-Mode OPTIONAL,
   --<iei format="tv" length="4">64</iei>
   descrSecondChannelAfterTime [17] Channel-Description OPTIONAL,
   --<iei format="tv" length="2">66</iei>
   modeSecondChannel [18] Channel-Mode-2 OPTIONAL,
   --<iei format="tv" length="10">69</iei>
   freqChannelSequenceAfterTime [19] Frequency-Channel-Sequence OPTIONAL,
   --<iei format="tlv">72</iei>
   mobileAllocationAfterTime [20] Mobile-Allocation OPTIONAL,
   --<iei format="tv" length="3">7C</iei>
   startingTime [21] Starting-Time OPTIONAL,
   --<iei format="tlv">7B</iei>
   realTimeDifference [22] Time-Difference OPTIONAL,
   --<iei format="tv" length="2">7D</iei>
   timingAdvance [23] Timing-Advance OPTIONAL,
   --<iei format="tv" length="10">12</iei>
   freqShortListBeforeTime [24] Frequency-Short-List OPTIONAL,
   --<iei format="tlv">19</iei>
   freqListBeforeTime [25] Frequency-List OPTIONAL,
   --<iei format="tv" length="4">1C</iei>
   descrFirstChannelBeforeTime [26] Channel-Description-2 OPTIONAL,
   --<iei format="tv" length="4">1D</iei>
   descrSecondChannelBeforeTime [27] Channel-Description OPTIONAL,
   --<iei format="tv" length="10">1E</iei>
   freqChannelSequneceBeforeTime [28] Frequency-Channel-Sequence OPTIONAL,
   --<iei format="tlv">21</iei>
   mobileAllocationBeforeTime [29] Mobile-Allocation OPTIONAL,
   --<iei format="tv" length="1">9</iei>
   cipherModeSetting [30] Cipher-Mode-Setting OPTIONAL,
   --<iei format="tlv">1</iei>
   vgcsTargetModeIndication [31] VGCS-target-mode-Indication OPTIONAL,
   --<iei format="tlv">3</iei>
   multirateConfig [32] Multirate-Configuration OPTIONAL,
   --<iei format="tlv">76</iei>
   dynamicArfcnMapping [33] Dynamic-ARFCN-Mapping OPTIONAL,
   --<iei format="tlv">4</iei>
   vgcsCipheringParameters [34] VGCS-Ciphering-Parameters OPTIONAL,
   --<iei format="tv" length="2">51</iei>
   dedicatedServiceInformation [35] Dedicated-Service-Information OPTIONAL,
   --<iei format="tv" length="1">A</iei>
   plmnIndex [36] PLMN-Index OPTIONAL,
   ...,
   [[ 12:
      extTSCSetAfterTime [37] ExtendedTSCSet OPTIONAL,
      extTSCSetBeforeTime [38] ExtendedTSCSet OPTIONAL
   ]]
}

-- 9.1.15a Inter System To UTRAN Handover Command 
--<is3GMessage/>
InterSystemToUtranHandoverCommand ::= SEQUENCE {
   handoverToUtranCommand [0] Handover-To-UTRAN-Command
   -- CN to MS transparent information is left as an unknown IE.  As of Release
   -- 15, the specification does not provide the IEI to be used with it.
}

-- 9.1.15b Inter System To cdma2000 Handover Command 
--<is3GMessage/>
InterSystemToCdma2000HandoverCommand ::= SEQUENCE {
   handoverToCdma2000Command [0] Handover-To-cdma2000-Command
}

/* 9.1.15c Handover To GERAN Iu Mode Command 
   No message type value is defined for this message, preventing its
   implementation.
--<is3GMessage/>
HandoverToGeranIuModeCommand ::= SEQUENCE {
   radioBearerReconfig Radio-Bearer-Reconfiguration
}*/
-- 9.1.15d Inter System To E-UTRAN Handover Command 
--<is3GMessage/>
InterSystemToEutranHandoverCommand ::= SEQUENCE {
   dlDcchMessage [0] DL-DCCH-Message,
   cnsToMsTransparentInfo [1] CN-to-MS-transparent-information
}

-- 9.1.21j MBMS Announcement 
--<is3GMessage/>
MbmsAnnouncement ::= SEQUENCE {
   tempMobileGroupId [0] TMGI,
   --<iei format="tv" length="2">1</iei>
   mbmsSessionIdentity [1] MBMS-Session-Identity OPTIONAL,
   --<iei format="tlv">2</iei>
   mbmsCountingChannelDescr [2] MPRACH-description OPTIONAL,
   --<iei format="tlv">3</iei>
   mbmsPtmChannelDescr [3] MBMS-p-t-m-Channel-Description OPTIONAL,
   --<iei format="tlv">4</iei>
   mbmsSessionParametersList [4] MBMS-Session-Parameters-List OPTIONAL,
   --<iei format="tv" length="2">5</iei>
   restrictionTimer [5] Restriction-Timer OPTIONAL
}

-- 9.1.21f Packet Assignment 
--<is3GMessage/>
PacketAssignment ::= SEQUENCE {
   gprsBroadcastInfo [0] GPRS-broadcast-information,
   --<iei format="tlv">22</iei>
   descrUplinkPacketChannelAssignment [1] RR-Packet-Uplink-Assignment OPTIONAL,
   --<iei format="tlv">23</iei>
   descrDownlinkPacketChannelAssignment [2] RR-Packet-Downlink-Assignment
       OPTIONAL,
   --<iei format="tlv">12</iei>
   freqListC2 [3] Frequency-List OPTIONAL,
   --<iei format="tlv">13</iei>
   mobileAllocationC2 [4] Mobile-Allocation OPTIONAL,
   --<iei format="tv" length="3">14</iei>
   channelDescrC2 [5] Channel-Description-3 OPTIONAL,
   --<iei format="tlv">24</iei>
   descrDownlinkPacketChannelAssignmentType2 [6] 
      RR-Packet-Downlink-Assignment-Type-2 OPTIONAL,
   ...,
   [[ 12:
      extTSCSet [7] ExtendedTSCSet OPTIONAL
   ]]
}

-- 9.1.21g Packet Notification 
--<is3GMessage/>
PacketNotification ::= SEQUENCE {
   --<iei format="tv" length="5">10</iei>
   packetTMSI [0] TMSI OPTIONAL,
   --<iei format="tlv">11</iei>
   mobileIdentity [1] EXPLICIT MobileIdentity OPTIONAL
}

-- 9.1.26 Partial Release 
--<is3GMessage/>
PartialRelease ::= SEQUENCE {
   channelDescription [0] Channel-Description
}

-- 9.1.28 Physical Information 
--<is3GMessage/>
PhysicalInformation ::= SEQUENCE {
   timingAdvance [0] Timing-Advance
}

-- 9.1.29 RR Status 
--<is3GMessage/>
RrStatus ::= SEQUENCE {
   rrCause [0] INTEGER (0..255)
}

-- 9.1.46 Uplink Busy 
--<is3GMessage/>
UplinkBusy ::= SEQUENCE {
   --<iei format="tlv">31</iei>
   talkerPriorityEmergencyInd [0] Talker-Priority-Status OPTIONAL,
   --<iei format="tv" length="5">32</iei>
   token [1] Token OPTIONAL,
   --<iei format="tlv">33</iei>
   talkerIdentity [2] Talker-Identity OPTIONAL,
   --<iei format="tv" length="1">8</iei>
   uplinkAccessIndication [3] Uplink-Access-Indication OPTIONAL
}

-- 9.1.48 Uplink Release 
--<is3GMessage/>
UplinkRelease ::= SEQUENCE {
   rrCause [0] INTEGER (0..255)
}

-- 9.1.49 VGCS Uplink Grant 
--<is3GMessage/>
VgcsUplinkGrant ::= SEQUENCE {
   requestReference [0] Request-Reference,
   timingAdvance [1] Timing-Advance
}

DL-DCCH-PDU ::= SEQUENCE {
   l3HdrOpts [0] EXPLICIT L3HdrOptions, -- L3 header, octet 1, bits 5 thru 8
   protoDiscr [1] NAS-PROTOCOL-CLASS.&protoDiscr ({DL-DCCH-Messages}),
   msgType [2] NAS-PROTOCOL-CLASS.&msgType ({DL-DCCH-Messages}) (0..255),
   data [3] EXPLICIT NAS-PROTOCOL-CLASS.&Value ({DL-DCCH-Messages}{@protoDiscr,
      @msgType})
}

-- 9.1.11b cdma2000 Classmark Change 
--<is3GMessage/>
Cdma2000ClassmarkChange ::= SEQUENCE {
   terminalInfo [0] OCTET STRING,
   securityStatus [1] OCTET STRING,
   bandClassInfo [2] OCTET STRING,
   powerClassInfo [3] OCTET STRING,
   operatingModeInfo [4] OCTET STRING,
   serviceOptionInfo [5] OCTET STRING,
   multiplexOptionInfo [6] OCTET STRING,
   powerControlInfo [7] OCTET STRING,
   capabilityInfo [8] OCTET STRING,
   channelConfigCapabilityInfo [9] OCTET STRING,
   extendedMultiplexOptionInfo [10] OCTET STRING,
   bandSubclassInfo [11] OCTET STRING,
   encryptionCapability [12] OCTET STRING
}

-- 9.1.6 Channel Mode Modify Acknowledge 
--<is3GMessage/>
ChannelModeModifyAck ::= SEQUENCE {
   channelDesc [0] Channel-Description,
   channelMode [1] INTEGER (0..255),
   ...,
   [[ 12:
      extTSCSetAfterTime [2] ExtendedTSCSet OPTIONAL
   ]]
}

-- 9.1.10 Ciphering Mode Complete 
--<is3GMessage/>
CipheringModeComplete ::= SEQUENCE {
   --<iei format="tlv">17</iei>
   mobileEquipmentIdentity [0] EXPLICIT MobileIdentity OPTIONAL
}

-- 9.1.11 Classmark Change 
--<is3GMessage/>
ClassmarkChange ::= SEQUENCE {
   mobileStationClassmark [0] MobileStationClassmark2,
   --<iei format="tlv">20</iei>
   addlMobileStationClassmarkInfo [1] MobileStationClassmark3 OPTIONAL
}

-- 9.1.12d Configuration Change Reject 
--<is3GMessage/>
ConfigurationChangeReject ::= SEQUENCE {
   rrCause [0] INTEGER (0..255)
}

-- 9.1.44c Data Indication 2 
--<is3GMessage/>
DataIndication2 ::= SEQUENCE {
   mobileIdentity [0] TMSI,
   reducedGroupCallRef [1] Reduced-group-or-broadcast-call-reference,
   applicationData [2] Application-Data,
   dataIdentity [3] Data-Identity
}

-- 9.1.12f DTM Assignment Failure 
--<is3GMessage/>
DtmAssignmentFailure ::= SEQUENCE {
   rrCause [0] INTEGER (0..255)
}

-- 9.1.12i DTM Request 
--<is3GMessage/>
DtmRequest ::= SEQUENCE {
   tlli [0] TLLI,
   channelRequestDescr2 [1] Channel-Request-Description-2
}

-- 9.1.11d GERAN IU Mode Classmark Change 
--<is3GMessage/>
GeranIuModeClassmarkChange ::= SEQUENCE {
   geranIuModeClassmark [0] GERAN-Iu-Mode-Classmark
}

-- 9.1.13b GPRS Suspension Request 
--<is3GMessage/>
GprsSuspensionRequest ::= SEQUENCE {
   tlli [0] TLLI,
   routingAreaIdentification [1] RoutingAreaIdent,
   suspensionCause [2] Suspension-Cause,
   --<iei format="tv" length="2">1</iei>
   serviceSupport [3] Service-Support OPTIONAL
}

-- 9.1.16 Handover Complete 
--<is3GMessage/>
HandoverComplete ::= SEQUENCE {
   rrCause [0] INTEGER (0..255),
   --<iei format="tlv">77</iei>
   mobileObservedTimeDiff [1] Mobile-Time-Difference OPTIONAL,
   --<iei format="tlv">67</iei>
   mobileObservedTimeDiffOnHyperframeLevel [2] 
      Mobile-Time-Difference-on-Hyperframe-level OPTIONAL
}

-- 9.1.17 Handover Failure 
--<is3GMessage/>
HandoverFailure ::= SEQUENCE {
   rrCause [0] INTEGER (0..255),
   --<iei format="tv" length="1">9</iei>
   psCause [1] PS-Cause OPTIONAL
}

-- 9.1.21d Notification Response 
--<is3GMessage/>
NotificationResponse ::= SEQUENCE {
   mobileStationClassmark [0] MobileStationClassmark2,
   mobileIdentity [1] EXPLICIT MobileIdentity,
   groupOrBroadcastCallReference [2] DescrGroupOrBcastCallRef
}

-- 9.1.25 Paging Response 
--<is3GMessage/>
PagingResponse ::= SEQUENCE {
   spare [0] INTEGER (0..15) DEFAULT 0,
   cipheringKeySequence [1] INTEGER (0..15),
   mobileStationClassmark [2] MobileStationClassmark2,
   mobileIdentity [3] EXPLICIT MobileIdentity,
   --<iei format="tv" length="1">C</iei>
   additionalUpdateParameters [4] AddnUpdateParams OPTIONAL
}

-- 9.1.44a Priority Uplink Request 
--<is3GMessage/>
PriorityUplinkRequest ::= SEQUENCE {
   establishmentCauseRandomRef [0] Random-Reference-Establishment-Cause,
   token [1] Token,
   reducedGroupCallRef [2] Reduced-group-or-broadcast-call-reference,
   mobileIdentity [3] EXPLICIT MobileIdentity
}

-- 9.1.56 Service Information 
--<is3GMessage/>
ServiceInformation ::= SEQUENCE {
   tlli [0] TLLI,
   routingAreaIdent [1] RoutingAreaIdent,
   serviceSupport [2] Service-Support
}

-- 9.1.44 Talker Indication 
--<is3GMessage/>
TalkerIndication ::= SEQUENCE {
   mobileStationClassmark [0] MobileStationClassmark2,
   mobileIdentity [1] EXPLICIT MobileIdentity,
   --<iei format="tv" length="1">B</iei>
   cipheringKeySequenceNumber [2] CiphKeySeqNum OPTIONAL
}

-- 9.1.11a UTRAN Classmark Change 
--<is3GMessage/>
UtranClassmarkChange ::= SEQUENCE {
   utranClassmark [0] UTRAN-Classmark
}

UL-DCCH-PDU ::= SEQUENCE {
   l3HdrOpts [0] EXPLICIT L3HdrOptions, -- L3 header, octet 1, bits 5 thru 8
   protoDiscr [1] NAS-PROTOCOL-CLASS.&protoDiscr ({UL-DCCH-Messages}),
   msgType [2] NAS-PROTOCOL-CLASS.&msgType ({UL-DCCH-Messages}) (0..255),
   data [3] EXPLICIT NAS-PROTOCOL-CLASS.&Value ({UL-DCCH-Messages}{@protoDiscr,
      @msgType})
}

-- 9.1.21 Measurement Report 
--<is3GMessage/>
MeasurementReport ::= SEQUENCE {
   measurementResults [0] Measurement-Results
}

-- 9.1.52 Extended Measurement Report 
--<is3GMessage/>
ExtendedMeasurementReport ::= SEQUENCE {
   extendedMeasurementResults [0] Extended-Measurement-Results
}

UL-SACCH-PDU ::= SEQUENCE {
   l3HdrOpts [0] EXPLICIT L3HdrOptions, -- L3 header, octet 1, bits 5 thru 8
   protoDiscr [1] NAS-PROTOCOL-CLASS.&protoDiscr ({UL-SACCH-Messages}),
   msgType [2] NAS-PROTOCOL-CLASS.&msgType ({UL-SACCH-Messages}) (0..255),
   data [3] EXPLICIT NAS-PROTOCOL-CLASS.&Value ({UL-SACCH-Messages}{@protoDiscr
      ,@msgType})
}

-- 9.1.18 Immediate Assignment  
--<is3GMessage checkContainer="true"/>
--<cEncFuncFname>TS44018Enc_Immediate_Assignment.c</cEncFuncFname>
--<cDecFuncFname>TS44018Dec_Immediate_Assignment.c</cDecFuncFname>
ImmediateAssignment ::= SEQUENCE {
   dedicatedModeOrTBF [0] Dedicated-mode-or-TBF,
   pageMode [1] Page-Mode,
   channelDescr [2] Channel-Description OPTIONAL,
   packetChannelDescr [3] Packet-Channel-Description OPTIONAL,
   requestReference [4] Request-Reference,
   timingAdvance [5] Timing-Advance,
   mobileAllocation [6] Mobile-Allocation,
   --<iei format="tv" length="3">7C</iei>
   startingTime [7] Starting-Time OPTIONAL,
   ...,
   [[ 12:
      extTSCSet [8] ExtendedTSCSet OPTIONAL
   ]]
}

-- 9.1.19 Immediate Assignment Extended 
--<is3GMessage checkContainer="true"/>
ImmediateAssignmentExtended ::= SEQUENCE {
   featureIndicator [0] Feature-Indicator,
   pageMode [1] Page-Mode,
   channelDescr1 [2] Channel-Description,
   requestReference1 [3] Request-Reference,
   timingAdvance1 [4] Timing-Advance,
   channelDescr2 [5] Channel-Description,
   requestReference2 [6] Request-Reference,
   timingAdvance2 [7] Timing-Advance,
   mobileAllocation [8] Mobile-Allocation,
   --<iei format="tv" length="3">7C</iei>
   startingTime [9] Starting-Time OPTIONAL
}

-- 9.1.20 Immediate Assignment Reject 
--<is3GMessage checkContainer="true"/>
ImmediateAssignmentReject ::= SEQUENCE {
   featureIndicator [0] Feature-Indicator,
   pageMode [1] Page-Mode,
   requestReference1 [2] Request-Reference,
   waitIndication1 [3] Wait-Indication,
   requestReference2 [4] Request-Reference,
   waitIndication2 [5] Wait-Indication,
   requestReference3 [6] Request-Reference,
   waitIndication3 [7] Wait-Indication,
   requestReference4 [8] Request-Reference,
   waitIndication4 [9] Wait-Indication
}

-- 9.1.18b Immediate Packet Assignment 
--<is3GMessage checkContainer="true"/>
ImmediatePacketAssignment ::= SEQUENCE {
   featureIndicator [0] Feature-Indicator,
   pageMode [1] Page-Mode
}

-- 9.1.22 Paging Request Type 1 
--<is3GMessage checkContainer="true"/>
PagingRequestType1 ::= SEQUENCE {
   channelsNeededForMobiles1And2 [0] Channel-Needed,
   pageMode [1] Page-Mode,
   mobileIdentity1 [2] EXPLICIT MobileIdentity,
   --<iei format="tlv">17</iei>
   mobileIdentity2 [3] EXPLICIT MobileIdentity OPTIONAL
}

-- 9.1.23 Paging Request Type 2 
--<is3GMessage checkContainer="true"/>
PagingRequestType2 ::= SEQUENCE {
   channelsNeededForMobiles1And2 [0] Channel-Needed,
   pageMode [1] Page-Mode,
   mobileIdentity1 [2] EXPLICIT MobileIdentity,
   mobileIdentity2 [3] EXPLICIT MobileIdentity,
   --<iei format="tlv">17</iei>
   mobileIdentity3 [4] EXPLICIT MobileIdentity OPTIONAL
}

-- 9.1.24 Paging Request Type 3 
--<is3GMessage checkContainer="true"/>
PagingRequestType3 ::= SEQUENCE {
   channelsNeededForMobiles1And2 [0] Channel-Needed,
   pageMode [1] Page-Mode,
   mobileIdentity1 [2] EXPLICIT MobileIdentity,
   mobileIdentity2 [3] EXPLICIT MobileIdentity,
   mobileIdentity3 [4] EXPLICIT MobileIdentity,
   mobileIdentity4 [5] EXPLICIT MobileIdentity
}

-- 9.1.31 System Information Type 1 
--<is3GMessage imperativeOnly="true"/>
SystemInformationType1 ::= SEQUENCE {
   cellChannelDescription [0] EXPLICIT Cell-Channel-Description,
   rachControlParameter [1] RACH-Control-Parameters
}

-- 9.1.32 System Information Type 2 
--<is3GMessage imperativeOnly="true"/>
SystemInformationType2 ::= SEQUENCE {
   bcchFrequencyList [0] EXPLICIT Neighbour-Cell-Description,
   nccPermitted [1] NCC-Permitted,
   rachControlParameter [2] RACH-Control-Parameters
}

-- 9.1.33 System Information Type 2bis 
--<is3GMessage imperativeOnly="true"/>
SystemInformationType2bis ::= SEQUENCE {
   extendedBCCHFrequencyList [0] EXPLICIT Neighbour-Cell-Description,
   rachControlParameter [1] RACH-Control-Parameters
}

-- 9.1.34 System Information Type 2ter 
--<is3GMessage imperativeOnly="true"/>
SystemInformationType2ter ::= SEQUENCE {
   extendedBCCHFrequencyList [0] EXPLICIT Neighbour-Cell-Description-2
}

-- 9.1.35 System Information Type 3 
--<is3GMessage imperativeOnly="true"/>
SystemInformationType3 ::= SEQUENCE {
   cellIdentity [0] CellIdentityValue,
   locationAreaIdentification [1] LocAreaIdent,
   controlChannelDescription [2] Control-Channel-Description,
   cellOptions [3] Cell-Options-BCCH,
   cellSelectionParameters [4] Cell-Selection-Parameters,
   rachControlParameters [5] RACH-Control-Parameters
}

-- 9.1.36 System Information Type 4 
--<is3GMessage checkContainer="true"/>
SystemInformationType4 ::= SEQUENCE {
   locationAreaIdentification [0] LocAreaIdent,
   cellSelectionParameters [1] Cell-Selection-Parameters,
   rachControlParameters [2] RACH-Control-Parameters,
   --<iei format="tv" length="4">64</iei>
   cbchChannelDescription [3] Channel-Description OPTIONAL,
   --<iei format="tlv">72</iei>
   cbchMobileAllocation [4] Mobile-Allocation OPTIONAL
}

-- 9.1.37 System Information Type 5 
--<is3GMessage checkContainer="true"/>
SystemInformationType5 ::= SEQUENCE {
   bcchFrequencyList [0] EXPLICIT Neighbour-Cell-Description
}

-- 9.1.38 System Information Type 5bis 
--<is3GMessage checkContainer="true"/>
SystemInformationType5bis ::= SEQUENCE {
   extensionBCCHFrequencyListDescription [0] EXPLICIT 
      Neighbour-Cell-Description
}

-- 9.1.39 System Information Type 5ter 
--<is3GMessage checkContainer="true"/>
SystemInformationType5ter ::= SEQUENCE {
   extendedBCCHFrequencyList [0] EXPLICIT Neighbour-Cell-Description-2
}

-- 9.1.40 System Information Type 6 
--<is3GMessage checkContainer="true"/>
SystemInformationType6 ::= SEQUENCE {
   cellIdentity [0] CellIdentityValue,
   locationAreaIdentification [1] LocAreaIdent,
   cellOptions [2] Cell-Options-SACCH,
   nccPermitted [3] NCC-Permitted
}

-- 9.1.43 System Information Type 9 
--<is3GMessage imperativeOnly="true"/>
SystemInformationType9 ::= SEQUENCE {
   rachControlParameter [0] RACH-Control-Parameters
}

-- 9.1.51 Extended Measurement Order 
--<is3GMessage checkContainer="true"/>
ExtendedMeasurementOrder ::= SEQUENCE {
   extendedMeasurementFrequencyList [0] EXPLICIT 
      Extended-Measurement-Frequency-List
}

--<isL2PseudoLenPdu/>
L2-PSEUDO-LEN-PDU ::= SEQUENCE {
   l2PseudoLen [0] L2-Pseudo-Length,
   l3HdrOpts [1] EXPLICIT L3HdrOptions, -- L3 header, octet 1, bits 5 thru 8
   protoDiscr [2] L2-PSEUDO-LEN-CLASS.&protoDiscr ({L2-PSEUDO-LEN-PDU-Messages}
      ),
   msgType [3] L2-PSEUDO-LEN-CLASS.&msgType ({L2-PSEUDO-LEN-PDU-Messages}) (0..255)
      ,
   data [4] EXPLICIT L2-PSEUDO-LEN-CLASS.&Value ({L2-PSEUDO-LEN-PDU-Messages}{@
      protoDiscr,@msgType}),
   restOctets [5] EXPLICIT L2-PSEUDO-LEN-CLASS.&RestOctets ({
      L2-PSEUDO-LEN-PDU-Messages}{@protoDiscr,@msgType})
}

-- 9.1.30a Synchronization Channel Information 
SynchChannelInfo ::= SEQUENCE {
   bsic [0] INTEGER (0..63), -- 6 bits
   t1 [1] INTEGER (0..2047), -- 11 bits
   t2 [2] INTEGER (0..31), -- 5 bits
   t3 [3] INTEGER (0..7) -- 3 bits
}

-- 9.1.30b COMPACT Synchronization Channel Information 
CompactSynchChannelInfo ::= SEQUENCE {
   bsic [0] INTEGER (0..63), -- 6 bits
   r1 [1] INTEGER (0..1023), -- 10 bits
   r2 [2] INTEGER (0..63), -- 6 bits
   tg [3] INTEGER (0..3), -- 2 bits
   spare [4] INTEGER (0..1) DEFAULT 0 -- 1 bit
}

-- Value assignments

mt-AdditionalAssignment INTEGER ::= 59

mt-ImmediateAssignment INTEGER ::= 63

mt-ImmediateAssignmentExtended INTEGER ::= 57

mt-ImmediateAssignmentReject INTEGER ::= 58

mt-ImmediatePacketAssignment INTEGER ::= 105

mt-CipheringModeCommand INTEGER ::= 53

mt-CipheringModeComplete INTEGER ::= 50

mt-ConfigurationChangeCommand INTEGER ::= 48

mt-ConfigurationChangeAck INTEGER ::= 49

mt-ConfigurationChangeReject INTEGER ::= 51

mt-AssignmentCommand INTEGER ::= 46

mt-AssignmentComplete INTEGER ::= 41

mt-AssignmentFailure INTEGER ::= 47

mt-HandoverCommand INTEGER ::= 43

mt-HandoverComplete INTEGER ::= 44

mt-HandoverFailure INTEGER ::= 40

mt-PhysicalInformation INTEGER ::= 45

mt-ChannelRelease INTEGER ::= 13

mt-PartialRelease INTEGER ::= 10

mt-PartialReleaseComplete INTEGER ::= 15

mt-PagingRequestType1 INTEGER ::= 33

mt-PagingRequestType2 INTEGER ::= 34

mt-PagingRequestType3 INTEGER ::= 36

mt-PagingResponse INTEGER ::= 39

mt-NotificationNch INTEGER ::= 32

mt-NotificationResponse INTEGER ::= 38

mt-SystemInformationType8 INTEGER ::= 24

mt-SystemInformationType1 INTEGER ::= 25

mt-SystemInformationType2 INTEGER ::= 26

mt-SystemInformationType3 INTEGER ::= 27

mt-SystemInformationType4 INTEGER ::= 28

mt-SystemInformationType5 INTEGER ::= 29

mt-SystemInformationType6 INTEGER ::= 30

mt-SystemInformationType7 INTEGER ::= 31

mt-SystemInformationType2bis INTEGER ::= 2

mt-SystemInformationType2ter INTEGER ::= 3

mt-SystemInformationType2quater INTEGER ::= 7

mt-SystemInformationType5bis INTEGER ::= 5

mt-SystemInformationType5ter INTEGER ::= 6

mt-SystemInformationType9 INTEGER ::= 4

mt-SystemInformationType13 INTEGER ::= 0

mt-SystemInformationType16 INTEGER ::= 61

mt-SystemInformationType17 INTEGER ::= 62

mt-ChannelModeModify INTEGER ::= 16

mt-RrStatus INTEGER ::= 18

mt-ChannelModeModifyAck INTEGER ::= 23

mt-FrequencyRedefinition INTEGER ::= 20

mt-MeasurementReport INTEGER ::= 21

mt-ClassmarkChange INTEGER ::= 22

mt-ClassmarkEnquiry INTEGER ::= 19

mt-ExtendedMeasurementReport INTEGER ::= 54

mt-ExtendedMeasurementOrder INTEGER ::= 55

mt-GprsSuspensionRequest INTEGER ::= 52

mt-MbmsAnnouncement INTEGER ::= 22

mt-ServiceInformation INTEGER ::= 54

mt-VgcsUplinkGrant INTEGER ::= 9

mt-UplinkRelease INTEGER ::= 14

mt-UplinkBusy INTEGER ::= 42

mt-TalkerIndication INTEGER ::= 17

mt-PriorityUplinkRequest INTEGER ::= 102

mt-DataIndication INTEGER ::= 103

mt-DataIndication2 INTEGER ::= 104

mt-ApplicationInformation INTEGER ::= 56

mt-SystemInformationType14 INTEGER ::= 1

mt-SystemInformationType15 INTEGER ::= 67

mt-SystemInformationType18 INTEGER ::= 64

mt-SystemInformationType19 INTEGER ::= 65

mt-SystemInformationType20 INTEGER ::= 66

mt-SystemInformationType13alt INTEGER ::= 68

mt-SystemInformationType2n INTEGER ::= 69

mt-SystemInformationType21 INTEGER ::= 70

mt-SystemInformationType22 INTEGER ::= 71

mt-SystemInformationType23 INTEGER ::= 79

mt-DtmAssignmentFailure INTEGER ::= 72

mt-DtmReject INTEGER ::= 73

mt-DtmRequest INTEGER ::= 74

mt-PacketAssignment INTEGER ::= 75

mt-DtmAssignmentCommand INTEGER ::= 76

mt-DtmInformation INTEGER ::= 77

mt-PacketNotification INTEGER ::= 78

mt-UtranClassmarkChange INTEGER ::= 96

mt-Cdma2000ClassmarkChange INTEGER ::= 98

mt-InterSystemToUtranHandoverCommand INTEGER ::= 99

mt-InterSystemToCdma2000HandoverCommand INTEGER ::= 100

mt-GeranIuModeClassmarkChange INTEGER ::= 101

mt-InterSystemToEutranHandoverCommand INTEGER ::= 102

mt-GprsInformation INTEGER ::= 0

mt-notification-facch INTEGER ::= 1

mt-vbs-vgcs-reconfigure INTEGER ::= 6

mt-vbs-vgcs-reconfigure2 INTEGER ::= 7

mt-uplink-free INTEGER ::= 2

mt-vgcs-additional-info INTEGER ::= 8

mt-vgcs-sms-information INTEGER ::= 9

mt-system-information-type-10 INTEGER ::= 0

mt-system-information-type-10bis INTEGER ::= 10

mt-system-information-type-10ter INTEGER ::= 11

mt-measurement-information INTEGER ::= 5

mt-enhanced-measurement-report INTEGER ::= 4

mt-vgcs-neighbour-cell-information INTEGER ::= 12

mt-notify-application-data INTEGER ::= 13


-- Class definitions

RR-SHORT-CLASS ::= CLASS {
   &msgType INTEGER (0..31),
   &Value
}

L2-PSEUDO-LEN-CLASS ::= CLASS {
   &protoDiscr ProtoDiscr,
   &msgType INTEGER (0..255),
   &Value,
   &RestOctets
}


-- Information Object definitions

obj-AdditionalAssignment NAS-PROTOCOL-CLASS ::= {
   &protoDiscr rrMgmt, 
   &msgType mt-AdditionalAssignment, 
   &Value AdditionalAssignment
}


obj-CipheringModeCommand NAS-PROTOCOL-CLASS ::= {
   &protoDiscr rrMgmt, 
   &msgType mt-CipheringModeCommand, 
   &Value CipheringModeCommand
}


obj-CipheringModeComplete NAS-PROTOCOL-CLASS ::= {
   &protoDiscr rrMgmt, 
   &msgType mt-CipheringModeComplete, 
   &Value CipheringModeComplete
}


obj-ConfigurationChangeCommand NAS-PROTOCOL-CLASS ::= {
   &protoDiscr rrMgmt, 
   &msgType mt-ConfigurationChangeCommand, 
   &Value ConfigurationChangeCommand
}


obj-ConfigurationChangeAck NAS-PROTOCOL-CLASS ::= {
   &protoDiscr rrMgmt, 
   &msgType mt-ConfigurationChangeAck, 
   &Value ConfigurationChangeAck
}


obj-ConfigurationChangeReject NAS-PROTOCOL-CLASS ::= {
   &protoDiscr rrMgmt, 
   &msgType mt-ConfigurationChangeReject, 
   &Value ConfigurationChangeReject
}


obj-AssignmentCommand NAS-PROTOCOL-CLASS ::= {
   &protoDiscr rrMgmt, 
   &msgType mt-AssignmentCommand, 
   &Value AssignmentCommand
}


obj-AssignmentComplete NAS-PROTOCOL-CLASS ::= {
   &protoDiscr rrMgmt, 
   &msgType mt-AssignmentComplete, 
   &Value AssignmentComplete
}


obj-AssignmentFailure NAS-PROTOCOL-CLASS ::= {
   &protoDiscr rrMgmt, 
   &msgType mt-AssignmentFailure, 
   &Value AssignmentFailure
}


obj-HandoverCommand NAS-PROTOCOL-CLASS ::= {
   &protoDiscr rrMgmt, 
   &msgType mt-HandoverCommand, 
   &Value HandoverCommand
}


obj-HandoverComplete NAS-PROTOCOL-CLASS ::= {
   &protoDiscr rrMgmt, 
   &msgType mt-HandoverComplete, 
   &Value HandoverComplete
}


obj-HandoverFailure NAS-PROTOCOL-CLASS ::= {
   &protoDiscr rrMgmt, 
   &msgType mt-HandoverFailure, 
   &Value HandoverFailure
}


obj-ImmediateAssignment L2-PSEUDO-LEN-CLASS ::= {
   &protoDiscr rrMgmt, 
   &msgType mt-ImmediateAssignment, 
   &Value ImmediateAssignment, 
   &RestOctets IA-Rest-Octets
}


obj-ImmediateAssignmentExtended L2-PSEUDO-LEN-CLASS ::= {
   &protoDiscr rrMgmt, 
   &msgType mt-ImmediateAssignmentExtended, 
   &Value ImmediateAssignmentExtended, 
   &RestOctets IAX-Rest-Octets
}


obj-ImmediateAssignmentReject L2-PSEUDO-LEN-CLASS ::= {
   &protoDiscr rrMgmt, 
   &msgType mt-ImmediateAssignmentReject, 
   &Value ImmediateAssignmentReject, 
   &RestOctets IAR-Rest-Octets
}


obj-ImmediatePacketAssignment L2-PSEUDO-LEN-CLASS ::= {
   &protoDiscr rrMgmt, 
   &msgType mt-ImmediatePacketAssignment, 
   &Value ImmediatePacketAssignment, 
   &RestOctets IPA-Rest-Octets
}


obj-PhysicalInformation NAS-PROTOCOL-CLASS ::= {
   &protoDiscr rrMgmt, 
   &msgType mt-PhysicalInformation, 
   &Value PhysicalInformation
}


obj-ChannelRelease NAS-PROTOCOL-CLASS ::= {
   &protoDiscr rrMgmt, 
   &msgType mt-ChannelRelease, 
   &Value ChannelRelease
}


obj-PartialRelease NAS-PROTOCOL-CLASS ::= {
   &protoDiscr rrMgmt, 
   &msgType mt-PartialRelease, 
   &Value PartialRelease
}


obj-PartialReleaseComplete NAS-PROTOCOL-CLASS ::= {
   &protoDiscr rrMgmt, 
   &msgType mt-PartialReleaseComplete, 
   &Value PartialReleaseComplete
}


obj-PagingRequestType1 L2-PSEUDO-LEN-CLASS ::= {
   &protoDiscr rrMgmt, 
   &msgType mt-PagingRequestType1, 
   &Value PagingRequestType1, 
   &RestOctets P1-Rest-Octets
}


obj-PagingRequestType2 L2-PSEUDO-LEN-CLASS ::= {
   &protoDiscr rrMgmt, 
   &msgType mt-PagingRequestType2, 
   &Value PagingRequestType2, 
   &RestOctets P2-Rest-Octets
}


obj-PagingRequestType3 L2-PSEUDO-LEN-CLASS ::= {
   &protoDiscr rrMgmt, 
   &msgType mt-PagingRequestType3, 
   &Value PagingRequestType3, 
   &RestOctets P3-Rest-Octets
}


obj-PagingResponse NAS-PROTOCOL-CLASS ::= {
   &protoDiscr rrMgmt, 
   &msgType mt-PagingResponse, 
   &Value PagingResponse
}


obj-NotificationNch L2-PSEUDO-LEN-CLASS ::= {
   &protoDiscr rrMgmt, 
   &msgType mt-NotificationNch, 
   &Value NotificationNch, 
   &RestOctets NT-N-Rest-Octets
}


obj-NotificationResponse NAS-PROTOCOL-CLASS ::= {
   &protoDiscr rrMgmt, 
   &msgType mt-NotificationResponse, 
   &Value NotificationResponse
}


obj-SystemInformationType1 L2-PSEUDO-LEN-CLASS ::= {
   &protoDiscr rrMgmt, 
   &msgType mt-SystemInformationType1, 
   &Value SystemInformationType1, 
   &RestOctets SI1-Rest-Octets
}


obj-SystemInformationType2 L2-PSEUDO-LEN-CLASS ::= {
   &protoDiscr rrMgmt, 
   &msgType mt-SystemInformationType2, 
   &Value SystemInformationType2, 
   &RestOctets NULL
}


obj-SystemInformationType2bis L2-PSEUDO-LEN-CLASS ::= {
   &protoDiscr rrMgmt, 
   &msgType mt-SystemInformationType2bis, 
   &Value SystemInformationType2bis, 
   &RestOctets SI2bis-Rest-Octets
}


obj-SystemInformationType2ter L2-PSEUDO-LEN-CLASS ::= {
   &protoDiscr rrMgmt, 
   &msgType mt-SystemInformationType2ter, 
   &Value SystemInformationType2ter, 
   &RestOctets SI2ter-Rest-Octets
}


obj-SystemInformationType2quater L2-PSEUDO-LEN-CLASS ::= {
   &protoDiscr rrMgmt, 
   &msgType mt-SystemInformationType2quater, 
   &Value SystemInformationType2quater, 
   &RestOctets SI2quater-Rest-Octets
}


obj-SystemInformationType2n L2-PSEUDO-LEN-CLASS ::= {
   &protoDiscr rrMgmt, 
   &msgType mt-SystemInformationType2n, 
   &Value SystemInformationType2n, 
   &RestOctets SI2n-Rest-Octets
}


obj-SystemInformationType3 L2-PSEUDO-LEN-CLASS ::= {
   &protoDiscr rrMgmt, 
   &msgType mt-SystemInformationType3, 
   &Value SystemInformationType3, 
   &RestOctets SI3-Rest-Octets-Data
}


obj-SystemInformationType4 L2-PSEUDO-LEN-CLASS ::= {
   &protoDiscr rrMgmt, 
   &msgType mt-SystemInformationType4, 
   &Value SystemInformationType4, 
   &RestOctets SI4-Rest-Octets
}


obj-SystemInformationType5 L2-PSEUDO-LEN-CLASS ::= {
   &protoDiscr rrMgmt, 
   &msgType mt-SystemInformationType5, 
   &Value SystemInformationType5, 
   &RestOctets NULL
}


obj-SystemInformationType5bis L2-PSEUDO-LEN-CLASS ::= {
   &protoDiscr rrMgmt, 
   &msgType mt-SystemInformationType5bis, 
   &Value SystemInformationType5bis, 
   &RestOctets NULL
}


obj-SystemInformationType5ter L2-PSEUDO-LEN-CLASS ::= {
   &protoDiscr rrMgmt, 
   &msgType mt-SystemInformationType5ter, 
   &Value SystemInformationType5ter, 
   &RestOctets NULL
}


obj-SystemInformationType6 L2-PSEUDO-LEN-CLASS ::= {
   &protoDiscr rrMgmt, 
   &msgType mt-SystemInformationType6, 
   &Value SystemInformationType6, 
   &RestOctets SI6-Rest-Octets
}


obj-SystemInformationType7 L2-PSEUDO-LEN-CLASS ::= {
   &protoDiscr rrMgmt, 
   &msgType mt-SystemInformationType7, 
   &Value SystemInformationType7, 
   &RestOctets SI7-Rest-Octets-Data
}


obj-SystemInformationType8 L2-PSEUDO-LEN-CLASS ::= {
   &protoDiscr rrMgmt, 
   &msgType mt-SystemInformationType8, 
   &Value SystemInformationType8, 
   &RestOctets SI8-Rest-Octets-Data
}


obj-SystemInformationType9 L2-PSEUDO-LEN-CLASS ::= {
   &protoDiscr rrMgmt, 
   &msgType mt-SystemInformationType9, 
   &Value SystemInformationType9, 
   &RestOctets SI9-Rest-Octets
}


obj-SystemInformationType13 L2-PSEUDO-LEN-CLASS ::= {
   &protoDiscr rrMgmt, 
   &msgType mt-SystemInformationType13, 
   &Value SystemInformationType13, 
   &RestOctets SI13-Rest-Octets
}


obj-SystemInformationType16 L2-PSEUDO-LEN-CLASS ::= {
   &protoDiscr rrMgmt, 
   &msgType mt-SystemInformationType16, 
   &Value SystemInformationType16, 
   &RestOctets SI16-Rest-Octets
}


obj-SystemInformationType17 L2-PSEUDO-LEN-CLASS ::= {
   &protoDiscr rrMgmt, 
   &msgType mt-SystemInformationType17, 
   &Value SystemInformationType17, 
   &RestOctets SI17-Rest-Octets
}


obj-SystemInformationType19 L2-PSEUDO-LEN-CLASS ::= {
   &protoDiscr rrMgmt, 
   &msgType mt-SystemInformationType19, 
   &Value SystemInformationType19, 
   &RestOctets SI19-Rest-Octets
}


obj-SystemInformationType18 L2-PSEUDO-LEN-CLASS ::= {
   &protoDiscr rrMgmt, 
   &msgType mt-SystemInformationType18, 
   &Value SystemInformationType18, 
   &RestOctets SI18-Rest-Octets
}


obj-SystemInformationType20 L2-PSEUDO-LEN-CLASS ::= {
   &protoDiscr rrMgmt, 
   &msgType mt-SystemInformationType20, 
   &Value SystemInformationType20, 
   &RestOctets SI18-Rest-Octets
}


obj-SystemInformationType14 L2-PSEUDO-LEN-CLASS ::= {
   &protoDiscr rrMgmt, 
   &msgType mt-SystemInformationType14, 
   &Value SystemInformationType14, 
   &RestOctets SI14-Rest-Octets
}


obj-SystemInformationType15 L2-PSEUDO-LEN-CLASS ::= {
   &protoDiscr rrMgmt, 
   &msgType mt-SystemInformationType15, 
   &Value SystemInformationType15, 
   &RestOctets SI15-Rest-Octets
}


obj-SystemInformationType13alt L2-PSEUDO-LEN-CLASS ::= {
   &protoDiscr rrMgmt, 
   &msgType mt-SystemInformationType13alt, 
   &Value SystemInformationType13alt, 
   &RestOctets SI13alt-Rest-Octets
}


obj-SystemInformationType21 L2-PSEUDO-LEN-CLASS ::= {
   &protoDiscr rrMgmt, 
   &msgType mt-SystemInformationType21, 
   &Value SystemInformationType21, 
   &RestOctets SI21-Rest-Octets
}


obj-SystemInformationType22 L2-PSEUDO-LEN-CLASS ::= {
   &protoDiscr rrMgmt, 
   &msgType mt-SystemInformationType22, 
   &Value SystemInformationType22, 
   &RestOctets SI22-Rest-Octets
}


obj-SystemInformationType23 L2-PSEUDO-LEN-CLASS ::= {
   &protoDiscr rrMgmt, 
   &msgType mt-SystemInformationType23, 
   &Value SystemInformationType23, 
   &RestOctets SI23-Rest-Octets
}


obj-ChannelModeModify NAS-PROTOCOL-CLASS ::= {
   &protoDiscr rrMgmt, 
   &msgType mt-ChannelModeModify, 
   &Value ChannelModeModify
}


obj-RrStatus NAS-PROTOCOL-CLASS ::= {
   &protoDiscr rrMgmt, 
   &msgType mt-RrStatus, 
   &Value RrStatus
}


obj-ChannelModeModifyAck NAS-PROTOCOL-CLASS ::= {
   &protoDiscr rrMgmt, 
   &msgType mt-ChannelModeModifyAck, 
   &Value ChannelModeModifyAck
}


obj-FrequencyRedefinition NAS-PROTOCOL-CLASS ::= {
   &protoDiscr rrMgmt, 
   &msgType mt-FrequencyRedefinition, 
   &Value FrequencyRedefinition
}


obj-MeasurementReport NAS-PROTOCOL-CLASS ::= {
   &protoDiscr rrMgmt, 
   &msgType mt-MeasurementReport, 
   &Value MeasurementReport
}


obj-ClassmarkChange NAS-PROTOCOL-CLASS ::= {
   &protoDiscr rrMgmt, 
   &msgType mt-ClassmarkChange, 
   &Value ClassmarkChange
}


obj-ClassmarkEnquiry NAS-PROTOCOL-CLASS ::= {
   &protoDiscr rrMgmt, 
   &msgType mt-ClassmarkEnquiry, 
   &Value ClassmarkEnquiry
}


obj-ExtendedMeasurementReport NAS-PROTOCOL-CLASS ::= {
   &protoDiscr rrMgmt, 
   &msgType mt-ExtendedMeasurementReport, 
   &Value ExtendedMeasurementReport
}


obj-ExtendedMeasurementOrder L2-PSEUDO-LEN-CLASS ::= {
   &protoDiscr rrMgmt, 
   &msgType mt-ExtendedMeasurementOrder, 
   &Value ExtendedMeasurementOrder, 
   &RestOctets NULL
}


obj-GprsSuspensionRequest NAS-PROTOCOL-CLASS ::= {
   &protoDiscr rrMgmt, 
   &msgType mt-GprsSuspensionRequest, 
   &Value GprsSuspensionRequest
}


obj-MbmsAnnouncement NAS-PROTOCOL-CLASS ::= {
   &protoDiscr rrMgmt, 
   &msgType mt-MbmsAnnouncement, 
   &Value MbmsAnnouncement
}


obj-ServiceInformation NAS-PROTOCOL-CLASS ::= {
   &protoDiscr rrMgmt, 
   &msgType mt-ServiceInformation, 
   &Value ServiceInformation
}


obj-VgcsUplinkGrant NAS-PROTOCOL-CLASS ::= {
   &protoDiscr rrMgmt, 
   &msgType mt-VgcsUplinkGrant, 
   &Value VgcsUplinkGrant
}


obj-UplinkRelease NAS-PROTOCOL-CLASS ::= {
   &protoDiscr rrMgmt, 
   &msgType mt-UplinkRelease, 
   &Value UplinkRelease
}


obj-UplinkBusy NAS-PROTOCOL-CLASS ::= {
   &protoDiscr rrMgmt, 
   &msgType mt-UplinkBusy, 
   &Value UplinkBusy
}


obj-TalkerIndication NAS-PROTOCOL-CLASS ::= {
   &protoDiscr rrMgmt, 
   &msgType mt-TalkerIndication, 
   &Value TalkerIndication
}


obj-PriorityUplinkRequest NAS-PROTOCOL-CLASS ::= {
   &protoDiscr rrMgmt, 
   &msgType mt-PriorityUplinkRequest, 
   &Value PriorityUplinkRequest
}


obj-DataIndication NAS-PROTOCOL-CLASS ::= {
   &protoDiscr rrMgmt, 
   &msgType mt-DataIndication, 
   &Value DataIndication
}


obj-DataIndication2 NAS-PROTOCOL-CLASS ::= {
   &protoDiscr rrMgmt, 
   &msgType mt-DataIndication2, 
   &Value DataIndication2
}


obj-ApplicationInformation NAS-PROTOCOL-CLASS ::= {
   &protoDiscr rrMgmt, 
   &msgType mt-ApplicationInformation, 
   &Value ApplicationInformation
}


obj-DtmAssignmentFailure NAS-PROTOCOL-CLASS ::= {
   &protoDiscr rrMgmt, 
   &msgType mt-DtmAssignmentFailure, 
   &Value DtmAssignmentFailure
}


obj-DtmReject NAS-PROTOCOL-CLASS ::= {
   &protoDiscr rrMgmt, 
   &msgType mt-DtmReject, 
   &Value DtmReject
}


obj-DtmRequest NAS-PROTOCOL-CLASS ::= {
   &protoDiscr rrMgmt, 
   &msgType mt-DtmRequest, 
   &Value DtmRequest
}


obj-PacketAssignment NAS-PROTOCOL-CLASS ::= {
   &protoDiscr rrMgmt, 
   &msgType mt-PacketAssignment, 
   &Value PacketAssignment
}


obj-DtmAssignmentCommand NAS-PROTOCOL-CLASS ::= {
   &protoDiscr rrMgmt, 
   &msgType mt-DtmAssignmentCommand, 
   &Value DtmAssignmentCommand
}


obj-DtmInformation NAS-PROTOCOL-CLASS ::= {
   &protoDiscr rrMgmt, 
   &msgType mt-DtmInformation, 
   &Value DtmInformation
}


obj-PacketNotification NAS-PROTOCOL-CLASS ::= {
   &protoDiscr rrMgmt, 
   &msgType mt-PacketNotification, 
   &Value PacketNotification
}


obj-UtranClassmarkChange NAS-PROTOCOL-CLASS ::= {
   &protoDiscr rrMgmt, 
   &msgType mt-UtranClassmarkChange, 
   &Value UtranClassmarkChange
}


obj-Cdma2000ClassmarkChange NAS-PROTOCOL-CLASS ::= {
   &protoDiscr rrMgmt, 
   &msgType mt-Cdma2000ClassmarkChange, 
   &Value Cdma2000ClassmarkChange
}


obj-InterSystemToUtranHandoverCommand NAS-PROTOCOL-CLASS ::= {
   &protoDiscr rrMgmt, 
   &msgType mt-InterSystemToUtranHandoverCommand, 
   &Value InterSystemToUtranHandoverCommand
}


obj-InterSystemToCdma2000HandoverCommand NAS-PROTOCOL-CLASS ::= {
   &protoDiscr rrMgmt, 
   &msgType mt-InterSystemToCdma2000HandoverCommand, 
   &Value InterSystemToCdma2000HandoverCommand
}


obj-GeranIuModeClassmarkChange NAS-PROTOCOL-CLASS ::= {
   &protoDiscr rrMgmt, 
   &msgType mt-GeranIuModeClassmarkChange, 
   &Value GeranIuModeClassmarkChange
}


obj-InterSystemToEutranHandoverCommand NAS-PROTOCOL-CLASS ::= {
   &protoDiscr rrMgmt, 
   &msgType mt-InterSystemToEutranHandoverCommand, 
   &Value InterSystemToEutranHandoverCommand
}


obj-GprsInformation NAS-PROTOCOL-CLASS ::= {
   &protoDiscr gttp, 
   &msgType mt-GprsInformation, 
   &Value GprsInformation
}


obj-notification-facch RR-SHORT-CLASS ::= {
   &msgType mt-notification-facch, 
   &Value NOTIFICATION-FACCH
}


obj-vbs-vgcs-reconfigure RR-SHORT-CLASS ::= {
   &msgType mt-vbs-vgcs-reconfigure, 
   &Value VBS-VGCS-RECONFIGURE
}


obj-vbs-vgcs-reconfigure2 RR-SHORT-CLASS ::= {
   &msgType mt-vbs-vgcs-reconfigure2, 
   &Value VBS-VGCS-RECONFIGURE2
}


obj-uplink-free RR-SHORT-CLASS ::= {
   &msgType mt-uplink-free, 
   &Value UPLINK-FREE
}


obj-vgcs-additional-info RR-SHORT-CLASS ::= {
   &msgType mt-vgcs-additional-info, 
   &Value VGCS-ADDITIONAL-INFO
}


obj-vgcs-sms-information RR-SHORT-CLASS ::= {
   &msgType mt-vgcs-sms-information, 
   &Value VGCS-SMS-INFORMATION
}


obj-system-information-type-10 RR-SHORT-CLASS ::= {
   &msgType mt-system-information-type-10, 
   &Value SYSTEM-INFORMATION-TYPE-10
}


obj-system-information-type-10bis RR-SHORT-CLASS ::= {
   &msgType mt-system-information-type-10bis, 
   &Value SYSTEM-INFORMATION-TYPE-10bis
}


obj-system-information-type-10ter RR-SHORT-CLASS ::= {
   &msgType mt-system-information-type-10ter, 
   &Value SYSTEM-INFORMATION-TYPE-10ter
}


obj-measurement-information RR-SHORT-CLASS ::= {
   &msgType mt-measurement-information, 
   &Value Measurement-information
}


obj-enhanced-measurement-report RR-SHORT-CLASS ::= {
   &msgType mt-enhanced-measurement-report, 
   &Value Enhanced-Measurement-report
}


obj-vgcs-neighbour-cell-information RR-SHORT-CLASS ::= {
   &msgType mt-vgcs-neighbour-cell-information, 
   &Value VGCS-Neighbour-Cell-Information
}


obj-notify-application-data RR-SHORT-CLASS ::= {
   &msgType mt-notify-application-data, 
   &Value NOTIFY-APPLICATION-DATA
}


-- Information Object Set definitions

RR-Short-PD-Messages RR-SHORT-CLASS ::= {obj-notification-facch | 
   obj-vbs-vgcs-reconfigure | obj-vbs-vgcs-reconfigure2 | obj-uplink-free | 
   obj-vgcs-additional-info | obj-vgcs-sms-information | 
   obj-system-information-type-10 | obj-system-information-type-10bis | 
   obj-system-information-type-10ter | obj-measurement-information | 
   obj-enhanced-measurement-report | obj-vgcs-neighbour-cell-information | 
   obj-notify-application-data}

DL-DCCH-Messages NAS-PROTOCOL-CLASS ::= {obj-AdditionalAssignment | 
   obj-ApplicationInformation | obj-AssignmentCommand | obj-AssignmentComplete
    | obj-ChannelModeModify | obj-ChannelRelease | obj-CipheringModeCommand | 
   obj-ClassmarkEnquiry | obj-ConfigurationChangeCommand | obj-DataIndication
    | obj-DtmAssignmentCommand | obj-DtmInformation | obj-DtmReject | 
   obj-FrequencyRedefinition | obj-GprsInformation | obj-HandoverCommand | 
   obj-InterSystemToUtranHandoverCommand | 
   obj-InterSystemToCdma2000HandoverCommand | 
   obj-InterSystemToEutranHandoverCommand | obj-MbmsAnnouncement | 
   obj-PacketAssignment | obj-PacketNotification | obj-PartialRelease | 
   obj-PhysicalInformation | obj-RrStatus | obj-UplinkBusy | obj-UplinkRelease
    | obj-VgcsUplinkGrant}

UL-DCCH-Messages NAS-PROTOCOL-CLASS ::= {obj-ApplicationInformation | 
   obj-AssignmentComplete | obj-AssignmentFailure | obj-Cdma2000ClassmarkChange
    | obj-ChannelModeModifyAck | obj-CipheringModeComplete | 
   obj-ClassmarkChange | obj-ConfigurationChangeAck | 
   obj-ConfigurationChangeReject | obj-DataIndication | obj-DataIndication2 | 
   obj-DtmAssignmentFailure | obj-DtmRequest | obj-GeranIuModeClassmarkChange
    | obj-GprsInformation | obj-GprsSuspensionRequest | obj-HandoverComplete | 
   obj-HandoverFailure | obj-NotificationResponse | obj-PagingResponse | 
   obj-PartialReleaseComplete | obj-PriorityUplinkRequest | obj-RrStatus | 
   obj-ServiceInformation | obj-TalkerIndication | obj-UplinkRelease | 
   obj-UtranClassmarkChange}

UL-SACCH-Messages NAS-PROTOCOL-CLASS ::= {obj-MeasurementReport | 
   obj-ExtendedMeasurementReport}

L2-PSEUDO-LEN-PDU-Messages L2-PSEUDO-LEN-CLASS ::= {obj-ImmediateAssignment | 
   obj-ImmediateAssignmentExtended | obj-ImmediateAssignmentReject | 
   obj-ImmediatePacketAssignment | obj-NotificationNch | obj-PagingRequestType1
    | obj-PagingRequestType2 | obj-PagingRequestType3 | 
   obj-SystemInformationType1 | obj-SystemInformationType2 | 
   obj-SystemInformationType2bis | obj-SystemInformationType2ter | 
   obj-SystemInformationType2quater | obj-SystemInformationType2n | 
   obj-SystemInformationType3 | obj-SystemInformationType4 | 
   obj-SystemInformationType5 | obj-SystemInformationType5bis | 
   obj-SystemInformationType5ter | obj-SystemInformationType6 | 
   obj-SystemInformationType7 | obj-SystemInformationType8 | 
   obj-SystemInformationType9 | obj-SystemInformationType13 | 
   obj-SystemInformationType16 | obj-SystemInformationType17 | 
   obj-SystemInformationType19 | obj-SystemInformationType18 | 
   obj-SystemInformationType20 | obj-SystemInformationType14 | 
   obj-SystemInformationType15 | obj-SystemInformationType13alt | 
   obj-SystemInformationType21 | obj-SystemInformationType22 | 
   obj-SystemInformationType23 | obj-ExtendedMeasurementOrder}

END
TS44018IES DEFINITIONS AUTOMATIC TAGS ::= BEGIN

IMPORTS

Channel-Request-Description-IE, EGPRS-Modulation-and-Coding-IE, EGPRS-Level-IE
   , EGPRS-Window-Size-IE, Enhanced-Cell-Reselection-Parameters-IE, 
   Frequency-Parameters-IE, GPRS-Cell-Options-IE, GPRS-Mobile-Allocation-IE, 
   GPRS-Power-Control-Parameters-IE, MBMS-Channel-Parameters-IE, 
   MBMS-p-t-m-channel-description-IE, MBMS-Session-List-IE, 
   MBMS-Session-Parameters-List-IE, MPRACH-description-IE, 
   Packet-Timing-Advance-IE, PCID-Group-IE, PSC-Group-IE, 
   Power-Control-Parameters-IE, Pulse-Format-IE, TMGI-IE, 
   UTRAN-CSG-Measurement-Report-IE
FROM TS44060IES ;

-- Productions

La-different ::= SEQUENCE {
   cell-reselect-hysteresis [0] INTEGER (0..7) OPTIONAL
}

Further-cell-info ::= SEQUENCE {
   la-different [0] La-different,
   ms-txpwr-max-cch [1] INTEGER (0..31),
   rxlev-access-min [2] INTEGER (0..63),
   cell-reselect-offset [3] INTEGER (0..63),
   temporary-offset [4] INTEGER (0..7),
   penalty-time [5] INTEGER (0..31)
}

Cell-parameters ::= CHOICE {
   cell-barred [0] NULL,
   further-cell-info [1] Further-cell-info
}

Cell-info ::= SEQUENCE {
   bsic [0] INTEGER (0..63),
   cell-parameters [1] EXPLICIT Cell-parameters OPTIONAL
}

Further-diff-cell-info ::= SEQUENCE {
   la-different [0] La-different,
   ms-txpwr-max-cch [1] INTEGER (0..31) OPTIONAL,
   rxlev-access-min [2] INTEGER (0..63) OPTIONAL,
   cell-reselect-offset [3] INTEGER (0..63) OPTIONAL,
   temporary-offset [4] INTEGER (0..7) OPTIONAL,
   penalty-time [5] INTEGER (0..31) OPTIONAL
}

Diff-cell-pars ::= CHOICE {
   cell-barred [0] NULL,
   further-diff-cell-info [1] Further-diff-cell-info
}

Differential-cell-info ::= SEQUENCE {
   component-1 [0] EXPLICIT CHOICE {
      bcc [0] INTEGER (0..7),
      bsic [1] INTEGER (0..63)
   },
   diff-cell-pars [1] EXPLICIT Diff-cell-pars OPTIONAL
}

Info-field ::= SEQUENCE {
   next-frequency [0] INTEGER (0..255),
   differential-cell-info [1] Differential-cell-info
}

Neighbour-information ::= SEQUENCE {
   first-frequency [0] INTEGER (0..31),
   cell-info [1] Cell-info,
   info-field-list [2] SEQUENCE OF Info-field
}

SI10-Rest-Octets ::= SEQUENCE {
   ba-ind [0] INTEGER (0..1),
   neighbour-information [1] Neighbour-information OPTIONAL
}

Mobile-Allocation ::= SEQUENCE {
   length [0] INTEGER (0..255),
   mac [1] BIT STRING  (SIZE (0..2040))
}

Notification-FACCH-Group-Channel-Description ::= SEQUENCE {
   channel-Description [0] INTEGER (0..16777215),
   component-2 [1] EXPLICIT CHOICE {
      mobile-Allocation [0] Mobile-Allocation,
      frequency-Short-List [1] BIT STRING  (SIZE (64))
   } OPTIONAL
}

Frequency-Short-List-2 ::= SEQUENCE {
   component-1 [0] INTEGER (2) DEFAULT 2,
   spare-bit [1] INTEGER (0..3) DEFAULT 0,
   component-3 [2] EXPLICIT CHOICE {
      range-1024 [0] BIT STRING  (SIZE (51)),
      range-512 [1] BIT STRING  (SIZE (49)),
      range-256 [2] BIT STRING  (SIZE (49)),
      range-128 [3] BIT STRING  (SIZE (49)),
      variable-bitmap [4] BIT STRING  (SIZE (49))
   }
}

Frequency-List ::= SEQUENCE {
   length [0] INTEGER (0..255),
   component-2 [1] EXPLICIT CHOICE {
      bitmap0 [0] SEQUENCE {
         spare-bit [0] INTEGER (0..3) DEFAULT 0,
         bitmap0 [1] BIT STRING  (SIZE (124))
      },
      choice-2 [1] SEQUENCE {
         spare-bit [0] INTEGER (0..3) DEFAULT 0,
         component-2 [1] EXPLICIT CHOICE {
            range-1024 [0] BIT STRING ,
            range-512 [1] BIT STRING ,
            range-256 [2] BIT STRING ,
            range-128 [3] BIT STRING ,
            variable-bitmap [4] BIT STRING 
         }
      }
   }
}

SI10bis-Neighbour-Cell-Info ::= SEQUENCE {
   group-Channel-Description [0] Notification-FACCH-Group-Channel-Description,
   component-2 [1] EXPLICIT CHOICE {
      frequency-Short-List [0] Frequency-Short-List-2,
      frequency-List [1] Frequency-List
   } OPTIONAL,
   cell-global-count [2] INTEGER (0..3),
   b22-count [3] INTEGER (0..1),
   component-5 [4] SEQUENCE {
      priority-Uplink-access [0] INTEGER (0..1) OPTIONAL,
      component-2 [1] SEQUENCE {
         fr-AMR-Config [0] INTEGER (0..15) OPTIONAL,
         hr-AMR-Config [1] INTEGER (0..15) OPTIONAL
      } OPTIONAL,
      component-3 [2] SEQUENCE {
         sms-Data-Confidentiality-Ind [0] INTEGER (0..1),
         sms-Guaranteed-Privacy-Ind [1] INTEGER (0..1)
      } OPTIONAL,
      component-4 [3] SEQUENCE {
         max-retrans [0] INTEGER (0..3),
         tx-Integer [1] INTEGER (0..15)
      } OPTIONAL
   } OPTIONAL
}

SI10bis-Rest-Octets ::= SEQUENCE {
   si10bis-Sequence [0] INTEGER (0..3),
   component-2 [1] SEQUENCE OF SEQUENCE {
      position-in-SI5-list [0] INTEGER (0..31),
      bcch-arfcn [1] INTEGER (0..1023) OPTIONAL,
      bsic [2] INTEGER (0..63) OPTIONAL,
      si10bis-Neighbour-Cell-Info [3] SI10bis-Neighbour-Cell-Info
   }
}

E-UTRAN-Measurement-Parameters-Description-struct ::= SEQUENCE {
   qsearch-C-E-UTRAN [0] INTEGER (0..15),
   e-utran-rep-quant [1] INTEGER (0..1),
   e-utran-multirat-reporting [2] INTEGER (0..3),
   component-4 [3] EXPLICIT CHOICE {
      choice-1 [0] SEQUENCE {
         component-1 [0] SEQUENCE {
            e-utran-fdd-reporting-threshold [0] INTEGER (0..7),
            e-utran-fdd-reporting-threshold-2 [1] INTEGER (0..63) OPTIONAL,
            e-utran-fdd-reporting-offset [2] INTEGER (0..7) OPTIONAL
         } OPTIONAL,
         component-2 [1] SEQUENCE {
            e-utran-tdd-reporting-threshold [0] INTEGER (0..7),
            e-utran-tdd-reporting-threshold-2 [1] INTEGER (0..63) OPTIONAL,
            e-utran-tdd-reporting-offset [2] INTEGER (0..7) OPTIONAL
         } OPTIONAL
      },
      choice-2 [1] SEQUENCE {
         component-1 [0] SEQUENCE {
            e-utran-fdd-measurement-report-offset [0] INTEGER (0..63),
            e-utran-fdd-reporting-threshold-2 [1] INTEGER (0..63) OPTIONAL,
            e-utran-fdd-reporting-offset [2] INTEGER (0..7) OPTIONAL
         } OPTIONAL,
         component-2 [1] SEQUENCE {
            e-utran-tdd-measurement-report-offset [0] INTEGER (0..63),
            e-utran-tdd-reporting-threshold-2 [1] INTEGER (0..63) OPTIONAL,
            e-utran-tdd-reporting-offset [2] INTEGER (0..7) OPTIONAL
         } OPTIONAL,
         reporting-granularity [2] INTEGER (0..1)
      }
   }
}

A3G-Additional-Measurement-Parameters-Description-2-struct ::= SEQUENCE {
   fdd-reporting-threshold-2 [0] INTEGER (0..63) OPTIONAL
}

A3G-CSG-Description-struct ::= SEQUENCE {
   component-1 [0] SEQUENCE OF SEQUENCE {
      csg-psc-split [0] PSC-Group-IE,
      utran-frequency-index-list [1] SEQUENCE OF INTEGER (0..31)
   },
   component-2 [1] SEQUENCE OF CHOICE {
      csg-fdd-uarfcn [0] INTEGER (0..16383),
      csg-tdd-uarfcn [1] INTEGER (0..16383)
   }
}

Group-Call-information ::= SEQUENCE {
   group-Call-Reference [0] BIT STRING  (SIZE (36)),
   group-Channel-Description [1] Notification-FACCH-Group-Channel-Description
       OPTIONAL
}

SI10ter-Rest-Octets ::= SEQUENCE {
   si10bis-Sequence [0] INTEGER (0..3),
   component-2 [1] EXPLICIT CHOICE {
      position-in-SI5-list [0] INTEGER (0..31),
      bcch-arfcn [1] INTEGER (0..1023)
   },
   bsic [2] INTEGER (0..63) OPTIONAL,
   nch-Position [3] INTEGER (0..31)
}

Channel-Description ::= SEQUENCE {
   channel-type-and-TDMA-offset [0] INTEGER (0..31),
   tn [1] INTEGER (0..7),
   tsc [2] INTEGER (0..7),
   component-4 [3] EXPLICIT CHOICE {
      choice-1 [0] SEQUENCE {
         maio [0] INTEGER (0..63),
         hsn [1] INTEGER (0..63)
      },
      choice-2 [1] SEQUENCE {
         spare-bit [0] INTEGER (0..3) DEFAULT 0,
         arfcn [1] INTEGER (0..1023)
      }
   }
}

Starting-Time ::= SEQUENCE {
   t1prime [0] INTEGER (0..31),
   t3 [1] INTEGER (0..63),
   spare-bit [2] INTEGER (0..31) DEFAULT 0
}

-- 10.5.2.82 Extended TSC Set
ExtendedTSCSet ::= SEQUENCE {
   secondaryTSCValue [0] INTEGER (0..7),
   secondaryTSCSet [1] BOOLEAN,
   primaryTSCSet [2] BOOLEAN,
   secondTSCAssigned [3] BOOLEAN,
   csTSCSet [4] INTEGER (0..3)
}

APDU-Flags ::= SEQUENCE {
   spare-bit [0] INTEGER (0..1) DEFAULT 0,
   cr [1] INTEGER (0..1),
   first-seg [2] INTEGER (0..1),
   second-seg [3] INTEGER (0..1)
}

APDU-ID ::= SEQUENCE {
   protocol-id [0] INTEGER (0..15)
}

APDU-Data ::= SEQUENCE {
   length [0] INTEGER (0..255),
   apdu-information [1] OCTET STRING (SIZE (0..255))
}

Channel-Description-2 ::= Channel-Description

Power-Command ::= SEQUENCE {
   spare-bit [0] INTEGER (0..1) DEFAULT 0,
   epc-mode [1] INTEGER (0..1),
   fpc-epc [2] INTEGER (0..1),
   power-level [3] INTEGER (0..31)
}

Cell-Channel-Description ::= CHOICE {
   bitmap0 [0] SEQUENCE {
      spare-bit [0] INTEGER (0..3) DEFAULT 0,
      bitmap0 [1] BIT STRING  (SIZE (124))
   },
   choice-2 [1] SEQUENCE {
      spare-bit [0] INTEGER (0..3) DEFAULT 0,
      component-2 [1] EXPLICIT CHOICE {
         range-1024 [0] BIT STRING  (SIZE (123)),
         range-512 [1] BIT STRING  (SIZE (121)),
         range-256 [2] BIT STRING  (SIZE (121)),
         range-128 [3] BIT STRING  (SIZE (121)),
         variable-bitmap [4] BIT STRING  (SIZE (121))
      }
   }
}

-- 10.5.2.21b Multislot Allocation
Multislot-Allocation ::= SEQUENCE {
   --<is3GLength/>
   length [0] INTEGER (0..255),
   --<first3GExtElem/>
   da [1] INTEGER (0..127),
   --<last3GExtElem/>
   ua [2] INTEGER (0..127) OPTIONAL,
   --<length fixed-size="0"/>
   channel-sets [3] SEQUENCE (SIZE (0..8)) OF INTEGER (0..255)
}

Channel-Mode ::= INTEGER (0..255)

Channel-Mode-2 ::= INTEGER (0..255)

Frequency-Channel-Sequence ::= SEQUENCE {
   spare-bit [0] INTEGER (0..1) DEFAULT 0,
   lowest-arfcn [1] INTEGER (0..127),
   inc-skip [2] SEQUENCE (SIZE (16)) OF INTEGER (0..15)
}

Cipher-Mode-Setting ::= SEQUENCE {
   algorithm-id [0] INTEGER (0..7),
   sc [1] INTEGER (0..1)
}

VGCS-target-mode-Indication ::= SEQUENCE {
   length [0] INTEGER (0..255),
   target-mode [1] INTEGER (0..3),
   group-cipher-key-num [2] INTEGER (0..15),
   spare [3] INTEGER (0..3) DEFAULT 3
}

-- 10.5.2 - Radio Resource management information elements 
--10.5.2.21aa MultiRate configuration
--<cDecFuncFname>TS44018Dec_Multirate_Configuration.c</cDecFuncFname>
--<cEncFuncFname>TS44018Enc_Multirate_Configuration.c</cEncFuncFname>
Multirate-Configuration ::= SEQUENCE {
   multirate-speech-version [0] ENUMERATED { v1(1), v2(2), max(7) },
   nscb [1] INTEGER (0..1),
   icmi [2] INTEGER (0..1),
   start-mode [3] INTEGER (0..3),
   amr-codec-modes [4] INTEGER (0..255),
   --<length fixed-size="0"/>
   params [5] SEQUENCE (SIZE (0..3)) OF SEQUENCE {
      threshold [0] INTEGER (0..63),
      hysteresis [1] INTEGER (0..15)
   }
}

                                    ---
-- 10.5.2.42b VGCS Ciphering Parameters
                                    ---
--<cDecFuncFname>TS44018Dec_VGCS_Ciphering_Parameters.c</cDecFuncFname>
--<cEncFuncFname>TS44018Enc_VGCS_Ciphering_Parameters.c</cEncFuncFname>
VGCS-Ciphering-Parameters ::= SEQUENCE {
   b22-count [0] INTEGER (0..1),
   cell-global-count [1] INTEGER (0..3),
   cell-identity [2] INTEGER (0..255) OPTIONAL,
   location-area-identification [3] OCTET STRING (SIZE (5)) OPTIONAL,
   vstk_rand [4] BIT STRING  (SIZE (36)) OPTIONAL
}

BA-Range ::= SEQUENCE {
   length [0] INTEGER (0..255),
   num-ranges [1] INTEGER (0..255),
   range [2] SEQUENCE (SIZE (0..255)) OF INTEGER (0..1023)
}

Group-Channel-Description ::= SEQUENCE {
   length [0] INTEGER (0..255),
   channel-type-and-TDMA-offset [1] INTEGER (0..31),
   tn [2] INTEGER (0..7),
   tsc [3] INTEGER (0..7),
   component-5 [4] EXPLICIT CHOICE {
      choice-1 [0] SEQUENCE {
         maio [0] INTEGER (0..63),
         hsn [1] INTEGER (0..63)
      },
      choice-2 [1] SEQUENCE {
         spare-bit [0] INTEGER (0..3) DEFAULT 0,
         arfcn [1] INTEGER (0..1023)
      }
   },
   mac [5] OCTET STRING
}

GPRS-Resumption ::= SEQUENCE {
   spare-bit [0] INTEGER (0..7) DEFAULT 0,
   ack [1] INTEGER (0..1)
}

RANGE-LIMITS ::= SEQUENCE {
   range-lower [0] INTEGER (0..1023),
   range-upper [1] INTEGER (0..1023)
}

BA-List-Pref ::= SEQUENCE {
   length-of-ba-list-pref [0] INTEGER (0..255),
   range-limits-list [1] SEQUENCE OF RANGE-LIMITS,
   ba-freq-list [2] SEQUENCE OF INTEGER (0..1023)
}

UTRAN-Freq-List ::= SEQUENCE {
   length-of-utran-freq-list [0] INTEGER (0..255),
   fdd-arfcn-list [1] SEQUENCE OF INTEGER (0..16383),
   tdd-arfcn-list [2] SEQUENCE OF INTEGER (0..16383)
}

GSM-Description-struct ::= SEQUENCE {
   band-Indicator [0] INTEGER (0..1),
   arfcn [1] INTEGER (0..1023),
   bsic [2] INTEGER (0..63)
}

Cell-Sel-Ind-UTRAN-FDD-Description-struct ::= SEQUENCE {
   bandwidth-FDD [0] INTEGER (0..7) OPTIONAL,
   fdd-arfcn [1] INTEGER (0..16383),
   component-3 [2] SEQUENCE {
      fdd-Indic0 [0] INTEGER (0..1),
      nr-of-fdd-cells [1] INTEGER (0..31),
      fdd-CELL-INFORMATION-Field [2] BIT STRING 
   } OPTIONAL
}

Cell-Sel-Ind-UTRAN-TDD-Description-struct ::= SEQUENCE {
   bandwidth-TDD [0] INTEGER (0..7) OPTIONAL,
   tdd-arfcn [1] INTEGER (0..16383),
   component-3 [2] SEQUENCE {
      tdd-Indic0 [0] INTEGER (0..1),
      nr-of-tdd-cells [1] INTEGER (0..31),
      tdd-CELL-INFORMATION-Field [2] BIT STRING 
   } OPTIONAL
}

E-UTRAN-Description-struct ::= SEQUENCE {
   earfcn [0] INTEGER (0..65535),
   measurement-Bandwidth [1] INTEGER (0..7) OPTIONAL,
   not-Allowed-Cells [2] PCID-Group-IE OPTIONAL,
   target-pcid [3] INTEGER (0..511) OPTIONAL
}

Cell-Sel-Ind-Post-Rel-TCH-SDCCH ::= SEQUENCE {
   length [0] INTEGER (0..255),
   component-2 [1] EXPLICIT CHOICE {
      choice-1 [0] SEQUENCE OF GSM-Description-struct,
      choice-2 [1] SEQUENCE OF Cell-Sel-Ind-UTRAN-FDD-Description-struct,
      choice-3 [2] SEQUENCE OF Cell-Sel-Ind-UTRAN-TDD-Description-struct,
      choice-4 [3] SEQUENCE OF E-UTRAN-Description-struct
   }
}

Enhanced-DTM-CS-Release-Indication ::= SEQUENCE {
   spare-bit [0] INTEGER (0..7) DEFAULT 0,
   ind [1] INTEGER (0..1)
}

Group-Channel-Description-2 ::= SEQUENCE {
   length [0] INTEGER (0..255),
   channel-type-and-TDMA-offset [1] INTEGER (0..31),
   tn [2] INTEGER (0..7),
   tsc [3] INTEGER (0..7),
   spare-bit [4] INTEGER (0..1) DEFAULT 0,
   maio [5] INTEGER (0..63),
   hsn [6] INTEGER (0..63),
   frequency-Short-List-2 [7] Frequency-Short-List-2
}

Talker-Identity ::= SEQUENCE {
   length [0] INTEGER (0..255),
   spare-bit [1] INTEGER (0..31) DEFAULT 0,
   filler [2] INTEGER (0..7),
   talker-id-field [3] OCTET STRING
}

Talker-Priority-Status ::= SEQUENCE {
   length [0] INTEGER (0..255),
   es [1] INTEGER (0..1),
   spare-bit [2] INTEGER (0..1) DEFAULT 0,
   uai [3] INTEGER (0..1),
   priority [4] INTEGER (0..7)
}

VGCS-AMR-Configuration ::= SEQUENCE {
   length [0] INTEGER (0..255),
   amr-config [1] INTEGER (0..15),
   spare-bit [2] INTEGER (0..15) DEFAULT 0
}

Repeated-Individual-UTRAN-Priority-Parameters-struct ::= SEQUENCE {
   component-1 [0] EXPLICIT CHOICE {
      choice-1 [0] SEQUENCE OF INTEGER (0..16383),
      choice-2 [1] SEQUENCE OF INTEGER (0..16383)
   },
   utran-priority [1] INTEGER (0..7)
}

A3G-Individual-Priority-Parameters-Description-struct ::= SEQUENCE {
   default-utran-priority [0] INTEGER (0..7) OPTIONAL,
   repeated-Individual-UTRAN-Priority-Parameters-list [1] SEQUENCE OF 
      Repeated-Individual-UTRAN-Priority-Parameters-struct
}

Repeated-Individual-E-UTRAN-Priority-Parameters-Description-struct ::= 
   SEQUENCE {
   earfcn-list [0] SEQUENCE OF INTEGER (0..65535),
   e-utran-priority [1] INTEGER (0..7)
}

E-UTRAN-Individual-Priority-Parameters-Description-struct ::= SEQUENCE {
   default-e-utran-priority [0] INTEGER (0..7) OPTIONAL,
   repeated-Individual-E-UTRAN-Priority-Parameters-list [1] SEQUENCE OF 
      Repeated-Individual-E-UTRAN-Priority-Parameters-Description-struct
}

Individual-priorities ::= SEQUENCE {
   length [0] INTEGER (0..255),
   component-2 [1] SEQUENCE {
      geran-priority [0] INTEGER (0..7),
      a3G-Individual-Priority-Parameters-Description [1] 
         A3G-Individual-Priority-Parameters-Description-struct OPTIONAL,
      e-UTRAN-Individual-Priority-Parameters-Description [2] 
         E-UTRAN-Individual-Priority-Parameters-Description-struct OPTIONAL,
      t3230-timeout-value [3] INTEGER (0..7) OPTIONAL
   } OPTIONAL
}

Cipher-Response ::= SEQUENCE {
   spare-bit [0] INTEGER (0..7) DEFAULT 0,
   cr [1] INTEGER (0..1)
}

Classmark-Enquiry-Mask ::= SEQUENCE {
   classmark-ind [0] INTEGER (0..1),
   utran-classmark-ind [1] INTEGER (0..7),
   cdma2000-classmark-ind [2] INTEGER (0..1),
   geran-iu-mode-classmark-ind [3] INTEGER (0..1),
   spare-bit [4] INTEGER (0..3) DEFAULT 0
}

TMSI ::= INTEGER (0..4294967295)

Application-Data ::= OCTET STRING (SIZE (9))

Data-Identity ::= SEQUENCE {
   dp [0] INTEGER (0..7),
   di [1] INTEGER (0..15),
   ai [2] INTEGER (0..1)
}

GPRS-broadcast-information ::= SEQUENCE {
   length [0] INTEGER (0..255),
   gprs-Cell-Options [1] GPRS-Cell-Options-IE,
   gprs-Power-Control-Parameters [2] GPRS-Power-Control-Parameters-IE
}

Dynamic-Allocation-struct ::= SEQUENCE {
   extended-Dynamic-Allocation [0] INTEGER (0..1),
   component-2 [1] SEQUENCE {
      p0 [0] INTEGER (0..15),
      pr-mode [1] INTEGER (0..1)
   } OPTIONAL,
   usf-granularity [2] INTEGER (0..1),
   uplink-tfi-assignment [3] INTEGER (0..31) OPTIONAL,
   component-5 [4] INTEGER (0) DEFAULT 0,
   component-6 [5] EXPLICIT CHOICE {
      choice-1 [0] SEQUENCE {
         usf-tn0 [0] INTEGER (0..7) OPTIONAL,
         usf-tn1 [1] INTEGER (0..7) OPTIONAL,
         usf-tn2 [2] INTEGER (0..7) OPTIONAL,
         usf-tn3 [3] INTEGER (0..7) OPTIONAL,
         usf-tn4 [4] INTEGER (0..7) OPTIONAL,
         usf-tn5 [5] INTEGER (0..7) OPTIONAL,
         usf-tn6 [6] INTEGER (0..7) OPTIONAL,
         usf-tn7 [7] INTEGER (0..7) OPTIONAL
      },
      choice-2 [1] SEQUENCE {
         alpha [0] INTEGER (0..15),
         component-2 [1] SEQUENCE {
            usf-tn0 [0] INTEGER (0..7),
            gamma-tn0 [1] INTEGER (0..31)
         } OPTIONAL,
         component-3 [2] SEQUENCE {
            usf-tn1 [0] INTEGER (0..7),
            gamma-tn1 [1] INTEGER (0..31)
         } OPTIONAL,
         component-4 [3] SEQUENCE {
            usf-tn2 [0] INTEGER (0..7),
            gamma-tn2 [1] INTEGER (0..31)
         } OPTIONAL,
         component-5 [4] SEQUENCE {
            usf-tn3 [0] INTEGER (0..7),
            gamma-tn3 [1] INTEGER (0..31)
         } OPTIONAL,
         component-6 [5] SEQUENCE {
            usf-tn4 [0] INTEGER (0..7),
            gamma-tn4 [1] INTEGER (0..31)
         } OPTIONAL,
         component-7 [6] SEQUENCE {
            usf-tn5 [0] INTEGER (0..7),
            gamma-tn5 [1] INTEGER (0..31)
         } OPTIONAL,
         component-8 [7] SEQUENCE {
            usf-tn6 [0] INTEGER (0..7),
            gamma-tn6 [1] INTEGER (0..31)
         } OPTIONAL,
         component-9 [8] SEQUENCE {
            usf-tn7 [0] INTEGER (0..7),
            gamma-tn7 [1] INTEGER (0..31)
         } OPTIONAL
      }
   }
}

Timeslot-description-struct ::= CHOICE {
   choice-1 [0] SEQUENCE (SIZE (8)) OF SEQUENCE {
      usf-granularity [0] INTEGER (0..1) OPTIONAL
   },
   choice-2 [1] SEQUENCE {
      alpha [0] INTEGER (0..15),
      component-2 [1] SEQUENCE (SIZE (8)) OF SEQUENCE {
         component-1 [0] SEQUENCE {
            usf-granularity [0] INTEGER (0..1),
            gamma-tn0 [1] INTEGER (0..31)
         } OPTIONAL
      }
   }
}

USF-Assignment-struct ::= SEQUENCE {
   usf-allocation [0] INTEGER (0..7) OPTIONAL
}

Uplink-TBF-Assignment-struct ::= SEQUENCE {
   pfi [0] INTEGER (0..127),
   rlc-mode [1] INTEGER (0..1),
   uplink-tfi-assignment [2] INTEGER (0..31),
   channel-coding-command [3] INTEGER (0..3) OPTIONAL,
   egprs-Channel-Coding-Command [4] EGPRS-Modulation-and-Coding-IE OPTIONAL,
   egprs-Window-Size [5] EGPRS-Window-Size-IE OPTIONAL,
   component-7 [6] EXPLICIT CHOICE {
      usf-allocation [0] INTEGER (0..7),
      choice-2 [1] SEQUENCE OF USF-Assignment-struct
   }
}

Multiple-TBF-Allocation-struct ::= SEQUENCE {
   extended-dynamic-allocation [0] INTEGER (0..1),
   component-2 [1] SEQUENCE {
      p0 [0] INTEGER (0..15),
      pr-mode [1] INTEGER (0..1)
   } OPTIONAL,
   component-3 [2] SEQUENCE {
      timeslot-description [0] EXPLICIT Timeslot-description-struct,
      uplink-TBF-Assignment-list [1] SEQUENCE OF Uplink-TBF-Assignment-struct
   } OPTIONAL
}

RLC-Entity-Struct ::= SEQUENCE {
   uplink-tfi-assignment [0] INTEGER (0..31),
   rlc-mode [1] INTEGER (0..1),
   egprs-Window-Size [2] EGPRS-Window-Size-IE OPTIONAL,
   pfi [3] INTEGER (0..127)
}

Additional-PFCs-struct ::= SEQUENCE {
   uplink-tfi-assignment [0] INTEGER (0..31),
   npm-Transfer-Time [1] INTEGER (0..31) OPTIONAL,
   pfi [2] INTEGER (0..127)
}

RR-Packet-Uplink-Assignment ::= SEQUENCE {
   length [0] INTEGER (0..255),
   channel-coding-command [1] INTEGER (0..3),
   tlli-block-channel-coding [2] INTEGER (0..1),
   packet-Timing-Advance [3] Packet-Timing-Advance-IE,
   component-5 [4] EXPLICIT CHOICE {
      dynamic-Allocation [0] Dynamic-Allocation-struct,
      choice-2 [1] SEQUENCE {
         component-1 [0] INTEGER (0) DEFAULT 0,
         multiple-TBF-Allocation [1] Multiple-TBF-Allocation-struct
      }
   },
   component-6 [5] SEQUENCE {
      component-1 [0] SEQUENCE {
         egprs-mcs-mode [0] INTEGER (0..15),
         resegment [1] INTEGER (0..1),
         egprs-Window-Size [2] EGPRS-Window-Size-IE
      } OPTIONAL,
      packet-Extended-Timing-Advance [1] INTEGER (0..3) OPTIONAL,
      component-3 [2] SEQUENCE {
         rlc-mode [0] INTEGER (0..1) OPTIONAL,
         component-2 [1] SEQUENCE OF SEQUENCE {
            npm-Transfer-Time [0] INTEGER (0..31) OPTIONAL
         },
         uplink-EGPRS-Level [2] EGPRS-Level-IE,
         pulse-Format [3] EXPLICIT Pulse-Format-IE OPTIONAL,
         component-5 [4] SEQUENCE {
            component-1 [0] SEQUENCE {
               reported-timeslots [0] INTEGER (0..255),
               tsh [1] INTEGER (0..3)
            } OPTIONAL
         } OPTIONAL,
         component-6 [5] SEQUENCE {
            component-1 [0] SEQUENCE OF SEQUENCE {
               measurement-Control-E-UTRAN [0] INTEGER (0..1),
               e-utran-frequency-index [1] INTEGER (0..7),
               e-utran-frequency-index-list [2] SEQUENCE OF INTEGER (0..7)
            } OPTIONAL,
            component-2 [1] SEQUENCE OF SEQUENCE {
               measurement-Control-UTRAN [0] INTEGER (0..1),
               utran-frequency-index [1] INTEGER (0..31),
               utran-frequency-index-list [2] SEQUENCE OF INTEGER (0..31)
            } OPTIONAL,
            component-3 [2] SEQUENCE {
               component-1 [0] EXPLICIT CHOICE {
                  emst-NW-Capability [0] INTEGER (0..1),
                  choice-2 [1] SEQUENCE {
                     rlc-Entity-2 [0] RLC-Entity-Struct,
                     rlc-Entity-3 [1] RLC-Entity-Struct OPTIONAL
                  }
               },
               component-2 [1] SEQUENCE {
                  emsr-Additional-PFCs-1-list [0] SEQUENCE OF 
                     Additional-PFCs-struct,
                  emsr-Additional-PFCs-2-list [1] SEQUENCE OF 
                     Additional-PFCs-struct,
                  emsr-Additional-PFCs-3-list [2] SEQUENCE OF 
                     Additional-PFCs-struct
               } OPTIONAL
            } OPTIONAL
         } OPTIONAL
      } OPTIONAL
   } OPTIONAL
}

Downlink-TBF-assignment-struct ::= SEQUENCE {
   pfi [0] INTEGER (0..127),
   rlc-mode [1] INTEGER (0..1),
   downlink-tfi-assignment [2] INTEGER (0..31),
   control-ack [3] INTEGER (0..1),
   egprs-Window-Size [4] EGPRS-Window-Size-IE OPTIONAL
}

Multiple-Downlink-TBF-Assignment-struct ::= SEQUENCE {
   uplink-Control-Timeslot [0] INTEGER (0..7) OPTIONAL,
   timeslot-allocation [1] INTEGER (0..255),
   downlink-TBF-assignment-list [2] SEQUENCE OF Downlink-TBF-assignment-struct
}

DL-RLC-Entity-Struct ::= SEQUENCE {
   downlink-tfi-assignment [0] INTEGER (0..31),
   rlc-mode [1] INTEGER (0..1),
   egprs-Window-Size [2] EGPRS-Window-Size-IE OPTIONAL,
   pfi [3] INTEGER (0..127)
}

DL-Additional-PFCs-struct ::= SEQUENCE {
   downlink-tfi-assignment [0] INTEGER (0..31),
   npm-Transfer-Time [1] INTEGER (0..31) OPTIONAL,
   pfi [2] INTEGER (0..127)
}

RR-Packet-Downlink-Assignment ::= SEQUENCE {
   length [0] INTEGER (0..255),
   mac-mode [1] INTEGER (0..3),
   rlc-mode [2] INTEGER (0..1),
   timeslot-allocation [3] INTEGER (0..255),
   packet-Timing-Advance [4] Packet-Timing-Advance-IE,
   component-6 [5] SEQUENCE {
      p0 [0] INTEGER (0..15),
      component-2 [1] INTEGER (0) DEFAULT 0,
      pr-mode [2] INTEGER (0..1)
   } OPTIONAL,
   power-Control-Parameters [6] Power-Control-Parameters-IE OPTIONAL,
   downlink-tfi-assignment [7] INTEGER (0..31) OPTIONAL,
   component-9 [8] INTEGER (0) DEFAULT 0,
   component-10 [9] SEQUENCE {
      component-1 [0] SEQUENCE {
         egprs-Window-Size [0] EGPRS-Window-Size-IE,
         link-quality-measurement-mode [1] INTEGER (0..3)
      } OPTIONAL,
      packet-Extended-Timing-Advance [1] INTEGER (0..3) OPTIONAL,
      component-3 [2] SEQUENCE {
         multiple-Downlink-TBF-Assignment-list [0] SEQUENCE OF 
            Multiple-Downlink-TBF-Assignment-struct,
         component-2 [1] SEQUENCE {
            fanr [0] INTEGER (0..1),
            component-2 [1] SEQUENCE OF SEQUENCE {
               npm-Transfer-Time [0] INTEGER (0..31) OPTIONAL,
               event-based-fanr [1] INTEGER (0..1)
            },
            downlink-EGPRS-Level [2] EGPRS-Level-IE,
            component-4 [3] SEQUENCE {
               component-1 [0] SEQUENCE OF SEQUENCE {
                  measurement-Control-E-UTRAN [0] INTEGER (0..1),
                  e-utran-frequency-index [1] INTEGER (0..7),
                  e-utran-frequency-index-list [2] SEQUENCE OF INTEGER (0..7)
               } OPTIONAL,
               component-2 [1] SEQUENCE OF SEQUENCE {
                  measurement-Control-UTRAN [0] INTEGER (0..1),
                  utran-frequency-index [1] INTEGER (0..31),
                  utran-frequency-index-list [2] SEQUENCE OF INTEGER (0..31)
               } OPTIONAL,
               component-3 [2] SEQUENCE {
                  component-1 [0] SEQUENCE {
                     rlc-Entity-2 [0] DL-RLC-Entity-Struct,
                     rlc-Entity-3 [1] DL-RLC-Entity-Struct OPTIONAL
                  } OPTIONAL,
                  component-2 [1] SEQUENCE {
                     emsr-Additional-PFCs-1-list [0] SEQUENCE OF 
                        DL-Additional-PFCs-struct,
                     emsr-Additional-PFCs-2-list [1] SEQUENCE OF 
                        DL-Additional-PFCs-struct,
                     emsr-Additional-PFCs-3-list [2] SEQUENCE OF 
                        DL-Additional-PFCs-struct
                  } OPTIONAL
               } OPTIONAL
            } OPTIONAL
         } OPTIONAL
      } OPTIONAL
   } OPTIONAL
}

Downlink-TBF-assignment-2-struct ::= SEQUENCE {
   pfi [0] INTEGER (0..127),
   rlc-mode [1] INTEGER (0..1),
   tfi-Assignment [2] INTEGER (0..31),
   control-ack [3] INTEGER (0..1),
   npm-Transfer-Time [4] INTEGER (0..31) OPTIONAL,
   event-based-fanr [5] INTEGER (0..1),
   downlink-EGPRS-Window-Size [6] EGPRS-Window-Size-IE OPTIONAL
}

BTTI-Multiple-Downlink-Assignment-struct ::= SEQUENCE {
   uplink-Control-Timeslot [0] INTEGER (0..7) OPTIONAL,
   timeslot-allocation-c1 [1] INTEGER (0..255) OPTIONAL,
   timeslot-allocation-c2 [2] INTEGER (0..255) OPTIONAL,
   downlink-TBF-assignment-list [3] SEQUENCE OF 
      Downlink-TBF-assignment-2-struct
}

RTTI-Multiple-Downlink-Assignment-SC-struct ::= SEQUENCE {
   rtti-downlink-pdch-pair-assignment-sc [0] INTEGER (0..15),
   downlink-TBF-assignment-list [1] SEQUENCE OF 
      Downlink-TBF-assignment-2-struct
}

RTTI-Multiple-Downlink-Assignment-DC-struct ::= SEQUENCE {
   rtti-downlink-pdch-pair-assignment-dc [0] INTEGER (0..255),
   downlink-TBF-assignment-list [1] SEQUENCE OF 
      Downlink-TBF-assignment-2-struct
}

RR-Packet-Downlink-Assignment-Type-2 ::= SEQUENCE {
   length [0] INTEGER (0..255),
   rlc-mode [1] INTEGER (0..1),
   component-3 [2] SEQUENCE {
      p0-c1 [0] INTEGER (0..15),
      pr-mode-c1 [1] INTEGER (0..1),
      component-3 [2] SEQUENCE {
         p0-c2 [0] INTEGER (0..15),
         pr-mode-c2 [1] INTEGER (0..1)
      } OPTIONAL
   } OPTIONAL,
   power-Control-Parameters-C1 [3] Power-Control-Parameters-IE OPTIONAL,
   power-Control-Parameters-C2 [4] Power-Control-Parameters-IE OPTIONAL,
   downlink-tfi-assignment [5] INTEGER (0..31) OPTIONAL,
   egprs-Window-Size [6] EGPRS-Window-Size-IE,
   link-quality-measurement-mode [7] INTEGER (0..3),
   component-9 [8] EXPLICIT CHOICE {
      choice-1 [0] SEQUENCE {
         fanr [0] INTEGER (0..1),
         btti-Multiple-Downlink-Assignment-list [1] SEQUENCE OF 
            BTTI-Multiple-Downlink-Assignment-struct
      },
      choice-2 [1] EXPLICIT CHOICE {
         choice-1 [0] SEQUENCE {
            component-1 [0] EXPLICIT CHOICE {
               default [0] NULL,
               unchanged [1] NULL,
               choice-3 [2] SEQUENCE {
                  downlink-pdch-pairs-c1 [0] INTEGER (0..255),
                  uplink-pdch-pairs-c1 [1] INTEGER (0..255)
               }
            },
            rtti-Multiple-Downlink-Assignment-SC-list [1] SEQUENCE OF 
               RTTI-Multiple-Downlink-Assignment-SC-struct
         },
         choice-2 [1] SEQUENCE {
            component-1 [0] EXPLICIT CHOICE {
               default [0] NULL,
               unchanged [1] NULL,
               choice-3 [2] SEQUENCE {
                  downlink-pdch-pairs-c1 [0] INTEGER (0..255),
                  downlink-pdch-pairs-c2 [1] INTEGER (0..255),
                  uplink-pdch-pairs-c1 [2] INTEGER (0..255),
                  uplink-pdch-pairs-c2 [3] INTEGER (0..255)
               }
            },
            rtti-Multiple-Downlink-Assignment-DC-list [1] SEQUENCE OF 
               RTTI-Multiple-Downlink-Assignment-DC-struct
         }
      }
   },
   downlink-EGPRS-Level [9] EGPRS-Level-IE,
   component-11 [10] SEQUENCE {
      component-1 [0] SEQUENCE OF SEQUENCE {
         measurement-Control-E-UTRAN [0] INTEGER (0..1),
         e-utran-frequency-index [1] INTEGER (0..7),
         e-utran-frequency-index-list [2] SEQUENCE OF INTEGER (0..7)
      } OPTIONAL,
      component-2 [1] SEQUENCE OF SEQUENCE {
         measurement-Control-UTRAN [0] INTEGER (0..1),
         utran-frequency-index [1] INTEGER (0..31),
         utran-frequency-index-list [2] SEQUENCE OF INTEGER (0..31)
      } OPTIONAL,
      component-3 [2] SEQUENCE {
         component-1 [0] SEQUENCE {
            rlc-Entity-2 [0] DL-RLC-Entity-Struct,
            rlc-Entity-3 [1] DL-RLC-Entity-Struct OPTIONAL
         } OPTIONAL,
         component-2 [1] SEQUENCE {
            emsr-Additional-PFCs-1-list [0] SEQUENCE OF 
               DL-Additional-PFCs-struct,
            emsr-Additional-PFCs-2-list [1] SEQUENCE OF 
               DL-Additional-PFCs-struct,
            emsr-Additional-PFCs-3-list [2] SEQUENCE OF 
               DL-Additional-PFCs-struct,
            egprs-Packet-Downlink-Ack-Nack-Type-3-Support [3] INTEGER (0..1)
                OPTIONAL
         } OPTIONAL
      } OPTIONAL
   } OPTIONAL
}

Channel-Description-3 ::= SEQUENCE {
   tsc [0] INTEGER (0..7),
   component-2 [1] EXPLICIT CHOICE {
      choice-1 [0] SEQUENCE {
         maio [0] INTEGER (0..63),
         hsn [1] INTEGER (0..63)
      },
      choice-2 [1] SEQUENCE {
         spare-bit [0] INTEGER (0..3) DEFAULT 0,
         arfcn [1] INTEGER (0..1023)
      }
   }
}

DTM-Information-Details ::= SEQUENCE {
   length [0] INTEGER (0..255),
   max-LAPDm [1] INTEGER (0..7),
   gprs-ms-txpwr-max-cch [2] INTEGER (0..31),
   cell-identity [3] INTEGER (0..65535),
   component-5 [4] SEQUENCE {
      component-1 [0] SEQUENCE {
         dedicated-mode-mbms-notification-support [0] INTEGER (0..1),
         mnci-support [1] INTEGER (0..1)
      } OPTIONAL
   } OPTIONAL
}

Wait-Indication ::= SEQUENCE {
   t3122-T3142-timeout [0] INTEGER (0..255)
}

Carrier-Indication ::= SEQUENCE {
   spare-bit [0] INTEGER (0..7) DEFAULT 0,
   ci [1] INTEGER (0..1)
}

TLLI ::= INTEGER (0..4294967295)

LLC-PDU-Container ::= SEQUENCE {
   length [0] INTEGER (0..255),
   value [1] OCTET STRING (SIZE (0..255))
}

Cell-Description ::= SEQUENCE {
   bcch-arfcn-high [0] INTEGER (0..3),
   ncc [1] INTEGER (0..7),
   bcc [2] INTEGER (0..7),
   bcch-arfcn-low [3] INTEGER (0..255)
}

Handover-Reference ::= INTEGER (0..255)

Power-Command-and-access-type ::= SEQUENCE {
   atc [0] INTEGER (0..1),
   epc-mode [1] INTEGER (0..1),
   fpc-epc [2] INTEGER (0..1),
   power-level [3] INTEGER (0..31)
}

Synchronization-Indication ::= SEQUENCE {
   nci [0] INTEGER (0..1),
   rot [1] INTEGER (0..1),
   si [2] INTEGER (0..3)
}

Frequency-Short-List ::= SEQUENCE {
   component-1 [0] INTEGER (2) DEFAULT 2,
   spare-bit [1] INTEGER (0..3) DEFAULT 0,
   component-3 [2] EXPLICIT CHOICE {
      range-1024 [0] BIT STRING  (SIZE (67)),
      range-512 [1] BIT STRING  (SIZE (65)),
      range-256 [2] BIT STRING  (SIZE (65)),
      range-128 [3] BIT STRING  (SIZE (65)),
      variable-bitmap [4] BIT STRING  (SIZE (65))
   }
}

Time-Difference ::= SEQUENCE {
   length [0] INTEGER (0..255),
   value [1] INTEGER (0..255)
}

Timing-Advance ::= INTEGER (0..255)

DYNAMIC-ARFCN-MAPPING ::= SEQUENCE {
   gsm-Band [0] INTEGER (0..15),
   arfcn-first [1] INTEGER (0..1023),
   band-offset [2] INTEGER (0..1023),
   arfcn-range [3] INTEGER (0..127)
}

Dynamic-ARFCN-Mapping ::= SEQUENCE {
   length-of-dynamic-arfcn-mapping [0] INTEGER (0..255),
   dynamic-ARFCN-MAPPING-Description [1] SEQUENCE OF DYNAMIC-ARFCN-MAPPING
}

Dedicated-Service-Information ::= SEQUENCE {
   spare-bit [0] INTEGER (0..127) DEFAULT 0,
   sis [1] INTEGER (0..1)
}

PLMN-Index ::= SEQUENCE {
   plmn-index [0] INTEGER (0..15)
}

Handover-To-UTRAN-Command ::= SEQUENCE {
   length [0] INTEGER (0..255),
   handover-To-UTRAN-Command [1] OCTET STRING (SIZE (0..255))
}

Handover-To-cdma2000-Command ::= SEQUENCE {
   length [0] INTEGER (0..255),
   handover-To-cdma2000-Command [1] OCTET STRING (SIZE (0..255))
}

DL-DCCH-Message ::= SEQUENCE {
   length [0] INTEGER (0..255),
   value [1] OCTET STRING (SIZE (0..255))
}

CN-to-MS-transparent-information ::= SEQUENCE {
   length [0] INTEGER (0..255),
   value [1] OCTET STRING (SIZE (0..255))
}

MBMS-Session-Identity ::= SEQUENCE {
   length [0] INTEGER (0..255),
   mbms-Session-Identity [1] INTEGER (0..255)
}

MPRACH-description ::= SEQUENCE {
   length [0] INTEGER (0..255),
   mprach-description [1] MPRACH-description-IE
}

MBMS-p-t-m-Channel-Description ::= SEQUENCE {
   length [0] INTEGER (0..255),
   mbms-p-t-m-Channel-Description [1] MBMS-p-t-m-channel-description-IE
}

MBMS-Session-Parameters-List ::= SEQUENCE {
   length [0] INTEGER (0..255),
   mbms-Session-Parameters-List [1] MBMS-Session-Parameters-List-IE
}

Restriction-Timer ::= SEQUENCE {
   restriction-timer [0] INTEGER (0..15),
   spare-bit [1] INTEGER (0..15) DEFAULT 0
}

Token ::= SEQUENCE {
   identification [0] INTEGER (0..4294967295)
}

Uplink-Access-Indication ::= SEQUENCE {
   spare-bit [0] INTEGER (0..7) DEFAULT 0,
   ua-ind [1] INTEGER (0..1)
}

Request-Reference ::= SEQUENCE {
   ra [0] INTEGER (0..255),
   t1prime [1] INTEGER (0..31),
   t3 [2] INTEGER (0..63),
   t2 [3] INTEGER (0..31)
}

Reduced-group-or-broadcast-call-reference ::= SEQUENCE {
   binary-code [0] INTEGER (0..134217727),
   sf [1] INTEGER (0..1),
   spare-bit [2] INTEGER (0..15) DEFAULT 0
}

Channel-Request-Description-2 ::= SEQUENCE {
   length [0] INTEGER (0..255),
   packet-establishment-cause [1] INTEGER (0..3),
   channel-Request-Description [2] Channel-Request-Description-IE,
   pfi [3] INTEGER (0..127) OPTIONAL,
   multiple-TBF-Capability [4] INTEGER (0..1),
   component-6 [5] SEQUENCE {
      rlc-Non-persistent-Mode-Capability [0] INTEGER (0..1),
      reduced-Latency-Capability [1] INTEGER (0..1),
      uplink-EGPRS2 [2] INTEGER (0..3),
      downlink-EGPRS2 [3] INTEGER (0..3),
      component-5 [4] SEQUENCE {
         emst-MS-Capability [0] INTEGER (0..1),
         component-2 [1] SEQUENCE {
            emsr-MS-Capability [0] INTEGER (0..1),
            fanr-Capability [1] INTEGER (0..1) OPTIONAL
         } OPTIONAL
      } OPTIONAL
   } OPTIONAL
}

GERAN-Iu-Mode-Classmark ::= SEQUENCE {
   length [0] INTEGER (0..255),
   geran-Iu-Mode-Classmark [1] OCTET STRING (SIZE (0..255))
}

Suspension-Cause ::= INTEGER (0..255)

Service-Support ::= SEQUENCE {
   spare-bit [0] INTEGER (0..63) DEFAULT 0,
   mbms-multicast [1] INTEGER (0..1),
   mbms-broadcast [2] INTEGER (0..1)
}

Mobile-Time-Difference ::= SEQUENCE {
   length [0] INTEGER (0..255),
   mobile-time-difference [1] INTEGER (0..2097151),
   spare-bit [2] INTEGER (0..7) DEFAULT 0
}

Mobile-Time-Difference-on-Hyperframe-level ::= SEQUENCE {
   length [0] INTEGER (0..255),
   value [1] BIT STRING  (SIZE (33)),
   spare-bit [2] INTEGER (0..127) DEFAULT 0
}

PS-Cause ::= SEQUENCE {
   value [0] INTEGER (0..15)
}

Random-Reference-Establishment-Cause ::= INTEGER (0..255)

UTRAN-Classmark ::= SEQUENCE {
   length [0] INTEGER (0..255),
   utran-classmark [1] OCTET STRING (SIZE (0..255))
}

NCELL-Report-struct ::= SEQUENCE {
   rxlev-ncell [0] INTEGER (0..63),
   bcch-freq-ncell [1] INTEGER (0..31),
   bsic-ncell [2] INTEGER (0..63)
}

Measurement-Results ::= SEQUENCE {
   ba-used [0] INTEGER (0..1),
   dtx-used [1] INTEGER (0..1),
   rxlev-full-serving-cell [2] INTEGER (0..63),
   a3G-BA-USED [3] INTEGER (0..1),
   meas-valid [4] INTEGER (0..1),
   rxlev-sub-serving-cell [5] INTEGER (0..63),
   si23-ba-used [6] INTEGER (0..1),
   rxqual-full-serving-cell [7] INTEGER (0..7),
   rxqual-sub-serving-cell [8] INTEGER (0..7),
   no-ncell-m [9] INTEGER (0..7),
   component-11 [10] EXPLICIT CHOICE {
      choice-1 [0] NULL,
      choice-2 [1] SEQUENCE {
         ncell-Report [0] SEQUENCE (SIZE (0..7)) OF NCELL-Report-struct,
         utran-CSG-Measurement-Report [1] UTRAN-CSG-Measurement-Report-IE
             OPTIONAL
      }
   }
}

Extended-Measurement-Results ::= SEQUENCE {
   sc-used [0] INTEGER (0..1),
   dtx-used [1] INTEGER (0..1),
   rxlev-carrier [2] SEQUENCE (SIZE (21)) OF INTEGER (0..63)
}

L2-Pseudo-Length ::= SEQUENCE {
   pseudo-length [0] INTEGER (0..63),
   fixed-bits [1] INTEGER (1) DEFAULT 1
}

Dedicated-mode-or-TBF ::= SEQUENCE {
   spare-bit [0] INTEGER (0..1) DEFAULT 0,
   tma [1] INTEGER (0..1),
   downlink [2] INTEGER (0..1),
   tbf-or-dedicated [3] INTEGER (0..1)
}

Page-Mode ::= SEQUENCE {
   spare-bit [0] INTEGER (0..3) DEFAULT 0,
   pm [1] INTEGER (0..3)
}

Packet-Channel-Description ::= SEQUENCE {
   channel-type [0] INTEGER (0..31),
   tn [1] INTEGER (0..7),
   tsc [2] INTEGER (0..7),
   component-4 [3] EXPLICIT CHOICE {
      choice-1 [0] EXPLICIT CHOICE {
         choice-1 [0] SEQUENCE {
            spare-bit [0] INTEGER (0..1) DEFAULT 0,
            arfcn [1] INTEGER (0..1023)
         },
         choice-2 [1] SEQUENCE {
            spare-bit [0] INTEGER (0..1) DEFAULT 0,
            maio [1] INTEGER (0..63),
            ma-number-ind [2] INTEGER (0..1),
            component-4 [3] EXPLICIT CHOICE {
               spare-bits [0] INTEGER (0..3),
               change-mark-1 [1] INTEGER (0..3)
            }
         }
      },
      choice-2 [1] SEQUENCE {
         maio [0] INTEGER (0..63),
         hsn [1] INTEGER (0..63)
      }
   }
}

Feature-Indicator ::= SEQUENCE {
   spare-bit [0] INTEGER (0..3) DEFAULT 0,
   cs-ir [1] INTEGER (0..1),
   ps-ir [2] INTEGER (0..1)
}

Channel-Needed ::= SEQUENCE {
   channel-second [0] INTEGER (0..3),
   channel-first [1] INTEGER (0..3)
}

RACH-Control-Parameters ::= SEQUENCE {
   max-retrans [0] INTEGER (0..3),
   tx-integer [1] INTEGER (0..15),
   cell-bar-access [2] INTEGER (0..1),
   re [3] INTEGER (0..1),
   acc [4] INTEGER (0..65535)
}

Neighbour-Cell-Description ::= CHOICE {
   bitmap0 [0] SEQUENCE {
      ext-ind [0] INTEGER (0..1),
      ba-ind [1] INTEGER (0..1),
      bitmap0 [2] BIT STRING  (SIZE (124))
   },
   choice-2 [1] SEQUENCE {
      ext-ind [0] INTEGER (0..1),
      ba-ind [1] INTEGER (0..1),
      component-3 [2] EXPLICIT CHOICE {
         range-1024 [0] BIT STRING  (SIZE (123)),
         range-512 [1] BIT STRING  (SIZE (121)),
         range-256 [2] BIT STRING  (SIZE (121)),
         range-128 [3] BIT STRING  (SIZE (121)),
         variable-bitmap [4] BIT STRING  (SIZE (121))
      }
   }
}

NCC-Permitted ::= INTEGER (0..255)

Neighbour-Cell-Description-2 ::= CHOICE {
   bitmap0 [0] SEQUENCE {
      multiband-reporting [0] INTEGER (0..3),
      ba-ind [1] INTEGER (0..1),
      ca-arfcn [2] BIT STRING  (SIZE (124))
   },
   choice-2 [1] SEQUENCE {
      multiband-reporting [0] INTEGER (0..3),
      ba-ind [1] INTEGER (0..1),
      component-3 [2] EXPLICIT CHOICE {
         range-1024 [0] BIT STRING  (SIZE (123)),
         range-512 [1] BIT STRING  (SIZE (121)),
         range-256 [2] BIT STRING  (SIZE (121)),
         range-128 [3] BIT STRING  (SIZE (121)),
         variable-bitmap [4] BIT STRING  (SIZE (121))
      }
   }
}

Control-Channel-Description ::= SEQUENCE {
   mscr [0] INTEGER (0..1),
   att [1] INTEGER (0..1),
   bs-ag-blks-res [2] INTEGER (0..7),
   ccch-conf [3] INTEGER (0..7),
   si22ind [4] INTEGER (0..1),
   cbq3 [5] INTEGER (0..3),
   spare-bit [6] INTEGER (0..3) DEFAULT 0,
   bs-pa-mfrms [7] INTEGER (0..7),
   t3212 [8] INTEGER (0..255)
}

Cell-Options-BCCH ::= SEQUENCE {
   dn-ind [0] INTEGER (0..1),
   pwrc [1] INTEGER (0..1),
   dtx [2] INTEGER (0..3),
   radio-link-timeout [3] INTEGER (0..15)
}

Cell-Selection-Parameters ::= SEQUENCE {
   cell-reselect-hysteresis [0] INTEGER (0..7),
   ms-txpwr-max-cch [1] INTEGER (0..31),
   acs [2] INTEGER (0..1),
   neci [3] INTEGER (0..1),
   rxlev-access-min [4] INTEGER (0..63)
}

Cell-Options-SACCH ::= SEQUENCE {
   dtx-high [0] INTEGER (0..1),
   pwrc [1] INTEGER (0..1),
   dtx-low [2] INTEGER (0..3),
   radio-link-timeout [3] INTEGER (0..15)
}

Extended-Measurement-Frequency-List ::= CHOICE {
   bitmap0 [0] SEQUENCE {
      spare-bit [0] INTEGER (0..1) DEFAULT 0,
      seq-code [1] INTEGER (0..1),
      bitmap0 [2] BIT STRING  (SIZE (124))
   },
   choice-2 [1] SEQUENCE {
      spare-bit [0] INTEGER (0..1) DEFAULT 0,
      seq-code [1] INTEGER (0..1),
      component-3 [2] EXPLICIT CHOICE {
         range-1024 [0] BIT STRING  (SIZE (123)),
         range-512 [1] BIT STRING  (SIZE (121)),
         range-256 [2] BIT STRING  (SIZE (121)),
         range-128 [3] BIT STRING  (SIZE (121)),
         variable-bitmap [4] BIT STRING  (SIZE (121))
      }
   }
}

LHType ::= ENUMERATED { lbit(0), hbit(1) }

Access-Technologies-Request-struct ::= SEQUENCE {
   access-Technology-Type [0] INTEGER (0..15),
   access-Technology-Type-list [1] SEQUENCE OF INTEGER (0..15)
}

EGPRS-Packet-Uplink-Assignment ::= SEQUENCE {
   extended-RA [0] INTEGER (0..31),
   access-Technologies-Request [1] Access-Technologies-Request-struct OPTIONAL,
   component-3 [2] EXPLICIT CHOICE {
      choice-1 [0] SEQUENCE {
         tfi-assignment [0] INTEGER (0..31),
         polling [1] INTEGER (0..1),
         component-3 [2] INTEGER (0) DEFAULT 0,
         usf [3] INTEGER (0..7),
         usf-granularity [4] INTEGER (0..1),
         component-6 [5] SEQUENCE {
            p0 [0] INTEGER (0..15),
            pr-mode [1] INTEGER (0..1)
         } OPTIONAL,
         egprs-channel-coding-command [6] EGPRS-Modulation-and-Coding-IE,
         tlli-block-channel-coding [7] INTEGER (0..1),
         bep-period2 [8] INTEGER (0..15) OPTIONAL,
         resegment [9] INTEGER (0..1),
         egprs-Window-Size [10] EGPRS-Window-Size-IE,
         alpha [11] INTEGER (0..15) OPTIONAL,
         gamma [12] INTEGER (0..31),
         timing-advance-index [13] INTEGER (0..15) OPTIONAL,
         tbf-starting-time [14] INTEGER (0..65535) OPTIONAL,
         component-16 [15] EXPLICIT CHOICE {
            choice-1 [0] SEQUENCE {
               component-1 [0] SEQUENCE {
                  component-1 [0] SEQUENCE {
                     reported-timeslots [0] INTEGER (0..255),
                     tsh [1] INTEGER (0..3)
                  } OPTIONAL
               } OPTIONAL
            },
            choice-2 [1] SEQUENCE {
               rtti-USF-Mode [0] INTEGER (0..1),
               pdch-pair-indication [1] INTEGER (0..7),
               additional-USF [2] SEQUENCE (SIZE (0..1)) OF INTEGER (0..7),
               component-4 [3] SEQUENCE {
                  usf2 [0] INTEGER (0..7),
                  additional-USF2 [1] SEQUENCE (SIZE (0..1)) OF INTEGER (0..7)
               } OPTIONAL,
               component-5 [4] SEQUENCE {
                  reported-timeslots [0] INTEGER (0..255),
                  tsh [1] INTEGER (0..3)
               } OPTIONAL
            }
         } OPTIONAL
      },
      choice-2 [1] SEQUENCE {
         alpha [0] INTEGER (0..15) OPTIONAL,
         gamma [1] INTEGER (0..31),
         tbf-starting-time [2] INTEGER (0..65535),
         number-of-radio-blocks-allocated [3] INTEGER (0..3),
         component-5 [4] SEQUENCE {
            p0 [0] INTEGER (0..15),
            component-2 [1] INTEGER (0) DEFAULT 0,
            pr-mode [2] INTEGER (0..1)
         } OPTIONAL,
         component-6 [5] SEQUENCE {
            pfi [0] INTEGER (0..127) OPTIONAL
         } OPTIONAL
      }
   }
}

Multiple-Blocks-Packet-Downlink-Assignment ::= SEQUENCE {
   tbf-starting-time [0] INTEGER (0..65535),
   number-of-allocated-blocks [1] INTEGER (0..15),
   component-3 [2] EXPLICIT CHOICE {
      choice-1 [0] SEQUENCE {
         tmgi [0] EXPLICIT TMGI-IE,
         mbms-Session-Identity [1] INTEGER (0..255) OPTIONAL
      },
      choice-2 [1] SEQUENCE {
         tlli-g-rnti [0] INTEGER (0..4294967295),
         component-2 [1] SEQUENCE {
            length-Indicator-of-MS-ID [0] INTEGER (0..3),
            ms-id [1] BIT STRING  (SIZE (1..4)),
            packet-timing-advance [2] Packet-Timing-Advance-IE,
            component-4 [3] SEQUENCE {
               alpha [0] INTEGER (0..15),
               gamma [1] INTEGER (0..31) OPTIONAL
            } OPTIONAL
         } OPTIONAL
      }
   } OPTIONAL
}

Frequency-Parameters-before-time ::= SEQUENCE {
   length-of-frequency-parameters [0] INTEGER (0..63),
   component-2 [1] SEQUENCE {
      spare [0] INTEGER (0) DEFAULT 0,
      maio [1] INTEGER (0..63),
      mobile-Allocation [2] OCTET STRING
   } OPTIONAL
}

Packet-Uplink-Assignment ::= SEQUENCE {
   component-1 [0] EXPLICIT CHOICE {
      choice-1 [0] SEQUENCE {
         tfi-assignment [0] INTEGER (0..31),
         polling [1] INTEGER (0..1),
         component-3 [2] INTEGER (0) DEFAULT 0,
         usf [3] INTEGER (0..7),
         usf-granularity [4] INTEGER (0..1),
         component-6 [5] SEQUENCE {
            p0 [0] INTEGER (0..15),
            pr-mode [1] INTEGER (0..1)
         } OPTIONAL,
         channel-coding-command [6] INTEGER (0..3),
         tlli-block-channel-coding [7] INTEGER (0..1),
         alpha [8] INTEGER (0..15) OPTIONAL,
         gamma [9] INTEGER (0..31),
         timing-advance-index [10] INTEGER (0..15) OPTIONAL,
         tbf-starting-time [11] INTEGER (0..65535) OPTIONAL
      },
      choice-2 [1] SEQUENCE {
         alpha [0] INTEGER (0..15) OPTIONAL,
         gamma [1] INTEGER (0..31),
         component-3 [2] INTEGER (1) DEFAULT 1,
         tbf-starting-time [3] INTEGER (0..65535),
         component-5 [4] SEQUENCE {
            p0 [0] INTEGER (0..15),
            component-2 [1] INTEGER (0) DEFAULT 0,
            pr-mode [2] INTEGER (0..1)
         } OPTIONAL
      }
   },
   component-2 [1] SEQUENCE {
      extended-RA [0] INTEGER (0..31) OPTIONAL
   } OPTIONAL,
   component-3 [2] SEQUENCE {
      pfi [0] INTEGER (0..127) OPTIONAL
   } OPTIONAL
}

Packet-Downlink-Assignment ::= SEQUENCE {
   tlli [0] INTEGER (0..4294967295),
   component-2 [1] SEQUENCE {
      tfi-assignment [0] INTEGER (0..31),
      rlc-mode [1] INTEGER (0..1),
      alpha [2] INTEGER (0..15) OPTIONAL,
      gamma [3] INTEGER (0..31),
      polling [4] INTEGER (0..1),
      ta-valid [5] INTEGER (0..1)
   } OPTIONAL,
   timing-advance-index [2] INTEGER (0..15) OPTIONAL,
   tbf-starting-time [3] INTEGER (0..65535) OPTIONAL,
   component-5 [4] SEQUENCE {
      p0 [0] INTEGER (0..15),
      component-2 [1] INTEGER (0) DEFAULT 0,
      pr-mode [2] INTEGER (0..1)
   } OPTIONAL,
   component-6 [5] SEQUENCE {
      egprs-Window-Size [0] EGPRS-Window-Size-IE,
      link-quality-measurement-mode [1] INTEGER (0..3),
      bep-period2 [2] INTEGER (0..15) OPTIONAL
   } OPTIONAL,
   component-7 [6] SEQUENCE {
      pfi [0] INTEGER (0..127) OPTIONAL
   } OPTIONAL,
   component-8 [7] SEQUENCE {
      npm-Transfer-Time [0] INTEGER (0..31) OPTIONAL,
      component-2 [1] EXPLICIT CHOICE {
         choice-1 [0] SEQUENCE {
            event-based-fanr [0] INTEGER (0..1) OPTIONAL
         },
         choice-2 [1] SEQUENCE {
            event-based-fanr [0] INTEGER (0..1),
            pdch-pair-indication [1] INTEGER (0..7)
         }
      },
      downlink-EGPRS-Level [2] EGPRS-Level-IE
   } OPTIONAL
}

Second-Part-Packet-Assignment ::= SEQUENCE {
   component-1 [0] SEQUENCE {
      extended-RA [0] INTEGER (0..31) OPTIONAL
   } OPTIONAL
}

IA-Rest-Octets ::= CHOICE {
   compressed-Inter-RAT-HO-INFO-IND [0] LHType,
   choice-2 [1] EXPLICIT CHOICE {
      egprs-Packet-Uplink-Assignment [0] EGPRS-Packet-Uplink-Assignment,
      multiple-Blocks-Packet-Downlink-Assignment [1] 
         Multiple-Blocks-Packet-Downlink-Assignment
   },
   choice-3 [2] SEQUENCE {
      frequency-Parameters-before-time [0] Frequency-Parameters-before-time,
      compressed-Inter-RAT-HO-INFO-IND [1] LHType
   },
   choice-4 [3] SEQUENCE {
      component-1 [0] EXPLICIT CHOICE {
         packet-Uplink-Assignment [0] Packet-Uplink-Assignment,
         packet-Downlink-Assignment [1] Packet-Downlink-Assignment,
         second-Part-Packet-Assignment [2] Second-Part-Packet-Assignment
      },
      component-2 [1] SEQUENCE {
         implicit-Reject-CS [0] INTEGER (0..1),
         implicit-Reject-PS [1] INTEGER (0..1)
      } OPTIONAL
   }
}

IAX-Rest-Octets ::= SEQUENCE {
   compressed-Inter-RAT-HO-INFO-IND [0] INTEGER (0..1)
}

IAR-Rest-Octets ::= SEQUENCE {
   extended-RA-1 [0] INTEGER (0..31) OPTIONAL,
   extended-RA-2 [1] INTEGER (0..31) OPTIONAL,
   extended-RA-3 [2] INTEGER (0..31) OPTIONAL,
   extended-RA-4 [3] INTEGER (0..31) OPTIONAL
}

IPA-Uplink-Assignment-struct ::= SEQUENCE {
   component-1 [0] SEQUENCE OF SEQUENCE {
      random-Reference [0] INTEGER (0..2047),
      fn-offset [1] INTEGER (0..255),
      gamma [2] INTEGER (0..31),
      timing-advance-value [3] INTEGER (0..63),
      tfi-assignment [4] INTEGER (0..31),
      usf [5] INTEGER (0..7),
      egprs-channel-coding-command [6] INTEGER (0..15),
      radio-Access-Capabilities-Request [7] INTEGER (0..1)
   },
   tn [1] INTEGER (0..7),
   frequency-Parameters [2] Frequency-Parameters-IE OPTIONAL
}

IPA-Downlink-Assignment-struct ::= SEQUENCE {
   component-1 [0] SEQUENCE OF SEQUENCE {
      tlli [0] INTEGER (0..4294967295),
      tfi-assignment [1] INTEGER (0..31),
      gamma [2] INTEGER (0..31),
      timing-advance-value [3] INTEGER (0..63) OPTIONAL
   },
   link-quality-measurement-mode [1] INTEGER (0..3) OPTIONAL,
   rlc-mode [2] INTEGER (0..1),
   tn [3] INTEGER (0..7),
   frequency-Parameters [4] Frequency-Parameters-IE OPTIONAL
}

IPA-Single-Block-Uplink-Assignment-struct ::= SEQUENCE {
   component-1 [0] SEQUENCE OF SEQUENCE {
      random-Reference [0] INTEGER (0..2047),
      fn-offset [1] INTEGER (0..255),
      gamma [2] INTEGER (0..31),
      timing-advance-value [3] INTEGER (0..63),
      starting-time-offset [4] INTEGER (0..63)
   },
   tn [1] INTEGER (0..7),
   frequency-Parameters [2] Frequency-Parameters-IE OPTIONAL
}

IPA-Rest-Octets ::= SEQUENCE {
   ipa-Uplink-Assignment-struct [0] IPA-Uplink-Assignment-struct OPTIONAL,
   ipa-Downlink-Assignment-struct [1] IPA-Downlink-Assignment-struct OPTIONAL,
   ipa-Single-Block-Uplink-Assignment-struct [2] 
      IPA-Single-Block-Uplink-Assignment-struct OPTIONAL
}

List-of-Group-Call-NCH-information ::= SEQUENCE OF Group-Call-information

List-of-Reduced-GCR ::= SEQUENCE OF INTEGER (0..268435455)

List-of-VSTK-RAND-information ::= SEQUENCE OF SEQUENCE {
   segment-Id [0] INTEGER (0..1),
   vstk-rand [1] BIT STRING  (SIZE (36)) OPTIONAL
}

List-of-Emergency-information ::= SEQUENCE OF INTEGER (0..1)

NT-N-Rest-Octets ::= SEQUENCE {
   nln-nch [0] INTEGER (0..3) OPTIONAL,
   list-of-Group-Call-NCH-information [1] List-of-Group-Call-NCH-information,
   component-3 [2] SEQUENCE {
      cell-global-count [0] INTEGER (0..3) OPTIONAL,
      list-of-Reduced-GCR [1] List-of-Reduced-GCR,
      list-of-VSTK-RAND-information [2] List-of-VSTK-RAND-information
   } OPTIONAL,
   component-4 [3] SEQUENCE {
      list-of-Emergency-information [0] List-of-Emergency-information,
      priority-Uplink-access [1] INTEGER (0..1) OPTIONAL,
      component-3 [2] SEQUENCE {
         fr-AMR-Config [0] INTEGER (0..15) OPTIONAL,
         hr-AMR-Config [1] INTEGER (0..15) OPTIONAL
      } OPTIONAL,
      component-4 [3] SEQUENCE {
         sms-Data-Confidentiality-Ind [0] INTEGER (0..1),
         sms-Guaranteed-Privacy-Ind [1] INTEGER (0..1)
      } OPTIONAL
   } OPTIONAL
}

Priority ::= INTEGER (0..7)

MBMS-Information ::= SEQUENCE {
   mbms-Sessions-List [0] MBMS-Session-List-IE,
   component-2 [1] SEQUENCE {
      same-as-notification-flag [0] INTEGER (0..1),
      mbms-Sessions-List [1] MBMS-Session-List-IE
   } OPTIONAL,
   component-3 [2] SEQUENCE OF SEQUENCE {
      mbms-Channel-Parameters [0] EXPLICIT MBMS-Channel-Parameters-IE,
      mbms-Sessions-List [1] MBMS-Session-List-IE
   }
}

ETWS-Primary-Notification-struct ::= SEQUENCE {
   component-1 [0] EXPLICIT CHOICE {
      total-No-Of-Segments-For-ETWS-Primary-Notification [0] INTEGER (0..15),
      segment-Number [1] INTEGER (0..15)
   },
   pni [1] INTEGER (0..1),
   length-Of-Segment [2] INTEGER (0..127),
   etws-Primary-Notification-Data [3] BIT STRING  (SIZE (0..127))
}

P1-Rest-Octets ::= SEQUENCE {
   component-1 [0] SEQUENCE {
      nln-pch [0] INTEGER (0..3),
      nln-status-PCH [1] INTEGER (0..1)
   } OPTIONAL,
   priority1 [1] Priority OPTIONAL,
   priority2 [2] Priority OPTIONAL,
   group-Call-information [3] Group-Call-information OPTIONAL,
   packet-Page-Indication-1 [4] LHType OPTIONAL,
   packet-Page-Indication-2 [5] LHType OPTIONAL,
   component-7 [6] SEQUENCE {
      component-1 [0] EXPLICIT CHOICE {
         cell-global-count [0] INTEGER (0..3),
         choice-2 [1] SEQUENCE {
            cell-global-count [0] INTEGER (0..3),
            vstk-rand [1] BIT STRING  (SIZE (36))
         },
         choice-3 [2] SEQUENCE {
            reduced-GCR [0] INTEGER (0..268435455),
            vstk-rand [1] BIT STRING  (SIZE (36))
         },
         choice-4 [3] SEQUENCE {
            cell-global-count [0] INTEGER (0..3),
            reduced-GCR [1] INTEGER (0..268435455),
            vstk-rand [2] BIT STRING  (SIZE (36))
         }
      } OPTIONAL,
      component-2 [1] SEQUENCE {
         mbms-Notification-1 [0] EXPLICIT MBMS-Channel-Parameters-IE OPTIONAL,
         mbms-Notification-2 [1] SEQUENCE {
            mbms-Channel-Parameters-IE [0] EXPLICIT MBMS-Channel-Parameters-IE
                OPTIONAL
         } OPTIONAL,
         mbms-Information [2] MBMS-Information OPTIONAL
      } OPTIONAL
   } OPTIONAL,
   component-8 [7] SEQUENCE {
      amr-Config [0] INTEGER (0..15) OPTIONAL
   } OPTIONAL,
   component-9 [8] SEQUENCE {
      priority-Uplink-Access [0] INTEGER (0..1),
      etws-Primary-Notification [1] ETWS-Primary-Notification-struct OPTIONAL
   } OPTIONAL,
   component-10 [9] SEQUENCE {
      implicit-Reject-CS [0] INTEGER (0..1),
      implicit-Reject-PS [1] INTEGER (0..1)
   } OPTIONAL,
   ipa-Support [10] INTEGER (0..1) OPTIONAL
}

P2-MBMS-Information ::= SEQUENCE {
   mbms-Sessions-List [0] MBMS-Session-List-IE,
   mbms-Sessions-List-2 [1] MBMS-Session-List-IE OPTIONAL,
   component-3 [2] SEQUENCE OF SEQUENCE {
      mbms-Channel-Parameters [0] EXPLICIT MBMS-Channel-Parameters-IE,
      mbms-Sessions-List [1] MBMS-Session-List-IE
   }
}

P2-Rest-Octets ::= SEQUENCE {
   cn3 [0] INTEGER (0..3) OPTIONAL,
   component-2 [1] SEQUENCE {
      nln-pch [0] INTEGER (0..3),
      nln-status-PCH [1] INTEGER (0..1)
   } OPTIONAL,
   priority1 [2] Priority OPTIONAL,
   priority2 [3] Priority OPTIONAL,
   priority3 [4] Priority OPTIONAL,
   packet-Page-Indication-3 [5] LHType OPTIONAL,
   component-7 [6] SEQUENCE {
      component-1 [0] SEQUENCE {
         mbms-Notification-3 [0] EXPLICIT MBMS-Channel-Parameters-IE OPTIONAL,
         p2-MBMS-Information [1] P2-MBMS-Information OPTIONAL
      } OPTIONAL
   } OPTIONAL,
   component-8 [7] SEQUENCE {
      implicit-Reject-CS [0] INTEGER (0..1),
      implicit-Reject-PS [1] INTEGER (0..1)
   } OPTIONAL,
   ipa-Support [8] INTEGER (0..1) OPTIONAL
}

P3-Rest-Octets ::= SEQUENCE {
   component-1 [0] SEQUENCE {
      cn3 [0] INTEGER (0..3),
      cn4 [1] INTEGER (0..3)
   } OPTIONAL,
   component-2 [1] SEQUENCE {
      nln-pch [0] INTEGER (0..3),
      nln-status-PCH [1] INTEGER (0..1)
   } OPTIONAL,
   priority1 [2] Priority OPTIONAL,
   priority2 [3] Priority OPTIONAL,
   priority3 [4] Priority OPTIONAL,
   priority4 [5] Priority OPTIONAL,
   component-7 [6] SEQUENCE {
      implicit-Reject-CS [0] INTEGER (0..1),
      implicit-Reject-PS [1] INTEGER (0..1)
   } OPTIONAL,
   ipa-Support [7] INTEGER (0..1) OPTIONAL
}

Band-indicator ::= LHType

SI1-Rest-Octets ::= SEQUENCE {
   nch-Position [0] INTEGER (0..31) OPTIONAL,
   band-indicator [1] Band-indicator
}

SI2bis-Rest-Octets ::= SEQUENCE {
   padding [0] EXPLICIT CHOICE {
      choice-1 [0] NULL,
      choice-2 [1] NULL
   } OPTIONAL
}

SI2ter-UTRAN-FDD-Description-struct ::= SEQUENCE {
   component-1 [0] INTEGER (1) DEFAULT 1,
   fdd-arfcn [1] INTEGER (0..16383),
   bandwidth-FDD [2] INTEGER (0..7) OPTIONAL
}

SI2ter-UTRAN-TDD-Description-struct ::= SEQUENCE {
   component-1 [0] INTEGER (1) DEFAULT 1,
   tdd-arfcn [1] INTEGER (0..16383),
   bandwidth-TDD [2] INTEGER (0..7) OPTIONAL
}

SI2ter-3G-MEASUREMENT-Parameters-Description-struct ::= SEQUENCE {
   qsearch-I [0] INTEGER (0..15),
   component-2 [1] SEQUENCE {
      fdd-Qoffset [0] INTEGER (0..15),
      fdd-Qmin [1] INTEGER (0..7)
   } OPTIONAL,
   tdd-Qoffset [2] INTEGER (0..15) OPTIONAL
}

A3G-Additional-Measurement-Parameters-Description-struct ::= SEQUENCE {
   fdd-Qmin-Offset [0] INTEGER (0..7),
   fdd-RSCPmin [1] INTEGER (0..15)
}

SI2ter-Rest-Octets ::= SEQUENCE {
   component-1 [0] SEQUENCE {
      si2ter-MP-CHANGE-MARK [0] INTEGER (0..1),
      si2ter-3G-CHANGE-MARK [1] INTEGER (0..1),
      si2ter-INDEX [2] INTEGER (0..7),
      si2ter-COUNT [3] INTEGER (0..7),
      utran-FDD-Description [4] SI2ter-UTRAN-FDD-Description-struct OPTIONAL,
      utran-TDD-Description [5] SI2ter-UTRAN-TDD-Description-struct OPTIONAL,
      a3G-MEASUREMENT-Parameters-Description [6] 
         SI2ter-3G-MEASUREMENT-Parameters-Description-struct OPTIONAL,
      component-8 [7] SEQUENCE {
         a3G-Additional-Measurement-Parameters-Description [0] 
            A3G-Additional-Measurement-Parameters-Description-struct OPTIONAL
      } OPTIONAL
   } OPTIONAL
}

MEASUREMENT-PARAMETERS-Description-Struct ::= SEQUENCE {
   report-type [0] INTEGER (0..1),
   serving-band-reporting [1] INTEGER (0..3)
}

RTD6-Struct ::= SEQUENCE OF INTEGER (0..63)

RTD12-Struct ::= SEQUENCE OF INTEGER (0..4095)

GPRS-Real-Time-Difference-Description-struct ::= SEQUENCE {
   component-1 [0] SEQUENCE {
      ba-Index-Start-RTD [0] INTEGER (0..31) OPTIONAL,
      rtd [1] RTD6-Struct,
      rtd-list [2] SEQUENCE OF RTD6-Struct
   } OPTIONAL,
   component-2 [1] SEQUENCE {
      ba-Index-Start-RTD [0] INTEGER (0..31) OPTIONAL,
      rtd [1] RTD12-Struct,
      rtd-list [2] SEQUENCE OF RTD12-Struct
   } OPTIONAL
}

GPRS-BSIC-Description-struct ::= SEQUENCE {
   ba-Index-Start-BSIC [0] INTEGER (0..31) OPTIONAL,
   bsic [1] INTEGER (0..63),
   number-Remaining-BSIC [2] INTEGER (0..127),
   component-4 [3] SEQUENCE (SIZE (0..127)) OF SEQUENCE {
      frequency-Scrolling [0] INTEGER (0..1),
      bsic [1] INTEGER (0..63)
   }
}

GPRS-REPORT-PRIORITY-Description-struct ::= SEQUENCE {
   number-Cells [0] INTEGER (0..127),
   rep-priority [1] BIT STRING  (SIZE (0..127))
}

GPRS-MEASUREMENT-PARAMETERS-Description-struct ::= SEQUENCE {
   report-type [0] INTEGER (0..1),
   reporting-rate [1] INTEGER (0..1),
   invalid-bsic-reporting [2] INTEGER (0..1),
   multiband-reporting [3] INTEGER (0..3) OPTIONAL,
   serving-band-reporting [4] INTEGER (0..3) OPTIONAL,
   scale-ord [5] INTEGER (0..3),
   component-7 [6] SEQUENCE {
      a900-REPORTING-OFFSET [0] INTEGER (0..7),
      a900-REPORTING-THRESHOLD [1] INTEGER (0..7)
   } OPTIONAL,
   component-8 [7] SEQUENCE {
      a1800-REPORTING-OFFSET [0] INTEGER (0..7),
      a1800-REPORTING-THRESHOLD [1] INTEGER (0..7)
   } OPTIONAL,
   component-9 [8] SEQUENCE {
      a400-REPORTING-OFFSET [0] INTEGER (0..7),
      a400-REPORTING-THRESHOLD [1] INTEGER (0..7)
   } OPTIONAL,
   component-10 [9] SEQUENCE {
      a1900-REPORTING-OFFSET [0] INTEGER (0..7),
      a1900-REPORTING-THRESHOLD [1] INTEGER (0..7)
   } OPTIONAL,
   component-11 [10] SEQUENCE {
      a850-REPORTING-OFFSET [0] INTEGER (0..7),
      a850-REPORTING-THRESHOLD [1] INTEGER (0..7)
   } OPTIONAL
}

NC-Measurement-Parameters-struct ::= SEQUENCE {
   network-control-order [0] INTEGER (0..3),
   component-2 [1] SEQUENCE {
      nc-non-drx-period [0] INTEGER (0..7),
      nc-reporting-period-i [1] INTEGER (0..7),
      nc-reporting-period-t [2] INTEGER (0..7)
   } OPTIONAL
}

CCN-Support-Description-struct ::= SEQUENCE {
   number-Cells [0] INTEGER (0..127),
   ccn-supported [1] BIT STRING  (SIZE (0..127))
}

SI2q-Extension-Information ::= SEQUENCE {
   ccn-Support-Description [0] CCN-Support-Description-struct OPTIONAL
}

Repeated-UTRAN-FDD-Neighbour-Cells-struct ::= SEQUENCE {
   component-1 [0] INTEGER (0) DEFAULT 0,
   fdd-arfcn [1] INTEGER (0..16383),
   fdd-Indic0 [2] INTEGER (0..1),
   nr-of-fdd-cells [3] INTEGER (0..31),
   fdd-CELL-INFORMATION-Field [4] BIT STRING 
}

UTRAN-FDD-Description-struct ::= SEQUENCE {
   bandwidth-FDD [0] INTEGER (0..7) OPTIONAL,
   repeated-UTRAN-FDD-Neighbour-Cells-list [1] SEQUENCE OF 
      Repeated-UTRAN-FDD-Neighbour-Cells-struct
}

Repeated-UTRAN-TDD-Neighbour-Cells-struct ::= SEQUENCE {
   zerobit [0] INTEGER (0) DEFAULT 0,
   tdd-arfcn [1] INTEGER (0..16383),
   tdd-Indic0 [2] INTEGER (0..1),
   nr-of-tdd-cells [3] INTEGER (0..31),
   tdd-CELL-INFORMATION-Field [4] BIT STRING 
}

UTRAN-TDD-Description-struct ::= SEQUENCE {
   bandwidth-TDD [0] INTEGER (0..7) OPTIONAL,
   repeated-UTRAN-TDD-Neighbour-Cells-list [1] SEQUENCE OF 
      Repeated-UTRAN-TDD-Neighbour-Cells-struct
}

A3G-Neighbour-Cell-Description-struct ::= SEQUENCE {
   index-Start-3G [0] INTEGER (0..127) OPTIONAL,
   absolute-Index-Start-EMR [1] INTEGER (0..127) OPTIONAL,
   utran-FDD-Description [2] UTRAN-FDD-Description-struct OPTIONAL,
   utran-TDD-Description [3] UTRAN-TDD-Description-struct OPTIONAL
}

A3G-MEASUREMENT-PARAMETERS-Description-struct ::= SEQUENCE {
   qsearch-I [0] INTEGER (0..15),
   qsearch-C-Initial [1] INTEGER (0..1),
   component-3 [2] SEQUENCE {
      fdd-Qoffset [0] INTEGER (0..15),
      fdd-rep-quant [1] INTEGER (0..1),
      fdd-multirat-reporting [2] INTEGER (0..3),
      fdd-Qmin [3] INTEGER (0..7)
   } OPTIONAL,
   component-4 [3] SEQUENCE {
      tdd-Qoffset [0] INTEGER (0..15),
      tdd-multirat-reporting [1] INTEGER (0..3)
   } OPTIONAL
}

GPRS-3G-MEASUREMENT-PARAMETERS-Description-struct ::= SEQUENCE {
   qsearch-P [0] INTEGER (0..15),
   ignored [1] INTEGER (0..1),
   component-3 [2] SEQUENCE {
      fdd-rep-quant [0] INTEGER (0..1),
      fdd-multirat-reporting [1] INTEGER (0..3)
   } OPTIONAL,
   component-4 [3] SEQUENCE {
      fdd-reporting-offset [0] INTEGER (0..7),
      fdd-reporting-threshold [1] INTEGER (0..7)
   } OPTIONAL,
   tdd-multirat-reporting [4] INTEGER (0..3) OPTIONAL,
   component-6 [5] SEQUENCE {
      tdd-reporting-offset [0] INTEGER (0..7),
      tdd-reporting-threshold [1] INTEGER (0..7)
   } OPTIONAL
}

Serving-Cell-Priority-Parameters-Description-struct ::= SEQUENCE {
   geran-priority [0] INTEGER (0..7),
   thresh-Priority-Search [1] INTEGER (0..15),
   thresh-GSM-low [2] INTEGER (0..15),
   h-prio [3] INTEGER (0..3),
   t-Reselection [4] INTEGER (0..3)
}

Repeated-UTRAN-Priority-Parameters-struct ::= SEQUENCE {
   utran-frequency-index-list [0] SEQUENCE OF INTEGER (0..31),
   utran-priority [1] INTEGER (0..7) OPTIONAL,
   thresh-UTRAN-high [2] INTEGER (0..31),
   thresh-UTRAN-low [3] INTEGER (0..31) OPTIONAL,
   utran-qrxlevmin [4] INTEGER (0..31) OPTIONAL
}

A3G-Priority-Parameters-Description-struct ::= SEQUENCE {
   utran-Start [0] INTEGER (0..1),
   utran-Stop [1] INTEGER (0..1),
   component-3 [2] SEQUENCE {
      default-utran-priority [0] INTEGER (0..7),
      default-thresh-utran [1] INTEGER (0..31),
      default-utran-qrxlevmin [2] INTEGER (0..31)
   } OPTIONAL,
   repeated-UTRAN-Priority-Parameters-list [3] SEQUENCE OF 
      Repeated-UTRAN-Priority-Parameters-struct
}

GPRS-E-UTRAN-Measurement-Parameters-Description-struct ::= SEQUENCE {
   qsearch-P-E-UTRAN [0] INTEGER (0..15),
   e-utran-rep-quant [1] INTEGER (0..1),
   e-utran-multirat-reporting [2] INTEGER (0..3),
   component-4 [3] SEQUENCE {
      e-utran-fdd-reporting-threshold [0] INTEGER (0..7),
      e-utran-fdd-reporting-threshold-2 [1] INTEGER (0..63) OPTIONAL,
      e-utran-fdd-reporting-offset [2] INTEGER (0..7) OPTIONAL
   } OPTIONAL,
   component-5 [4] SEQUENCE {
      e-utran-tdd-reporting-threshold [0] INTEGER (0..7),
      e-utran-tdd-reporting-threshold-2 [1] INTEGER (0..63) OPTIONAL,
      e-utran-tdd-reporting-offset [2] INTEGER (0..7) OPTIONAL
   } OPTIONAL
}

Repeated-E-UTRAN-Neighbour-Cells-struct ::= SEQUENCE {
   component-1 [0] SEQUENCE OF SEQUENCE {
      earfcn [0] INTEGER (0..65535),
      measurement-Bandwidth [1] INTEGER (0..7) OPTIONAL
   },
   e-utran-priority [1] INTEGER (0..7) OPTIONAL,
   thresh-E-UTRAN-high [2] INTEGER (0..31),
   thresh-E-UTRAN-low [3] INTEGER (0..31) OPTIONAL,
   e-utran-qrxlevmin [4] INTEGER (0..31) OPTIONAL
}

Repeated-E-UTRAN-Not-Allowed-Cells-struct ::= SEQUENCE {
   not-Allowed-Cells [0] PCID-Group-IE,
   e-utran-frequency-index-list [1] SEQUENCE OF INTEGER (0..7)
}

Repeated-E-UTRAN-PCID-to-TA-mapping-struct ::= SEQUENCE {
   pcid-to-TA-mapping-list [0] SEQUENCE OF PCID-Group-IE,
   e-utran-frequency-index-list [1] SEQUENCE OF INTEGER (0..7)
}

E-UTRAN-Parameters-Description-struct ::= SEQUENCE {
   e-utran-ccn-active [0] INTEGER (0..1),
   e-UTRAN-Start [1] INTEGER (0..1),
   e-UTRAN-Stop [2] INTEGER (0..1),
   e-UTRAN-Measurement-Parameters-Description [3] 
      E-UTRAN-Measurement-Parameters-Description-struct OPTIONAL,
   gprs-E-UTRAN-Measurement-Parameters-Description [4] 
      GPRS-E-UTRAN-Measurement-Parameters-Description-struct OPTIONAL,
   repeated-E-UTRAN-Neighbour-Cells-list [5] SEQUENCE OF 
      Repeated-E-UTRAN-Neighbour-Cells-struct,
   repeated-E-UTRAN-Not-Allowed-Cells-list [6] SEQUENCE OF 
      Repeated-E-UTRAN-Not-Allowed-Cells-struct,
   repeated-E-UTRAN-PCID-to-TA-mapping-list [7] SEQUENCE OF 
      Repeated-E-UTRAN-PCID-to-TA-mapping-struct
}

Priority-and-E-UTRAN-Parameters-Description-struct ::= SEQUENCE {
   serving-Cell-Priority-Parameters-Description [0] 
      Serving-Cell-Priority-Parameters-Description-struct OPTIONAL,
   a3G-Priority-Parameters-Description [1] 
      A3G-Priority-Parameters-Description-struct OPTIONAL,
   e-UTRAN-Parameters-Description [2] E-UTRAN-Parameters-Description-struct
       OPTIONAL
}

E-UTRAN-CSG-Description-struct ::= SEQUENCE {
   component-1 [0] SEQUENCE OF SEQUENCE {
      csg-pci-split [0] PCID-Group-IE,
      e-utran-frequency-index-list [1] SEQUENCE OF INTEGER (0..7)
   },
   csg-earfcn-list [1] SEQUENCE OF INTEGER (0..65535)
}

UTRAN-CSG-Cells-Reporting-Description-struct ::= SEQUENCE {
   component-1 [0] SEQUENCE {
      utran-csg-fdd-reporting-threshold [0] INTEGER (0..7),
      utran-csg-fdd-reporting-threshold-2 [1] INTEGER (0..63)
   } OPTIONAL,
   utran-csg-tdd-reporting-threshold [1] INTEGER (0..7) OPTIONAL
}

E-UTRAN-CSG-Cells-Reporting-Description-struct ::= SEQUENCE {
   component-1 [0] SEQUENCE {
      e-utran-csg-fdd-reporting-threshold [0] INTEGER (0..7),
      e-utran-csg-fdd-reporting-threshold-2 [1] INTEGER (0..63)
   } OPTIONAL,
   component-2 [1] SEQUENCE {
      e-utran-csg-tdd-reporting-threshold [0] INTEGER (0..7),
      e-utran-csg-fdd-reporting-threshold-2 [1] INTEGER (0..63)
   } OPTIONAL
}

CSG-Cells-Reporting-Description-struct ::= SEQUENCE {
   utran-CSG-Cells-Reporting-Description [0] 
      UTRAN-CSG-Cells-Reporting-Description-struct OPTIONAL,
   e-UTRAN-CSG-Cells-Reporting-Description [1] 
      E-UTRAN-CSG-Cells-Reporting-Description-struct OPTIONAL
}

SI2quater-Rest-Octets ::= SEQUENCE {
   ba-ind [0] INTEGER (0..1),
   a3G-BA-IND [1] INTEGER (0..1),
   mp-change-mark [2] INTEGER (0..1),
   si2quater-INDEX [3] INTEGER (0..15),
   si2quater-COUNT [4] INTEGER (0..15),
   measurement-Parameters-Description [5] 
      MEASUREMENT-PARAMETERS-Description-Struct OPTIONAL,
   gprs-Real-Time-Difference-Description [6] 
      GPRS-Real-Time-Difference-Description-struct OPTIONAL,
   gprs-BSIC-Description [7] GPRS-BSIC-Description-struct OPTIONAL,
   gprs-REPORT-PRIORITY-Description [8] GPRS-REPORT-PRIORITY-Description-struct
       OPTIONAL,
   gprs-MEASUREMENT-Parameters-Description [9] 
      GPRS-MEASUREMENT-PARAMETERS-Description-struct OPTIONAL,
   nc-Measurement-Parameters [10] NC-Measurement-Parameters-struct OPTIONAL,
   component-12 [11] SEQUENCE {
      extension-length [0] INTEGER (0..255),
      si2q-Extension-Information [1] SI2q-Extension-Information
   } OPTIONAL,
   a3G-Neighbour-Cell-Description [12] A3G-Neighbour-Cell-Description-struct
       OPTIONAL,
   a3G-Measurement-Parameters-Description [13] 
      A3G-MEASUREMENT-PARAMETERS-Description-struct OPTIONAL,
   gprs-3G-MEASUREMENT-Parameters-Description [14] 
      GPRS-3G-MEASUREMENT-PARAMETERS-Description-struct OPTIONAL,
   component-16 [15] SEQUENCE {
      a3G-Additional-Measurement-Parameters-Description [0] 
         A3G-Additional-Measurement-Parameters-Description-struct OPTIONAL,
      a3G-ADDITIONAL-MEASUREMENT-Parameters-Description-2 [1] 
         A3G-Additional-Measurement-Parameters-Description-2-struct OPTIONAL,
      component-3 [2] SEQUENCE {
         a3G-CCN-ACTIVE [0] INTEGER (0..1),
         component-2 [1] SEQUENCE {
            component-1 [0] SEQUENCE {
               a700-REPORTING-OFFSET [0] INTEGER (0..7),
               a700-REPORTING-THRESHOLD [1] INTEGER (0..7)
            } OPTIONAL,
            component-2 [1] SEQUENCE {
               a810-REPORTING-OFFSET [0] INTEGER (0..7),
               a810-REPORTING-THRESHOLD [1] INTEGER (0..7)
            } OPTIONAL,
            component-3 [2] SEQUENCE {
               priority-and-E-UTRAN-Parameters-Description [0] 
                  Priority-and-E-UTRAN-Parameters-Description-struct OPTIONAL,
               a3G-CSG-Description [1] A3G-CSG-Description-struct OPTIONAL,
               e-UTRAN-CSG-Description [2] E-UTRAN-CSG-Description-struct
                   OPTIONAL,
               component-4 [3] SEQUENCE {
                  enhanced-Cell-Reselection-Parameters-Description [0] 
                     Enhanced-Cell-Reselection-Parameters-IE OPTIONAL,
                  csg-Cells-Reporting-Description [1] 
                     CSG-Cells-Reporting-Description-struct OPTIONAL,
                  component-3 [2] SEQUENCE {
                     init-pwr-red [0] INTEGER (0..1) OPTIONAL,
                     nc2-CSG-PCCN-permitted [1] INTEGER (0..1)
                  } OPTIONAL
               } OPTIONAL
            } OPTIONAL
         } OPTIONAL
      } OPTIONAL
   } OPTIONAL
}

GPRS-Support-Indicator-struct ::= SEQUENCE {
   component-1 [0] SEQUENCE {
      same-ra-as-serving-cell [0] INTEGER (0..1),
      si13-position [1] INTEGER (0..1)
   } OPTIONAL
}

GSM-Neighbour-Cell-Selection-params-struct ::= SEQUENCE {
   ncell-list-index [0] INTEGER (0..63),
   bsic [1] INTEGER (0..63) OPTIONAL,
   component-3 [2] SEQUENCE {
      cell-bar-access [0] INTEGER (0..1),
      same-la-as-serving-cell [1] INTEGER (0..1),
      component-3 [2] SEQUENCE {
         rxlev-access-min [0] INTEGER (0..63),
         ms-txpwr-max-cch [1] INTEGER (0..31)
      } OPTIONAL,
      component-4 [3] SEQUENCE {
         cbq [0] INTEGER (0..1),
         cell-reselect-offset [1] INTEGER (0..63),
         temporary-offset [2] INTEGER (0..7),
         penalty-time [3] INTEGER (0..31)
      } OPTIONAL,
      power-offset [4] INTEGER (0..3) OPTIONAL,
      gprs-Support-Indicator [5] GPRS-Support-Indicator-struct OPTIONAL
   } OPTIONAL
}

SI2n-Rest-Octets ::= SEQUENCE {
   ba-ind [0] INTEGER (0..1),
   si2n-CHANGE-MARK [1] INTEGER (0..3),
   si2n-INDEX [2] INTEGER (0..15),
   si2n-COUNT [3] INTEGER (0..15),
   gsm-Neighbour-Cell-Selection-parameters [4] SEQUENCE OF 
      GSM-Neighbour-Cell-Selection-params-struct
}

SI3-Rest-Octets-Data ::= SEQUENCE {
   data [0] OCTET STRING
}

Selection-Parameters ::= SEQUENCE {
   cbq [0] INTEGER (0..1),
   cell-reselect-offset [1] INTEGER (0..63),
   temporary-offset [2] INTEGER (0..7),
   penalty-time [3] INTEGER (0..31)
}

Optional-Selection-Parameters ::= SEQUENCE {
   selection-Parameters [0] Selection-Parameters OPTIONAL
}

Optional-Power-Offset ::= SEQUENCE {
   power-Offset [0] INTEGER (0..3) OPTIONAL
}

GPRS-Indicator ::= SEQUENCE {
   ra-colour [0] INTEGER (0..7),
   si13-position [1] INTEGER (0..1)
}

SI4-Rest-Octets-O ::= SEQUENCE {
   optional-Selection-Parameters [0] Optional-Selection-Parameters OPTIONAL,
   optional-Power-Offset [1] Optional-Power-Offset OPTIONAL,
   gprs-Indicator [2] GPRS-Indicator OPTIONAL
}

Break-Indicator ::= LHType

SI4-LSA-Parameters ::= SEQUENCE {
   prio-thr [0] INTEGER (0..7),
   lsa-offset [1] INTEGER (0..7),
   component-3 [2] SEQUENCE {
      mcc [0] INTEGER (0..4095),
      mnc [1] INTEGER (0..4095)
   } OPTIONAL
}

LSA-identity ::= CHOICE {
   lsa-id [0] INTEGER (0..16777215),
   shortLSA-ID [1] INTEGER (0..1023)
}

LSA-ID-information ::= SEQUENCE {
   first [0] EXPLICIT LSA-identity,
   additional [1] SEQUENCE OF LSA-identity
}

SI4-Rest-Octets-S ::= SEQUENCE {
   si4-LSA-Parameters [0] SI4-LSA-Parameters OPTIONAL,
   cell-Identity [1] INTEGER (0..65535) OPTIONAL,
   lsa-ID-information [2] LSA-ID-information OPTIONAL,
   component-4 [3] SEQUENCE {
      cbq3 [0] INTEGER (0..3),
      si13alt-Position [1] INTEGER (0..1) OPTIONAL
   } OPTIONAL
}

SI4-Rest-Octets ::= SEQUENCE {
   si4-Rest-Octets-O [0] SI4-Rest-Octets-O OPTIONAL,
   component-2 [1] EXPLICIT CHOICE {
      break-Indicator [0] Break-Indicator,
      si4-Rest-Octets-S [1] SI4-Rest-Octets-S
   } OPTIONAL
}

Paging-channel-restructuring ::= CHOICE {
   choice-1 [0] NULL,
   choice-2 [1] NULL
}

PCH-and-NCH-info ::= SEQUENCE {
   paging-channel-restructuring [0] EXPLICIT Paging-channel-restructuring,
   nln-sacch [1] INTEGER (0..3),
   call-priority [2] INTEGER (0..7) OPTIONAL,
   nln-status-SACCH [3] INTEGER (0..1)
}

SI6-Rest-Octets ::= SEQUENCE {
   pch-and-NCH-info [0] PCH-and-NCH-info OPTIONAL,
   vbs-VGCS-options [1] INTEGER (0..3) OPTIONAL,
   component-3 [2] SEQUENCE {
      rac [0] INTEGER (0..255),
      max-LAPDm [1] INTEGER (0..7)
   } OPTIONAL,
   band-indicator [3] Band-indicator,
   gprs-ms-txpwr-max-cch [4] INTEGER (0..31) OPTIONAL,
   component-6 [5] SEQUENCE {
      dedicated-mode-mbms-notification-support [0] INTEGER (0..1),
      mnci-support [1] INTEGER (0..1)
   } OPTIONAL,
   component-7 [6] SEQUENCE {
      amr-Config [0] INTEGER (0..15) OPTIONAL
   } OPTIONAL,
   random-bit-stream [7] BIT STRING  OPTIONAL
}

SI7-Rest-Octets-Data ::= OCTET STRING

SI8-Rest-Octets-Data ::= OCTET STRING

Info-type ::= CHOICE {
   info-type-4 [0] INTEGER (0..15),
   info-type-5 [1] INTEGER (0..31),
   info-type-6 [2] INTEGER (0..63)
}

Position ::= SEQUENCE {
   modulus [0] INTEGER (0..15),
   component-1 [1] EXPLICIT CHOICE {
      bcch-type [0] INTEGER (0..1),
      choice-2 [1] SEQUENCE {
         relative-position [0] BIT STRING  (SIZE (1..16)),
         bcch-type [1] INTEGER (0..1)
      }
   }
}

Positions ::= SEQUENCE {
   position [0] Position,
   position2 [1] Position OPTIONAL
}

Scheduling-info ::= SEQUENCE {
   info-type [0] EXPLICIT Info-type,
   positions [1] Positions
}

Scheduling-info-list ::= SEQUENCE {
   scheduling-info [0] Scheduling-info,
   scheduling-info-list [1] SEQUENCE OF Scheduling-info
}

SI9-Rest-Octets ::= SEQUENCE {
   scheduling-info-list [0] Scheduling-info-list OPTIONAL
}

PBCCH-Description-struct ::= SEQUENCE {
   pb [0] INTEGER (0..15),
   tsc [1] INTEGER (0..7),
   tn [2] INTEGER (0..7),
   component-4 [3] EXPLICIT CHOICE {
      bcch [0] NULL,
      arfcn [1] INTEGER (0..1023),
      maio [2] INTEGER (0..63)
   }
}

SI-CHANGE-ALT ::= LHType

SI13-Rest-Octets ::= SEQUENCE {
   component-1 [0] SEQUENCE {
      bcch-change-mark [0] INTEGER (0..7),
      si-change-field [1] INTEGER (0..15),
      component-3 [2] SEQUENCE {
         si13-change-mark [0] INTEGER (0..3),
         gprs-Mobile-Allocation [1] GPRS-Mobile-Allocation-IE
      } OPTIONAL,
      component-4 [3] EXPLICIT CHOICE {
         choice-1 [0] SEQUENCE {
            rac [0] INTEGER (0..255),
            spgc-ccch-sup [1] INTEGER (0..1),
            priority-access-thr [2] INTEGER (0..7),
            network-control-order [3] INTEGER (0..3),
            gprs-Cell-Options [4] GPRS-Cell-Options-IE,
            gprs-Power-Control-Parameters [5] GPRS-Power-Control-Parameters-IE
         },
         choice-2 [1] SEQUENCE {
            psi1-repeat-period [0] INTEGER (0..15),
            pbcch-Description [1] PBCCH-Description-struct
         }
      },
      component-5 [4] SEQUENCE {
         sgsnr [0] INTEGER (0..1),
         component-2 [1] SEQUENCE {
            si-status-ind [0] INTEGER (0..1),
            component-2 [1] SEQUENCE {
               lb-ms-txpwr-max-cch [0] INTEGER (0..31) OPTIONAL,
               si2n-SUPPORT [1] INTEGER (0..3),
               si-change-alt [2] SI-CHANGE-ALT
            } OPTIONAL
         } OPTIONAL
      } OPTIONAL
   } OPTIONAL
}

LSA-Parameters ::= SEQUENCE {
   prio-thr [0] INTEGER (0..7),
   lsa-offset [1] INTEGER (0..7),
   component-3 [2] SEQUENCE {
      mcc [0] INTEGER (0..4095),
      mnc [1] INTEGER (0..4095)
   } OPTIONAL,
   lsa-ID-information [3] LSA-ID-information
}

SI16-Rest-Octets ::= SEQUENCE {
   lsa-Parameters [0] LSA-Parameters OPTIONAL
}

SI17-Rest-Octets ::= SEQUENCE {
   lsa-Parameters [0] LSA-Parameters OPTIONAL
}

LA-Different-struct ::= SEQUENCE {
   cell-reselect-hysterisis [0] INTEGER (0..7) OPTIONAL
}

COMPACT-Cell-Selection-struct ::= SEQUENCE {
   component-1 [0] EXPLICIT CHOICE {
      bcc [0] INTEGER (0..7),
      bsic [1] INTEGER (0..63)
   },
   cell-barred [1] INTEGER (0..1),
   component-3 [2] INTEGER (0) DEFAULT 0,
   la-Different-parameters [3] LA-Different-struct,
   ms-txpwr-max-cch [4] INTEGER (0..31) OPTIONAL,
   rxlev-access-min [5] INTEGER (0..63) OPTIONAL,
   cell-reselect-offset [6] INTEGER (0..63) OPTIONAL,
   component-8 [7] SEQUENCE {
      temporary-offset [0] INTEGER (0..7),
      penalty-time [1] INTEGER (0..31)
   } OPTIONAL,
   time-group [8] INTEGER (0..3) OPTIONAL,
   guar-constant-pwr-blks [9] INTEGER (0..3) OPTIONAL
}

COMPACT-Neighbour-Cell-params-struct ::= SEQUENCE OF SEQUENCE {
   start-frequency [0] INTEGER (0..1023),
   compact-Cell-selection-params [1] COMPACT-Cell-Selection-struct,
   nr-of-remaining-cells [2] INTEGER (0..15),
   freq-diff-length [3] INTEGER (0..7),
   component-5 [4] SEQUENCE (SIZE (0..15)) OF SEQUENCE {
      frequency-diff [0] BIT STRING  (SIZE (1..8)),
      compact-Cell-Selection-struct [1] COMPACT-Cell-Selection-struct
   }
}

SI19-Rest-Octets ::= SEQUENCE {
   si19-change-mark [0] INTEGER (0..3),
   si19-index [1] INTEGER (0..7),
   si19-last [2] INTEGER (0..1),
   compact-Neighbour-Cell-Parameters [3] COMPACT-Neighbour-Cell-params-struct
}

Non-GSM-Message-struct ::= SEQUENCE {
   non-GSM-Protocol-Discriminator [0] INTEGER (0..7),
   nr-of-container-octets [1] INTEGER (0..31),
   component-3 [2] EXPLICIT CHOICE {
      choice-1 [0] NULL,
      choice-2 [1] SEQUENCE {
         container [0] SEQUENCE (SIZE (0..31)) OF INTEGER (0..255),
         non-GSM-Message-struct [1] Non-GSM-Message-struct OPTIONAL
      }
   }
}

SI18-Rest-Octets ::= SEQUENCE {
   si18-change-mark [0] INTEGER (0..3),
   si18-index [1] INTEGER (0..7),
   si18-last [2] INTEGER (0..1),
   spare-bit [3] INTEGER (0..3) DEFAULT 0,
   non-GSM-Message [4] Non-GSM-Message-struct
}

SI14-Rest-Octets ::= SEQUENCE {
   si14-index [0] INTEGER (0..3),
   si14-count [1] INTEGER (0..3),
   dm-change-mark [2] INTEGER (0..15),
   dynamic-ARFCN-MAPPING-Description [3] SEQUENCE OF DYNAMIC-ARFCN-MAPPING
}

SI15-Rest-Octets ::= SEQUENCE {
   si15-index [0] INTEGER (0..3),
   si15-count [1] INTEGER (0..3),
   dm-change-mark [2] INTEGER (0..15),
   dynamic-ARFCN-MAPPING-Description [3] SEQUENCE OF DYNAMIC-ARFCN-MAPPING
}

PBCCH-Description-2-struct ::= SEQUENCE {
   psi1-repeat-period [0] INTEGER (0..15),
   pb [1] INTEGER (0..15),
   tn [2] INTEGER (0..7),
   pbcch-Frequency-Description [3] Frequency-Parameters-IE
}

SI13alt-Rest-Octets ::= SEQUENCE {
   pbcch-Description [0] PBCCH-Description-2-struct
}

Network-Sharing-EAB-Information-struct ::= SEQUENCE {
   component-1 [0] SEQUENCE {
      common-PLMN-PS-EAB-Authorization-Mask [0] INTEGER (0..1023),
      common-PLMN-PS-EAB-Subcategory [1] INTEGER (0..3)
   } OPTIONAL,
   nb-Additional-PLMNs [1] INTEGER (0..3),
   component-3 [2] SEQUENCE (SIZE (1..4)) OF SEQUENCE {
      component-1 [0] SEQUENCE {
         additional-EAB-Authorization-Mask [0] INTEGER (0..1023),
         additional-EAB-Subcategory [1] INTEGER (0..3)
      } OPTIONAL,
      component-2 [1] SEQUENCE {
         component-1 [0] SEQUENCE {
            ps-EAB-Authorization-Mask [0] INTEGER (0..1023),
            ps-EAB-Subcategory [1] INTEGER (0..3)
         } OPTIONAL
      } OPTIONAL
   }
}

SI21-Rest-Octets ::= SEQUENCE {
   si-21-change-mark [0] INTEGER (0..3),
   si-21-index [1] INTEGER (0..7),
   si-21-count [2] INTEGER (0..7),
   component-4 [3] SEQUENCE {
      eab-Authorization-Mask [0] INTEGER (0..1023),
      eab-Subcategory [1] INTEGER (0..3)
   } OPTIONAL,
   component-5 [4] SEQUENCE {
      network-Sharing-EAB-Information [0] 
         Network-Sharing-EAB-Information-struct OPTIONAL
   }
}

Network-Sharing-Information-struct ::= SEQUENCE {
   si23-Indicator [0] INTEGER (0..1),
   common-PLMN-Allowed [1] INTEGER (0..1),
   common-PLMN-PS-ACC [2] INTEGER (0..65535) OPTIONAL,
   nb-Additional-PLMNs [3] INTEGER (0..3),
   component-5 [4] SEQUENCE (SIZE (1..4)) OF SEQUENCE {
      mcc [0] INTEGER (0..4095) OPTIONAL,
      mnc [1] INTEGER (0..4095),
      ncc-Permitted [2] INTEGER (0..255),
      additional-ACC [3] INTEGER (0..65535) OPTIONAL,
      component-5 [4] SEQUENCE {
         ps-acc [0] INTEGER (0..65535) OPTIONAL
      } OPTIONAL
   }
}

SI22-Rest-Octets ::= SEQUENCE {
   si-22-change-mark [0] INTEGER (0..3),
   si-22-index [1] INTEGER (0..7),
   si-22-count [2] INTEGER (0..7),
   network-Sharing-Information [3] Network-Sharing-Information-struct OPTIONAL
}

Repeated-UTRAN-FDD-TDD-Neighbour-Frequency-and-Priority-struct ::= SEQUENCE {
   utran-arfcn-list [0] SEQUENCE OF INTEGER (0..16383),
   utran-priority [1] INTEGER (0..7) OPTIONAL,
   thresh-UTRAN-high [2] INTEGER (0..31),
   thresh-UTRAN-low [3] INTEGER (0..31) OPTIONAL,
   utran-qrxlevmin [4] INTEGER (0..31) OPTIONAL
}

UTRAN-FDD-TDD-Description-struct ::= SEQUENCE {
   bandwidth [0] INTEGER (0..7) OPTIONAL,
   repeated-UTRAN-FDD-TDD-Neighbour-Frequency-and-Priority-list [1] 
      SEQUENCE OF 
      Repeated-UTRAN-FDD-TDD-Neighbour-Frequency-and-Priority-struct
}

Priority-and-UTRAN-Parameters-Description-struct ::= SEQUENCE {
   component-1 [0] SEQUENCE {
      component-1 [0] SEQUENCE {
         default-utran-priority [0] INTEGER (0..7) OPTIONAL,
         default-THRESH-UTRAN-low [1] INTEGER (0..31) OPTIONAL,
         default-utran-qrxlevmin [2] INTEGER (0..31) OPTIONAL
      } OPTIONAL,
      utran-FDD-TDD-Description [1] UTRAN-FDD-TDD-Description-struct OPTIONAL
   } OPTIONAL
}

Repeated-E-UTRAN-Neighbour-Frequency-and-Priority-struct ::= SEQUENCE {
   component-1 [0] SEQUENCE OF SEQUENCE {
      earfcn [0] INTEGER (0..65535),
      measurement-Bandwidth [1] INTEGER (0..7) OPTIONAL
   },
   e-utran-priority [1] INTEGER (0..7) OPTIONAL,
   thresh-E-UTRAN-high [2] INTEGER (0..31),
   thresh-E-UTRAN-low [3] INTEGER (0..31) OPTIONAL,
   e-utran-qrxlevmin [4] INTEGER (0..31) OPTIONAL
}

SI23-Priority-and-E-UTRAN-Parameters-Description-struct ::= SEQUENCE {
   component-1 [0] SEQUENCE {
      component-1 [0] SEQUENCE {
         default-e-utran-priority [0] INTEGER (0..7) OPTIONAL,
         default-THRESH-E-UTRAN-low [1] INTEGER (0..31) OPTIONAL,
         default-e-utran-qrxlevmin [2] INTEGER (0..31) OPTIONAL
      } OPTIONAL,
      repeated-E-UTRAN-Neighbour-Frequency-and-Priority-list [1] SEQUENCE OF 
         Repeated-E-UTRAN-Neighbour-Frequency-and-Priority-struct,
      repeated-E-UTRAN-Not-Allowed-Cells-list [2] SEQUENCE OF 
         Repeated-E-UTRAN-Not-Allowed-Cells-struct,
      repeated-E-UTRAN-PCID-to-TA-mapping-list [3] SEQUENCE OF 
         Repeated-E-UTRAN-PCID-to-TA-mapping-struct,
      enhanced-Cell-Reselection-Parameters-Description [4] 
         Enhanced-Cell-Reselection-Parameters-IE OPTIONAL
   } OPTIONAL
}

IRAT-Cell-Reselection-Information-struct ::= SEQUENCE {
   priority-and-UTRAN-Parameters-Description-for-the-Common-PLMN [0] 
      Priority-and-UTRAN-Parameters-Description-struct,
   priority-and-E-UTRAN-Parameters-Description-for-the-Common-PLMN [1] 
      SI23-Priority-and-E-UTRAN-Parameters-Description-struct,
   nb-Additional-PLMNs [2] INTEGER (0..3),
   component-4 [3] SEQUENCE (SIZE (1..4)) OF SEQUENCE {
      plmn-index [0] INTEGER (0..3),
      priority-and-UTRAN-Parameters-Description [1] 
         Priority-and-UTRAN-Parameters-Description-struct,
      priority-and-E-UTRAN-Parameters-Description [2] 
         SI23-Priority-and-E-UTRAN-Parameters-Description-struct
   }
}

SI23-Rest-Octets ::= SEQUENCE {
   si-23-3g-ba-ind [0] INTEGER (0..1),
   si-23-change-mark [1] INTEGER (0..3),
   si-23-index [2] INTEGER (0..7),
   si-23-count [3] INTEGER (0..7),
   irat-Cell-Reselection-Information [4] 
      IRAT-Cell-Reselection-Information-struct OPTIONAL
}

A3G-Early-Classmark-Sending-Restriction ::= LHType

Early-Classmark-Sending-Control ::= LHType

RR-Cause ::= INTEGER (0..255)

System-Information-2ter-Indicator ::= LHType

Iu-Indicator ::= SEQUENCE {
   si13alt-POSITION [0] INTEGER (0..1)
}

SI2quater-Indicator-struct ::= SEQUENCE {
   si2quater-POSITION [0] INTEGER (0..1)
}

Scheduling-if-and-where ::= SEQUENCE {
   where [0] INTEGER (0..7) OPTIONAL
}

System-Information-21-Indicator ::= SEQUENCE {
   si21-position [0] INTEGER (0..1) OPTIONAL
}

SI3-Rest-Octets ::= SEQUENCE {
   optional-Selection-Parameters [0] Optional-Selection-Parameters,
   optional-Power-Offset [1] Optional-Power-Offset,
   system-Information-2ter-Indicator [2] System-Information-2ter-Indicator,
   early-Classmark-Sending-Control [3] Early-Classmark-Sending-Control,
   scheduling-if-and-where [4] Scheduling-if-and-where,
   gprs-Indicator [5] GPRS-Indicator OPTIONAL,
   a3G-Early-Classmark-Sending-Restriction [6] 
      A3G-Early-Classmark-Sending-Restriction,
   si2quater-Indicator [7] SI2quater-Indicator-struct OPTIONAL,
   iu-Indicator [8] Iu-Indicator OPTIONAL,
   system-Information-21-Indicator [9] System-Information-21-Indicator OPTIONAL
}

SI7-Rest-Octets ::= SEQUENCE {
   si4-Rest-Octets-O [0] SI4-Rest-Octets-O OPTIONAL,
   si4-Rest-Octets-S [1] SI4-Rest-Octets-S
}

SI8-Rest-Octets ::= SEQUENCE {
   si4-Rest-Octets-O [0] SI4-Rest-Octets-O OPTIONAL,
   si4-Rest-Octets-S [1] SI4-Rest-Octets-S
}

Inband-notifications ::= CHOICE {
   choice-1 [0] NULL,
   choice-2 [1] NULL
}

Inband-pagings ::= CHOICE {
   choice-1 [0] NULL,
   choice-2 [1] NULL
}

VBS-VGCS-options ::= SEQUENCE {
   inband-notifications [0] EXPLICIT Inband-notifications,
   inband-pagings [1] EXPLICIT Inband-pagings
}

END
TS44060IES DEFINITIONS AUTOMATIC TAGS ::= BEGIN

-- Productions

PCID-Group-IE ::= SEQUENCE {
   pcid-list [0] SEQUENCE OF INTEGER (0..511),
   pcid-bitmap-group [1] INTEGER (0..63) OPTIONAL,
   component-3 [2] SEQUENCE OF SEQUENCE {
      pcid-Pattern-length [0] INTEGER (0..7),
      pcid-Pattern [1] BIT STRING  (SIZE (1..8)),
      pcid-pattern-sense [2] INTEGER (0..1)
   }
}

PLMN-ID-struct ::= SEQUENCE {
   mcc [0] INTEGER (0..4095),
   mnc [1] INTEGER (0..4095)
}

UTRAN-CSG-Measurement-Report-IE ::= SEQUENCE {
   utran-cgi [0] INTEGER (0..268435455),
   plmn-id [1] PLMN-ID-struct OPTIONAL,
   csg-id [2] INTEGER (0..134217727),
   access-Mode [3] INTEGER (0..1),
   reporting-quantity [4] INTEGER (0..63)
}

PSC-Group-IE ::= SEQUENCE {
   psc-list [0] SEQUENCE OF INTEGER (0..511),
   component-2 [1] SEQUENCE OF SEQUENCE {
      psc-Pattern-length [0] INTEGER (0..7),
      psc-Pattern [1] BIT STRING  (SIZE (1..8)),
      psc-pattern-sense [2] INTEGER (0..1)
   }
}

Extension-Information ::= SEQUENCE {
   component-1 [0] SEQUENCE {
      component-1 [0] SEQUENCE {
         egprs-packet-channel-request [0] INTEGER (0..1),
         bep-period [1] INTEGER (0..15)
      } OPTIONAL,
      pfc-feature-mode [1] INTEGER (0..1),
      dtm-support [2] INTEGER (0..1),
      bss-paging-coordination [3] INTEGER (0..1)
   } OPTIONAL,
   component-2 [1] SEQUENCE {
      ccn-active [0] INTEGER (0..1),
      nw-ext-utbf [1] INTEGER (0..1)
   } OPTIONAL,
   component-3 [2] SEQUENCE {
      multiple-tbf-capability [0] INTEGER (0..1),
      ext-utbf-nodata [1] INTEGER (0..1),
      dtm-enhancements-capability [2] INTEGER (0..1),
      component-4 [3] SEQUENCE {
         dedicated-mode-mbms-notification-support [0] INTEGER (0..1),
         mnci-support [1] INTEGER (0..1)
      } OPTIONAL
   } OPTIONAL,
   reduced-latency-access [3] INTEGER (0..1) OPTIONAL,
   nmo-i-alternate [4] INTEGER (0..1) OPTIONAL
}

GPRS-Cell-Options-IE ::= SEQUENCE {
   nmo [0] INTEGER (0..3),
   t3168 [1] INTEGER (0..7),
   t3192 [2] INTEGER (0..7),
   drx-timer-max [3] INTEGER (0..7),
   access-burst-type [4] INTEGER (0..1),
   control-ack-type [5] INTEGER (0..1),
   bs-cv-max [6] INTEGER (0..15),
   component-8 [7] SEQUENCE {
      pan-dec [0] INTEGER (0..7),
      pan-inc [1] INTEGER (0..7),
      pan-max [2] INTEGER (0..7)
   } OPTIONAL,
   component-9 [8] SEQUENCE {
      extension-Length [0] INTEGER (0..63),
      extension-Information [1] Extension-Information
   } OPTIONAL
}

GPRS-Power-Control-Parameters-IE ::= SEQUENCE {
   alpha [0] INTEGER (0..15),
   t-avg-w [1] INTEGER (0..31),
   t-avg-t [2] INTEGER (0..31),
   pc-meas-chan [3] INTEGER (0..1),
   n-avg-i [4] INTEGER (0..15)
}

Packet-Timing-Advance-IE ::= SEQUENCE {
   timing-advance-value [0] INTEGER (0..63) OPTIONAL,
   component-2 [1] SEQUENCE {
      timing-advance-index [0] INTEGER (0..15),
      timing-advance-timeslot-number [1] INTEGER (0..7)
   } OPTIONAL
}

EGPRS-Modulation-and-Coding-IE ::= INTEGER (0..15)

EGPRS-Window-Size-IE ::= INTEGER (0..31)

EGPRS-Level-IE ::= INTEGER (0..3)

Pulse-Format-Coding-2-struct ::= CHOICE {
   choice-1 [0] SEQUENCE {
      pulse-Format-Bitmap-Length [0] INTEGER (0..127),
      pulse-Format-Bitmap [1] BIT STRING  (SIZE (1..128))
   },
   non-Hopping-Carrier-Pulse-Format [1] EXPLICIT CHOICE {
      wide [0] NULL,
      wide-tight [1] NULL,
      narrow [2] NULL
   }
}

Pulse-Format-IE ::= CHOICE {
   pulse-Format-Coding-1 [0] INTEGER (0..7),
   pulse-Format-Coding-2 [1] EXPLICIT Pulse-Format-Coding-2-struct
}

Power-Control-Parameters-IE ::= SEQUENCE {
   alpha [0] INTEGER (0..15),
   gamma-tn0 [1] INTEGER (0..31) OPTIONAL,
   gamma-tn1 [2] INTEGER (0..31) OPTIONAL,
   gamma-tn2 [3] INTEGER (0..31) OPTIONAL,
   gamma-tn3 [4] INTEGER (0..31) OPTIONAL,
   gamma-tn4 [5] INTEGER (0..31) OPTIONAL,
   gamma-tn5 [6] INTEGER (0..31) OPTIONAL,
   gamma-tn6 [7] INTEGER (0..31) OPTIONAL,
   gamma-tn7 [8] INTEGER (0..31) OPTIONAL
}

Indirect-encoding-struct ::= SEQUENCE {
   maio [0] INTEGER (0..63),
   ma-number [1] INTEGER (0..15),
   component-3 [2] SEQUENCE {
      change-mark-1 [0] INTEGER (0..3),
      change-mark-2 [1] INTEGER (0..3) OPTIONAL
   } OPTIONAL
}

GPRS-Mobile-Allocation-IE ::= SEQUENCE {
   hsn [0] INTEGER (0..63),
   rfl-number-list [1] SEQUENCE OF INTEGER (0..15),
   component-3 [2] EXPLICIT CHOICE {
      choice-1 [0] SEQUENCE {
         ma-length [0] INTEGER (0..63),
         ma-bitmap [1] BIT STRING  (SIZE (1..64))
      },
      choice-2 [1] SEQUENCE OF INTEGER (0..63)
   }
}

Direct-encoding-1-struct ::= SEQUENCE {
   maio [0] INTEGER (0..63),
   gprs-Mobile-Allocation [1] GPRS-Mobile-Allocation-IE
}

Direct-encoding-2-struct ::= SEQUENCE {
   maio [0] INTEGER (0..63),
   hsn [1] INTEGER (0..63),
   length-of-MA-Frequency-List-contents [2] INTEGER (0..15),
   ma-Frequency-List-contents [3] OCTET STRING (SIZE (3..18))
}

Frequency-Parameters-IE ::= SEQUENCE {
   tsc [0] INTEGER (0..7),
   component-2 [1] EXPLICIT CHOICE {
      arfcn [0] INTEGER (0..1023),
      indirect-encoding [1] Indirect-encoding-struct,
      direct-encoding-1 [2] Direct-encoding-1-struct,
      direct-encoding-2 [3] Direct-encoding-2-struct
   }
}

MPRACH-Control-Parameters-IE ::= SEQUENCE {
   acc-contr-class [0] INTEGER (0..65535) OPTIONAL,
   max-retrans [1] INTEGER (0..3) OPTIONAL,
   s [2] INTEGER (0..15),
   tx-int [3] INTEGER (0..15) OPTIONAL,
   persistence-level [4] INTEGER (0..15) OPTIONAL
}

MPRACH-description-IE ::= SEQUENCE {
   frequency-Parameters [0] Frequency-Parameters-IE OPTIONAL,
   mprach-timeslot-number [1] INTEGER (0..7),
   usf [2] INTEGER (0..7),
   mprach-Control-Parameters [3] MPRACH-Control-Parameters-IE OPTIONAL
}

MBMS-p-t-m-channel-description-IE ::= SEQUENCE {
   frequency-Parameters [0] Frequency-Parameters-IE OPTIONAL,
   dl-timeslot-allocation [1] INTEGER (0..255)
}

MBMS-Session-Parameters-List-IE ::= SEQUENCE OF SEQUENCE {
   length-of-MBMS-Bearer-Identity [0] INTEGER (0..7),
   mbms-Bearer-Identity [1] BIT STRING  (SIZE (0..7)),
   estimated-Session-Duration [2] INTEGER (0..255),
   mbms-Radio-Bearer-Starting-Time [3] INTEGER (0..65535) OPTIONAL,
   egprs-Window-Size [4] EGPRS-Window-Size-IE OPTIONAL,
   npm-Transfer-Time [5] INTEGER (0..31) OPTIONAL
}

Channel-Request-Description-IE ::= SEQUENCE {
   peak-throughput-class [0] INTEGER (0..15),
   radio-priority [1] INTEGER (0..3),
   rlc-mode [2] INTEGER (0..1),
   llc-pdu-type [3] INTEGER (0..1),
   rlc-octet-count [4] INTEGER (0..65535)
}

TMGI-IE ::= CHOICE {
   mbms-service-id [0] INTEGER (0..16777215),
   choice-2 [1] SEQUENCE {
      mbms-service-id [0] INTEGER (0..16777215),
      mcc [1] INTEGER (0..4095),
      mnc [2] INTEGER (0..4095)
   }
}

MBMS-Channel-Parameters-IE ::= CHOICE {
   choice-1 [0] SEQUENCE {
      component-1 [0] SEQUENCE {
         mbms-p-t-m-channel-description [0] MBMS-p-t-m-channel-description-IE,
         mbms-Session-Parameters-List [1] MBMS-Session-Parameters-List-IE
      } OPTIONAL
   },
   choice-2 [1] SEQUENCE {
      mprach-description [0] MPRACH-description-IE OPTIONAL
   }
}

MBMS-Session-List-IE ::= SEQUENCE OF SEQUENCE {
   tmgi [0] EXPLICIT TMGI-IE,
   mbms-Session-Identity [1] INTEGER (0..255) OPTIONAL
}

Repeated-E-UTRAN-Enhanced-Cell-Reselection-Parameters-struct ::= SEQUENCE {
   e-utran-frequency-index-list [0] SEQUENCE OF INTEGER (0..7),
   component-2 [1] EXPLICIT CHOICE {
      e-UTRAN-Qmin [0] INTEGER (0..15),
      choice-2 [1] SEQUENCE {
         thresh-E-UTRAN-high-Q [0] INTEGER (0..31),
         thresh-E-UTRAN-low-Q [1] INTEGER (0..31) OPTIONAL,
         e-utran-qqualmin [2] INTEGER (0..15) OPTIONAL,
         e-UTRAN-RSRPmin [3] INTEGER (0..31) OPTIONAL
      }
   }
}

Enhanced-Cell-Reselection-Parameters-IE ::= SEQUENCE OF 
   Repeated-E-UTRAN-Enhanced-Cell-Reselection-Parameters-struct

Global-Packet-Timing-Advance-IE ::= SEQUENCE {
   timing-advance-value [0] INTEGER (0..63) OPTIONAL,
   component-2 [1] SEQUENCE {
      uplink-timing-advance-index [0] INTEGER (0..15),
      uplink-timing-advance-timeslot-number [1] INTEGER (0..7)
   } OPTIONAL,
   component-3 [2] SEQUENCE {
      downlink-timing-advance-index [0] INTEGER (0..15),
      downlink-timing-advance-timeslot-number [1] INTEGER (0..7)
   } OPTIONAL
}

END
TS24007L3 DEFINITIONS AUTOMATIC TAGS ::= BEGIN

-- Productions

-- 11.2.3.1.5 EPS Bearer Identity 
EPSBearerIdentity ::= ENUMERATED { noIdent(0), id5(5), id6(6), id7(7), id8(8), 
   id9(9), id10(10), id11(11), id12(12), id13(13), id14(14), id15(15) }

-- 11.2.3.1 Standard L3 Message Header 
L3HdrOptions ::= CHOICE {
   skipInd [0] INTEGER (0..15),
   --<inline/>
   transId [1] SEQUENCE {
      flag [0] BOOLEAN,
      value [1] INTEGER (0..255)
   },
   epsBearerIdent [2] EPSBearerIdentity,
   secHdr [3] INTEGER (0..15)
}

ProtoDiscr ::= ENUMERATED { gcc(0), bcc(1), epsSessMgmt(2), callCtrl(3), 
   gttp(4), mobMgmt(5), rrMgmt(6), epsMobMgmt(7), gprsMobMgmt(8), sms(9), 
   sessMgmt(10), nonCallSS(11), locnSvcs(12), extPduInd(14), testProc(15) }

SecHdrType ::= ENUMERATED { noSec(0), integProt(1), integProtAndCipher(2), 
   integProtAndSecCtxt(3), integProtAndCipherAndSecCtxt(4), 
   integProtAndPartCipher(5), secHdrForSvcReq(12) }

Header ::= SEQUENCE {
   l3HdrOpts [0] EXPLICIT L3HdrOptions, -- L3 header, octet 1, bits 5 thru 8
   protoDiscr [1] ProtoDiscr,
   msgType [2] INTEGER (0..255)
}

MsgType-MM-CC-SS ::= SEQUENCE {
   sendSeqNum [0] INTEGER (0..3),
   value [1] INTEGER (0..63)
}

SecProtMsgHeader ::= SEQUENCE {
   secHdrType [0] SecHdrType, -- Security header type
   protoDiscr [1] INTEGER (0..15), -- Protocol discriminator
   msgAuthCode [2] INTEGER (0..4294967295), -- Message authentication code (MAC)
   seqNumber [3] INTEGER (0..255) -- Sequence number
}

-- Class definitions

NAS-PROTOCOL-CLASS ::= CLASS {
   &protoDiscr ProtoDiscr,
   &msgType INTEGER (0..255),
   &Value
}


END
TS24008IES DEFINITIONS AUTOMATIC TAGS ::= BEGIN

-- Productions

--<ctype>chararray</ctype>
--<isTBCDString/>
IMSI ::= IA5String (FROM ("0123456789")SIZE (14..15))

--<ctype>chararray</ctype>
--<isTBCDString/>
IMEI ::= IA5String (FROM ("0123456789")SIZE (15))

--<ctype>chararray</ctype>
--<isTBCDString/>
IMEISV ::= IA5String (FROM ("0123456789")SIZE (16))

TBCDString ::= IA5String (FROM ("0123456789#*abc"))

-- BCDString3 should be configured as <ctype>chararray</ctype>
TBCDString3 ::= TBCDString (SIZE (3))

-- MCC/MNC pair
MCCMNCPair ::= SEQUENCE {
   mcc [0] TBCDString3,
   mnc [1] TBCDString3
}

-- 10.5.1.4 - Mobile Identity 
MobileIdentity-TMGI ::= SEQUENCE {
   mbmsSessIdInd [0] BOOLEAN,
   mccMncInd [1] BOOLEAN,
   mbmsServiceID [2] OCTET STRING (SIZE (3)),
   mcc-mnc [3] MCCMNCPair,
   mbmsSessionID [4] INTEGER (0..255)
}

MobileIdentity ::= CHOICE {
   imsi [0] IMSI,
   imei [1] IMEI,
   imeisv [2] IMEISV,
   tmsi [3] OCTET STRING (SIZE (4)),
   tmgi [4] MobileIdentity-TMGI,
   /* When none is used, the identity digits shall be all zeros (as per 
      24.008. 10.5.1.4.)  The value of the none field indicates the length
      of the MobileIdentity IE, which is required to be 1 or 3.
   */
   none [5] INTEGER (1 | 3)
}

-- 10.5.5.15 - Routing area identification 
RoutingAreaIdent ::= SEQUENCE {
   mcc-mnc [0] MCCMNCPair,
   lac [1] INTEGER (0..65535),
   rac [2] INTEGER (0..255)
}

-- 10.5.6.13 - Temporary Mobile Group Identity (TMGI) 
TMGI ::= SEQUENCE {
   mbmsServiceID [0] OCTET STRING (SIZE (3)),
   mcc-mnc [1] MCCMNCPair
}

-- 10.5.1.5 - Mobile Station Classmark 1 
MobileStationClassmark1 ::= SEQUENCE {
   spare [0] BOOLEAN,
   revLevel [1] INTEGER (0..3), /* 0 = GSM phase 1, 
                               1 = GSM phase 2, 
                               2 = R99 or later */
   esInd [2] BOOLEAN,
   a5-1-alg [3] BOOLEAN,
   rfPowerCap [4] INTEGER (0..7)
}

-- 10.5.1.6 - Mobile Station Classmark 2 
MobileStationClassmark2 ::= SEQUENCE {
   -- octet 3 
   cm1 [0] MobileStationClassmark1 OPTIONAL,
   -- octet 4 
   octet4 [1] SEQUENCE {
      spare [0] BOOLEAN,
      psCapability [1] BOOLEAN,
      ssScreeningInd [2] INTEGER (0..3),
      smCapability [3] BOOLEAN,
      vbsNotifRecept [4] BOOLEAN,
      vgcsNotifRecept [5] BOOLEAN,
      fcFreqCap [6] BOOLEAN
   } OPTIONAL,
   -- octet 5 
   octet5 [2] SEQUENCE {
      cm3 [0] BOOLEAN,
      spare [1] BOOLEAN,
      lcsvaCap [2] BOOLEAN,
      ucs2Treatment [3] BOOLEAN,
      soLSA [4] BOOLEAN,
      cmsp [5] BOOLEAN,
      a5-3-alg [6] BOOLEAN,
      a5-2-alg [7] BOOLEAN
   } OPTIONAL
}

-- This type enumerates all of the valid bit patterns expressed in the CSN
-- for the multibandSupported eleemnt in MobileStationClassmark3
MBSEnum ::= ENUMERATED { mbs0(0), mbs1(1), mbs2(2), mbs4(4), mbs5(5), mbs6(6) }
   

/*< A5 bits > ::= 
	< A5/7 : bit > < A5/6 : bit > < A5/5 : bit > < A5/4 : bit >  ;*/
A5Bits ::= SEQUENCE {
   a5-7 [0] BOOLEAN,
   a5-6 [1] BOOLEAN,
   a5-5 [2] BOOLEAN,
   a5-4 [3] BOOLEAN
}

-- MultibandSupported is defined as a separate type to allow a custom NAS
-- encode and decode function to be defined to support the following CSN:
/*{	< Multiband supported : { 000 } >
		< A5 bits > 
|	< Multiband supported : { 101 | 110 } > 
		< A5 bits >
		< Associated Radio Capability 2 : bit(4) >
		< Associated Radio Capability 1 : bit(4) >
|	< Multiband supported : { 001 | 010 | 100 } > 
		< A5 bits >
		< spare bit >(4)
		< Associated Radio Capability 1 : bit(4) > }*/
MultibandSupported ::= SEQUENCE {
   supported [0] MBSEnum,
   a5bits [1] A5Bits,
   assocRadioCap2 [2] INTEGER (0..15),
   assocRadioCap1 [3] INTEGER (0..15)
}

/*<R Support>::=
	< R-GSM band Associated Radio Capability : bit(3) > ;*/
RSupport ::= INTEGER (0..7)

/*< HSCSD Multi Slot Capability > ::=
	< HSCSD Multi Slot Class : bit(5) >  ;*/
HSCSDMultiSlotCap ::= INTEGER (0..31)

-- 10.5.1.7 - Mobile Station Classmark 3 
/*< MS Measurement capability > ::=
	< SMS_VALUE : bit (4) >
	< SM_VALUE : bit (4) > ;*/
MSMeasurementCap ::= SEQUENCE {
   smsValue [0] INTEGER (0..15),
   smValue [1] INTEGER (0..15)
}

-- Name has to begin with some uppercase letter.
Type8PSKStruct ::= SEQUENCE {
   modulationCap [0] BOOLEAN,
   rfPowerCap1 [1] INTEGER (0..3) OPTIONAL,
   rfPowerCap2 [2] INTEGER (0..3) OPTIONAL
}

/*{       < T-GSM 400 Bands Supported : { 01 | 10 | 11 } >
	< T-GSM 400 Associated Radio Capability: bit(4) > }*/
GSM400Struct ::= SEQUENCE {
   bandsSupported [0] ENUMERATED { band1(1), band2(2), band3(3) },
   assocRadioCap [1] INTEGER (0..15)
}

/*{ 	< DTM GPRS Multi Slot Class : bit(2) >
	< Single Slot DTM : bit >
	{0 | 1 < DTM EGPRS Multi Slot Class : bit(2) > } } */
DTMGPRSStruct ::= SEQUENCE {
   dtmGPRSMultiSlotClass [0] INTEGER (0..3),
   singleSlotDTM [1] BOOLEAN,
   dtmEGPRSMultiSlotClass [2] INTEGER (0..3) OPTIONAL
}

GERANIuModeCap ::= SEQUENCE {
   --<is3GLength bitFieldSize="4" units="bits"/>
   length [0] INTEGER (0..15), -- number of bits, may be padded
   floIuCap [1] BOOLEAN,
   --<inline/>
   --<length fixed-size="0"/>
   spareBits [2] BIT STRING  (SIZE (0..14))
}

--<aligned/>
MobileStationClassmark3 ::= SEQUENCE {
   --<is3GLength/>
   length [0] INTEGER (0..32),
   spare [1] BOOLEAN,
   multiband [2] MultibandSupported,
   /*	{ 0 | 1 < R Support > }
	{ 0 | 1 < HSCSD Multi Slot Capability > }
	< UCS2 treatment: bit >
	< Extended Measurement Capability : bit >
	{ 0 | 1 < MS measurement capability > }
	{ 0 | 1 < MS Positioning Method Capability > }
	{ 0 | 1 < ECSD Multi Slot Capability > }
	{ 0 | 1 < 8-PSK Struct > }
   */
   rSupport [3] RSupport OPTIONAL,
   hscsdMultiSlotCap [4] HSCSDMultiSlotCap OPTIONAL,
   ucs2Treatment [5] BOOLEAN,
   extMeasurementCap [6] BOOLEAN,
   msMeasurementCap [7] MSMeasurementCap OPTIONAL,
   msPositioningMethodCap [8] INTEGER (0..31) OPTIONAL,
   ecsdMultiSlotCap [9] INTEGER (0..31) OPTIONAL,
   an-8-PSKStruct [10] Type8PSKStruct OPTIONAL,
   /*	{ 0 | 1 < GSM 400 Struct >
   */
   gsm400Struct [11] GSM400Struct OPTIONAL,
   /*	{ 0 | 1 <GSM 850 Associated Radio Capability : bit(4) > }
	{ 0 | 1 <GSM 1900 Associated Radio Capability : bit(4) > }
	< UMTS FDD Radio Access Technology Capability : bit >
	< UMTS 3.84 Mcps TDD Radio Access Technology Capability : bit >
	< CDMA 2000 Radio Access Technology Capability : bit >
   */
   gsm850AssocRadioCap [12] INTEGER (0..15) OPTIONAL,
   gsm1900AssocRadioCap [13] INTEGER (0..15) OPTIONAL,
   umtsFDDRadioAccessTechCap [14] BOOLEAN,
   umts384McpsTDDRadioAccessTechCap [15] BOOLEAN,
   cdma2000RadioAccessTechCap [16] BOOLEAN,
   /*	{ 0 | 1	< DTM GPRS Struct > }
   */
   dtmGPRSStruct [17] DTMGPRSStruct OPTIONAL,
   -- Release 4 starts here
   /*	{ 0 | 1 < Single Band Support > }
	{ 0 | 1 <GSM 750 Associated Radio Capability : bit(4)>}
	< UMTS 1.28 Mcps TDD Radio Access Technology Capability : bit >
	< GERAN Feature Package 1 : bit >
   */
   singleBandSupport [18] INTEGER (0..15) OPTIONAL,
   gsm750AssocRadioCap [19] INTEGER (0..15) OPTIONAL,
   umts1-28McpsTDDRadioAccessTechCap [20] BOOLEAN,
   geranFeaturePackage1 [21] BOOLEAN,
   /*	{ 0 | 1 < Extended DTM GPRS Multi Slot Class : bit(2) >
		< Extended DTM EGPRS Multi Slot Class : bit(2) > }
   */
   extDtmGPRSStruct [22] SEQUENCE {
      extDtmGPRSMultiSlotClass [0] INTEGER (0..3),
      extDtmEGPRSMultiSlotClass [1] INTEGER (0..3)
   } OPTIONAL,
   -- Release 5 starts here
   /*	{ 0 | 1 < High Multislot Capability : bit(2) > }
	{ 0 | 1 < GERAN Iu Mode Capabilities > }
	< GERAN Feature Package 2 : bit >
	< GMSK Multislot Power Profile : bit (2) >
	< 8-PSK Multislot Power Profile : bit (2) >
   */
   highMultislotCap [23] INTEGER (0..3) OPTIONAL,
   geranIuModeCap [24] GERANIuModeCap OPTIONAL,
   geranFeaturePackage2 [25] BOOLEAN,
   gmskMultislotPowerProfile [26] INTEGER (0..3),
   multislotPowerProfile8PSK [27] INTEGER (0..3),
   -- Release 6 starts here
   /*	{ 0 | 1 < GSM 400 Struct >
   */
   tgsm400Struct [28] GSM400Struct OPTIONAL,
   /* 
        0	The value '1' was allocated in an earlier version of the 
                protocol and shall not be used 
   */
   zerobit [29] BOOLEAN DEFAULT FALSE,
   /*	< Downlink Advanced Receiver Performance : bit (2)>
	< DTM Enhancements Capability : bit >
   */
   downlinkAdvancedRcvrPerf [30] INTEGER (0..3),
   dtmEnhancementsCap [31] BOOLEAN,
   /*	{ 0 | 1	< DTM GPRS High Multi Slot Class : bit(3) >
		< Offset required : bit>
		{ 0 | 1 < DTM EGPRS High Multi Slot Class : bit(3) > } }
   */
   dtmGPRSStruct2 [32] SEQUENCE {
      dtmGPRSHighMultiSlotClass [0] INTEGER (0..7),
      offsetRequired [1] BOOLEAN,
      dtmEGPRSHighMultiSlotClass [2] INTEGER (0..7) OPTIONAL
   } OPTIONAL,
   /*	< Repeated ACCH Capability : bit >
   */
   repeatedACCHCap [33] BOOLEAN,
   /*        -- Release 7 starts here
	{ 0 | 1 <GSM 710 Associated Radio Capability : bit(4)>}
	{ 0 | 1 <T-GSM 810 Associated Radio Capability : bit(4)>}
	< Ciphering Mode Setting Capability : bit >
	< Additional Positioning Capabilities : bit >
   */
   gsm710AssocRadioCap [34] INTEGER (0..15) OPTIONAL,
   tgsm810AssocRadioCap [35] INTEGER (0..15) OPTIONAL,
   cipheringModeSettingCap [36] BOOLEAN,
   additionalPositioningCap [37] BOOLEAN,
   /*       	-- Release 8 starts here
	< E-UTRA FDD support : bit >
	< E-UTRA TDD support : bit >
	< E-UTRA Measurement and Reporting support : bit >
	< Priority-based reselection support : bit >
   */
   e-UTRA-FDD-support [38] BOOLEAN,
   e-UTRA-TDD-support [39] BOOLEAN,
   e-UTRA-MeasAndReportSupport [40] BOOLEAN,
   priorityBasedReselectionSupport [41] BOOLEAN,
   ...,
   [[ 9:
      uTRA-CSG-Cells-Reporting [42] BOOLEAN,
      vAMOS-Level [43] INTEGER (0..3)
   ]],
   [[ 10:
      tighterCapability [44] INTEGER (0..3),
      selCiphOf-DL-SACCH [45] BOOLEAN
   ]],
   [[ 11:
      csToPsFromGeranToUtra [46] INTEGER (0..3),
      csToPsFromGeranToEUtra [47] INTEGER (0..3),
      geranNetShareSupport [48] BOOLEAN,
      eutraWideRsrqSupport [49] BOOLEAN
   ]],
   [[ 12:
      erBandSupport [50] BOOLEAN,
      utraMultFreqBandSupport [51] BOOLEAN,
      eutraMultFreqBandSupport [52] BOOLEAN,
      extTscSetCapSupport [53] BOOLEAN,
      extEarfcnValRange [54] BOOLEAN
   ]],
   spareBits [55] BIT STRING 
}

-- 10.5.1.9 - Descriptive group or broadcast call reference 
DescrGroupOrBcastCallRef ::= SEQUENCE {
   --binary code is a 27 bit value
   bc [0] INTEGER (0..134217727),
   sf [1] BOOLEAN,
   af [2] BOOLEAN,
   callPriority [3] INTEGER (0..7),
   cipheringInformation [4] INTEGER (0..15),
   spare [5] INTEGER (0..15) DEFAULT 0 -- should be set to 0
}

-- 10.5.3.14 - Additional update parameters 
AddnUpdateParams ::= SEQUENCE {
   spare [0] BOOLEAN DEFAULT FALSE,
   drvcc [1] BOOLEAN, -- added in v15.3
   cmso [2] BOOLEAN,
   cmst [3] BOOLEAN
}

-- 10.5.1.2 - Ciphering Key Sequence Number 
-- 3-bit number.  Valid values are 0 thru 6.  7 is no key available 
CiphKeySeqNum ::= SEQUENCE {
   spare [0] BOOLEAN,
   value [1] INTEGER (0..7)
}

-- Common types
-- 10.5.1.1 - Cell Identity 
CellIdentityValue ::= INTEGER (0..65535)

-- 10.5.1.3 - Location Area Identification 
LocAreaIdent ::= SEQUENCE {
   mcc-mnc [0] MCCMNCPair,
   lac [1] INTEGER (0..65535)
}

--<isGSMString/>
GSMString ::= PrintableString

-- 10.5.1.10 - Group Cipher Key Number 
GroupCipherKeyNumber ::= INTEGER (0..15)

-- 10.5.1.12 - Core Network System Information (UMTS only) 
-- 10.5.1.12.1 - CN Common GSM-MAP NAS system information 
CNCommonGSM-MAPNASSystemInformation ::= INTEGER (0..65535)

-- 10.5.3.1 - Authentication parameter RAND 
AuthParamRAND ::= OCTET STRING (SIZE (16))

-- 10.5.3.2 - Authentication Response parameter 
AuthRespParam ::= OCTET STRING (SIZE (4))

/* 10.5.3.2.1 - 
   Authentication Response Parameter (extension)
   (UMTS authentication challenge only) */
AuthRespParamExt ::= OCTET STRING (SIZE (1..12))

-- 10.5.3.3 - CM service type 
CMServiceType ::= ENUMERATED { mobOrigCallEstab(1), emerCallEstab(2), sms(4), 
   suplSvcActv(8), voiceGrpCallEstab(9), voiceBcastCallEstab(10), 
   locationSvcs(11) }

-- 10.5.3.6 - Reject cause 
RejectCauseValue ::= ENUMERATED { imsiUnkInHLR(2), illegalMS(3), 
   imsiUnkInVLR(4), imeiNotAcc(5), illegalME(6), plmnNotAllow(11), 
   locNotAllow(12), roamNotAllow(13), noCellsInLoc(15), networkFail(17), 
   macFail(20), synchFail(21), congestion(22), gsmAuthUnaccept(23), 
   csgNotAuth(25), svcOptNotSupp(32), notSubscribed(33), outOfOrder(34), 
   callNotIdent(38), semIncorrectMsg(95), invMandInfo(96), msgTypeNotExist(97)
   , msgTypeNotCompat(98), ieNotExist(99), condIEErr(100), msgNotCompat(101), 
   protocolErr(111), rejectCauseValueMAX(255) }

-- 10.5.3.7 - Follow-on Proceed: no value; IEI only 
-- 10.5.3.8 - Time Zone 
TimeZone ::= INTEGER (0..255)

-- 10.5.3.10 - CTS permission: no value; IEI only 
-- 10.5.3.11 - LSA Identifier 
LSAIdentifier ::= OCTET STRING (SIZE (0 | 3))

-- 10.5.4.1 - Extensions of codesets: informative only 
-- 10.5.4.2 - Locking shift procedure 
LockingShiftCodesetID ::= INTEGER (0..7)

-- 10.5.4.3 - Non-locking shift procedure 
NonLockingShiftCodesetID ::= INTEGER (0..7)

InfoXferCap ::= ENUMERATED { speech(0), digital(1), audio(2), fax(3), 
   otherITC(5), reserved(7) }

-- 10.5.4.6 - Call state 
CodingStandard ::= ENUMERATED { q931(0), rsvdForIntl(1), national(2), 
   stdDefForGSMPLMS(3) }

-- 10.5.4.11 - Cause 
Location ::= ENUMERATED { user(0), prvNWServLclUser(1), pubNWServLclUser(2), 
   transit(3), pubNWServRemUser(4), prvNWServRemUser(5), intlNetwork(7), 
   netBeyondIntworkPt(10) }

-- 10.5.4.11a CLIR suppression: IEI only
-- 10.5.4.11b CLIR invocation: IEI only
-- 10.5.4.12 - Congestion level 
CongestionLevel ::= INTEGER (0..15)

-- 10.5.4.9 - Calling party BCD number 
CallingPartyBCDNumber ::= SEQUENCE {
   --<is3GLength/>
   length [0] INTEGER (0..255),
   --<first3GExtElem/>
   octet3 [1] SEQUENCE {
      typeOfNumber [0] INTEGER (0..7),
      numberingPlanID [1] INTEGER (0..15)
   },
   --<last3GExtElem/>
   octet3a [2] SEQUENCE {
      presentationIndicator [0] INTEGER (0..3),
      spare [1] INTEGER (0..7) DEFAULT 0,
      screeningIndicator [2] INTEGER (0..3)
   } OPTIONAL,
   --<length fixed-size="0"/>
   number [3] TBCDString
}

-- 10.5.4.13 - Connected number 
ConnectedNumber ::= CallingPartyBCDNumber

-- 10.5.4.8 - Called party subaddress 
PartySubaddress ::= SEQUENCE {
   --<is3GLength/>
   length [0] INTEGER (0..255),
   --<first3GExtElem/>
   --<last3GExtElem/>
   octet3 [1] SEQUENCE {
      typeOfSubaddr [0] INTEGER (0..7),
      oddEvenIndicator [1] BOOLEAN,
      spare [2] INTEGER (0..7) DEFAULT 0
   } OPTIONAL,
   --<length fixed-size="0"/>
   subaddrInfo [2] OCTET STRING (SIZE (0..20))
}

-- 10.5.4.14 - Connected subaddress 
ConnectedSubaddress ::= PartySubaddress

-- 10.5.4.15 - Facility 
Facility ::= OCTET STRING

-- 10.5.4.18 - Low layer compatibility 
LowLayerCompatibility ::= OCTET STRING (SIZE (0..16))

-- 10.5.4.21b - Redirecting party BCD number 
RedirectingPartyBCDNumber ::= CallingPartyBCDNumber

-- 10.5.4.21c - Redirecting party subaddress 
RedirectingPartySubaddress ::= ConnectedSubaddress

-- 10.5.4.22 - Repeat indicator 
RepeatIndicator ::= INTEGER (0..15)

-- 10.5.4.22a - Reverse call setup direction: IEI only 
-- 10.5.4.22b - SETUP Container $(CCBS)$ 
Setup-Container ::= OCTET STRING

-- 10.5.4.23 - Signal 
Signal ::= INTEGER (0..255)

-- 10.5.4.24 - SS Version Indicator 
SSVersionIndicator ::= OCTET STRING

-- 10.5.3.4 - Identity type 
IdentityTypeValue ::= SEQUENCE {
   spare [0] BOOLEAN DEFAULT FALSE,
   typeOfIdent [1] ENUMERATED { imsi(1), imei(2), imeisv(3), tmsi(4), p-tmsi(5)
       }
}

-- 10.5.5.9 - Identity type 2 
IdentityType2Value ::= IdentityTypeValue

-- < DLMC Capability struct > ::=
--	{ 0 | 1	< DLMC - Non-contiguous intra-band reception : bit(2) >
-- 			< DLMC - Inter-band reception : bit(1) > }
--	< DLMC - Maximum Bandwidth : bit(2) >
--	< DLMC - Maximum Number of Downlink Timeslots : bit(6) >
--	< DLMC - Maximum Number of Downlink Carriers : bit(3) > ;
DLMCNonContigIntraBandRecep ::= ENUMERATED { nonContigIntraBandRecepNotSupp(0)
   , band-EGSM-GSM850(1), band-DCS1800-PCS1900(2), 
   band-EGSM-GSM850-DCS1800-PCS1900(3) }

-- 10.5.5.14 - GMM cause 
GMMCauseValue ::= INTEGER (0..255)

-- 10.5.5.19 - A&C reference number 
AC-Reference-Number ::= INTEGER (0..15)

-- 10.5.5.24 - Inter RAT information container 
InterRATInfoContainer ::= OCTET STRING (SIZE (1..248))

-- 10.5.5.26 - UE network capability 
UENetCapability ::= OCTET STRING (SIZE (2..5))

-- 10.5.5.27 - E-UTRAN inter RAT information container 
E-UTRANInterRATInfoContainer ::= OCTET STRING -- (SIZE(1..255))


-- 10.5.5.33 - Message authentication code 
MsgAuthCode ::= OCTET STRING

-- 10.5.5.35 - DCN-ID 
DcnID ::= OCTET STRING (SIZE (2))

-- 10.5.6.1 - Access point name 
--<ctype>chararray</ctype>
--<cDecFuncFname>TS24008IESDec_AccessPointName.c</cDecFuncFname>
--<cEncFuncFname>TS24008IESEnc_AccessPointName.c</cEncFuncFname>
AccessPointName ::= IA5String (SIZE (1..100))

-- 10.5.6.6 - SM cause 
SMCauseValue ::= INTEGER (0..255)

-- 10.5.6.6A SM cause 2
SMCause2Value ::= SMCauseValue

-- 10.5.6.15 - MBMS protocol configuration options 
MBMS-PCO ::= OCTET STRING

-- 10.5.6.16 - Enhanced network service access point identifier 
EnhancedNSAPIValue ::= INTEGER (0..255)

-- 10.5.6.18 - Session management notification indicator 
SM-NotificationIndicator ::= OCTET STRING (SIZE (1))

-- 10.5.6.19 - Connectivity type 
ConnectivityType ::= INTEGER (0..15)

-- 10.5.6.21 - NBIFOM container 
NBIFOMContainer ::= OCTET STRING

-- 10.5.7.2 - Radio priority 
RadioPriorityValue ::= ENUMERATED { priorityLevel1(1), priorityLevel2(2), 
   priorityLevel3(3), priorityLevel4(4), radioPriorityValueMAX(15) }

-- 10.5.7.5 - Radio priority 2 
RadioPriorityValue2 ::= RadioPriorityValue

-- 10.5.7.6 - MBMS context status 
MBMSContextStatus ::= OCTET STRING (SIZE (0..16))

-- 10.5.1.10a - PD and SAPI $(CCBS)$ 
PDAndSAPI ::= SEQUENCE {
   spare [0] INTEGER (0..3) DEFAULT 0, -- should be set to 0
   sapi [1] INTEGER (0..3),
   pd [2] INTEGER (0..15)
}

-- 10.5.1.11 - Priority Level 
PriorityLevel ::= SEQUENCE {
   spare [0] BOOLEAN,
   callPriority [1] INTEGER (0..7)
}

-- 10.5.1.12.2 - CS domain specific system information 
CSDomainSpecificSystemInformation ::= SEQUENCE {
   t3212 [0] INTEGER (0..255),
   spare [1] INTEGER (0..127) DEFAULT 0, -- should be set to 0
   att [2] BOOLEAN
}

-- 10.5.1.12.3 - PS domain specific system information 
PSDomainSpecificSystemInformation ::= SEQUENCE {
   rac [0] INTEGER (0..255),
   spare [1] INTEGER (0..63) DEFAULT 0, -- should be set to 0
   nmo1 [2] BOOLEAN,
   nmo [3] BOOLEAN
}

-- 10.5.1.13 - PLMN list 
PLMNList ::= SEQUENCE (SIZE (1..15)) OF MCCMNCPair

-- 10.5.1.14 - NAS container for PS HO 
NASContainerForPSHO ::= SEQUENCE {
   spare1 [0] INTEGER (0..7) DEFAULT 0, -- should be set to 0
   xid [1] BOOLEAN,
   spare2 [2] BOOLEAN DEFAULT FALSE,
   typeCiphAlgorithm [3] INTEGER (0..7),
   valueIOV-UI [4] INTEGER (0..4294967295)
}

-- 10.5.1.15 - MS Network Feature Support 
MSNetFeatureSupport ::= SEQUENCE {
   spare [0] INTEGER (0..7) DEFAULT 0,
   extPeriodTimer [1] BOOLEAN
}

/* 10.5.3.1.1 - 
	Authentication Parameter AUTN (UMTS and EPS authentication challenge) */
AuthParamAUTN ::= SEQUENCE {
   --<is3GLength/>
   length [0] INTEGER (0..255) DEFAULT 16, -- should be set to 16
   autn [1] OCTET STRING (SIZE (16))
}

/* 10.5.3.2.2 - 
   Authentication Failure parameter (UMTS and EPS authentication challenge) */
AuthFailureParam ::= SEQUENCE {
   --<is3GLength/>
   length [0] INTEGER (0..255) DEFAULT 14, -- should be set to 14
   param [1] OCTET STRING (SIZE (14))
}

-- 10.5.3.5 - Location updating type 
LocationUpdatingType ::= SEQUENCE {
   for [0] BOOLEAN, -- Follow-on request pending
   spare [1] BOOLEAN DEFAULT FALSE,
   lut [2] ENUMERATED { normLocUpdate(0), periodicUpdate(1), imsiAttach(2), 
      reserved(3) }
}

-- 10.5.3.5a - Network Name 
NetworkName ::= SEQUENCE {
   --<is3GLength/>
   length [0] INTEGER (0..255),
   ext [1] BOOLEAN DEFAULT TRUE,
   codingScheme [2] ENUMERATED { callBcastData(0), ucs2(1), codingSchemeMAX(7)
       },
   addCI [3] BOOLEAN,
   numSpareBitsInLastOct [4] INTEGER (0..7),
   --<inline/>
   textString [5] EXPLICIT CHOICE {
      --<selector element="codingScheme" value="0"/>
      --<length fixed-size="0" unusedBits="@numSpareBitsInLastOct"/>
      callBcastData [0] GSMString,
      --<selector element="codingScheme" value="1"/>
      ucs2 [1] BMPString
   }
}

-- 10.5.3.9 - Time Zone and Time 
TimeZoneAndTime ::= SEQUENCE {
   year [0] INTEGER (0..255),
   month [1] INTEGER (0..255),
   day [2] INTEGER (0..255),
   hour [3] INTEGER (0..255),
   minute [4] INTEGER (0..255),
   second [5] INTEGER (0..255),
   timezone [6] INTEGER (0..255)
}

-- 10.5.3.12 - Daylight Saving Time 
DaylightSavingTime ::= SEQUENCE {
   --<is3GLength/>
   length [0] INTEGER (1),
   spare [1] INTEGER (0..63) DEFAULT 0, -- should be set to 0
   dst [2] ENUMERATED { dstNoAdjust(0), dstPlus1(1), dstPlus2(2), 
      dstReserved(3) }
}

-- 10.5.3.13 - Emergency Number List 
/* If the emergency number contains an odd number of digits, 
   bits 5 to 8 of the last octet of the respective emergency 
   number (catValueOne or catValueTwo)
   shall be filled with an end mark coded as "1111". */
EmergencyNumber ::= SEQUENCE {
   --<is3GLength/>
   length [0] INTEGER (0..255),
   spare [1] INTEGER (0..7) DEFAULT 0,
   catValue [2] INTEGER (0..31),
   -- digits is string of valid TBCD numbers (0-9, #, *, a, b, c)
   --<length fixed-size="0"/>
   digits [3] TBCDString
}

-- Configured the following to use an array
EmergencyNumberList ::= SEQUENCE {
   --<is3GLength/>
   length [0] INTEGER (0..255),
   --<is3GVarLenList lengthElem="length"/>
   --<storage>array</storage>
   numbers [1] SEQUENCE (SIZE (1..10)) OF EmergencyNumber
}

-- 10.5.3.16 - MM Timer 
MMTimer ::= SEQUENCE {
   --<is3GLength/>
   length [0] INTEGER (1),
   value [1] INTEGER (0..255)
}

-- 10.5.4.4 - Auxiliary states 
AuxiliaryStates ::= SEQUENCE {
   ext [0] BOOLEAN DEFAULT TRUE,
   spare [1] INTEGER (0..7) DEFAULT 0,
   holdAuxState [2] INTEGER (0..3),
   multiPartyAuxState [3] INTEGER (0..3)
}

BearerCapOctet3 ::= SEQUENCE {
   radioChannelRequirement [0] INTEGER (0..3), -- 2 bits; always 1 
   nonstandardCoding [1] BOOLEAN, -- 0 - GSM 
   packetXferMode [2] BOOLEAN, -- 0 - circuit mode 
   infoXferCap [3] InfoXferCap -- 3 bits 
}

BearerCapOctet4 ::= SEQUENCE {
   compression [0] BOOLEAN,
   structure [1] INTEGER (0..3),
   fullDuplexMode [2] BOOLEAN,
   configuration [3] BOOLEAN,
   nirr [4] BOOLEAN,
   establishment [5] BOOLEAN
}

BearerCapOctet5 ::= SEQUENCE {
   accessIdentity [0] INTEGER (0..3), -- 2 bits; always 0 
   rateAdaption [1] INTEGER (0..3), -- 2 bits 
   signallingAccessProtocol [2] INTEGER (0..7) -- 3 bits; always 1 - I.440/450 
}

BearerCapOctet5a ::= SEQUENCE {
   -- 2 bits; always 0 - restricted digital information 
   otherITC [0] INTEGER (0..3),
   otherRateAdaption [1] INTEGER (0..3), -- 2 bits 
   spare [2] INTEGER (0..7) DEFAULT 0
}

BearerCapOctet6 ::= SEQUENCE {
   layer1Identity [0] INTEGER (0..3), -- 2 bits; always 1 - octet identifier 
   userInfoLayer1Protocol [1] INTEGER (0..15), -- 4 bits; always 0 - default 
   asynchronous [2] BOOLEAN -- 0 - synchronous 
}

BearerCapOctet6a ::= SEQUENCE {
   twoStopBits [0] BOOLEAN, -- 0 - one stop bit 
   negotiation [1] BOOLEAN, -- always 0 
   data8bits [2] BOOLEAN, -- 0 - 7 bits 
   userRate [3] INTEGER (0..15) -- 4 bits 
}

BearerCapOctet6b ::= SEQUENCE {
   intermediateRate [0] INTEGER (0..3), -- 2 bits 
   nicOnTX [1] BOOLEAN,
   nicOnRX [2] BOOLEAN,
   parity [3] INTEGER (0..7) -- 3 bits 
}

BearerCapOctet6c ::= SEQUENCE {
   connectionElement [0] INTEGER (0..3), -- 2 bits 
   modemType [1] INTEGER (0..31) -- 5 bits 
}

BearerCapOctet6d ::= SEQUENCE {
   otherModemType [0] INTEGER (0..3), -- 2 bits 
   fixedNetworkUserRate [1] INTEGER (0..31) -- 5 bits 
}

BearerCapOctet6e ::= SEQUENCE {
   acceptableChannelCodings [0] INTEGER (0..15), -- 4 bits; always 0 
   maximumNumberOfTrafficChannels [1] INTEGER (0..7) -- 3 bits; always 0 
}

BearerCapOctet6f ::= SEQUENCE {
   uimi [0] INTEGER (0..7), -- 3 bits 
   wantedAirInterfaceUserRate [1] INTEGER (0..15) -- 4 bits; always 0 
}

BearerCapOctet6g ::= SEQUENCE {
   acceptableChannelCodingsExtended [0] INTEGER (0..7), -- 3 bits; always 0 
   asymmetryIndication [1] INTEGER (0..3), -- 2 bits; always 0 
   spare [2] INTEGER (0..3) DEFAULT 0
}

BearerCapOctet7 ::= SEQUENCE {
   layer2Identity [0] INTEGER (0..3), -- 2 bits; always 2 - octet identifier 
   userInformationLayer2Protocol [1] INTEGER (0..31) -- 5 bits 
}

-- 10.5.4.4a - Backup bearer capability 
BackupBearerCapability ::= SEQUENCE {
   --<is3GLength/>
   length [0] INTEGER (0..255),
   --<first3GExtElem/>
   --<last3GExtElem/>
   octet3 [1] BearerCapOctet3,
   --<first3GExtElem/>
   --<last3GExtElem/>
   octet4 [2] BearerCapOctet4 OPTIONAL,
   --<first3GExtElem/>
   octet5 [3] BearerCapOctet5 OPTIONAL,
   --<last3GExtElem/>   
   octet5a [4] BearerCapOctet5a OPTIONAL,
   --<first3GExtElem/>
   octet6 [5] BearerCapOctet6 OPTIONAL,
   octet6a [6] BearerCapOctet6a OPTIONAL,
   octet6b [7] BearerCapOctet6b OPTIONAL,
   octet6c [8] BearerCapOctet6c OPTIONAL,
   octet6d [9] BearerCapOctet6d OPTIONAL,
   octet6e [10] BearerCapOctet6e OPTIONAL,
   octet6f [11] BearerCapOctet6f OPTIONAL,
   --<last3GExtElem/>
   octet6g [12] BearerCapOctet6g OPTIONAL,
   --<first3GExtElem/>
   --<last3GExtElem/>   
   octet7 [13] BearerCapOctet7 OPTIONAL
}

BearerCapOctet3b ::= SEQUENCE {
   coding [0] BOOLEAN,
   spare [1] INTEGER (0..3) DEFAULT 0,
   speechVersion [2] INTEGER (0..15)
}

BearerCapOctet5b ::= SEQUENCE {
   rateAdaptionHeader [0] BOOLEAN,
   multipleFrameEstablishment [1] BOOLEAN,
   protocolSensitiveMode [2] BOOLEAN,
   fullProtocolNegotiation [3] BOOLEAN,
   assignorOnly [4] BOOLEAN,
   uiNegotiation [5] BOOLEAN,
   spare [6] BOOLEAN DEFAULT FALSE
}

--<is3GExtList pre-eol="1"/>
BearerCapOctet3bList ::= SEQUENCE OF BearerCapOctet3b

BearerCapOctet3a ::= SEQUENCE {
   coding [0] BOOLEAN,
   ctm [1] BOOLEAN,
   spare [2] BOOLEAN DEFAULT FALSE,
   speechVersion [3] INTEGER (0..15) -- 4 bits 
}

-- 10.5.4.5 - Bearer capability 
BearerCapability ::= SEQUENCE {
   --<is3GLength/>
   length [0] INTEGER (0..255),
   --<first3GExtElem/>
   octet3 [1] BearerCapOctet3,
   octet3a [2] BearerCapOctet3a OPTIONAL,
   --<last3GExtElem/>
   octet3b [3] BearerCapOctet3bList,
   --<first3GExtElem/>
   --<last3GExtElem/>
   octet4 [4] BearerCapOctet4 OPTIONAL,
   --<first3GExtElem/>
   octet5 [5] BearerCapOctet5 OPTIONAL,
   octet5a [6] BearerCapOctet5a OPTIONAL,
   --<last3GExtElem/>
   octet5b [7] BearerCapOctet5b OPTIONAL,
   --<first3GExtElem/>
   octet6 [8] BearerCapOctet6 OPTIONAL,
   octet6a [9] BearerCapOctet6a OPTIONAL,
   octet6b [10] BearerCapOctet6b OPTIONAL,
   octet6c [11] BearerCapOctet6c OPTIONAL,
   octet6d [12] BearerCapOctet6d OPTIONAL,
   octet6e [13] BearerCapOctet6e OPTIONAL,
   octet6f [14] BearerCapOctet6f OPTIONAL,
   --<last3GExtElem/>
   octet6g [15] BearerCapOctet6g OPTIONAL,
   --<first3GExtElem/>
   --<last3GExtElem/>   
   octet7 [16] BearerCapOctet7 OPTIONAL
}

-- 10.5.4.5a - Call Control Capabilities 
CallControlCapabilities ::= SEQUENCE {
   --<is3GLength/>
   length [0] INTEGER (0..255) DEFAULT 2,
   maxNumSupportedBearers [1] INTEGER (0..15),
   mcat [2] BOOLEAN,
   enicm [3] BOOLEAN,
   pcp [4] BOOLEAN,
   dtmf [5] BOOLEAN,
   spare [6] INTEGER (0..15) DEFAULT 0,
   maxNumSpeechBearers [7] INTEGER (0..15)
}

CallState ::= SEQUENCE {
   codingStandard [0] CodingStandard,
   callStateValue [1] INTEGER (0..63)
}

-- 10.5.4.7 - Called party BCD number 
CalledPartyBCDNumber ::= SEQUENCE {
   --<is3GLength/>
   length [0] INTEGER (0..255),
   --<first3GExtElem/>
   --<last3GExtElem/>
   octet3 [1] SEQUENCE {
      typeOfNumber [0] INTEGER (0..7),
      numberingPlanID [1] INTEGER (0..15)
   },
   --<length fixed-size="0"/>
   number [2] TBCDString
}

-- Custom encode/decode function is used to handle condition of recommendation
Cause ::= SEQUENCE {
   --<is3GLength/>
   length [0] INTEGER (0..255),
   --<first3GExtElem/>
   octet3 [1] SEQUENCE {
      codingStandard [0] CodingStandard,
      spare [1] BOOLEAN DEFAULT FALSE,
      location [2] Location
   },
   --<last3GExtElem/>
   recommendation [2] INTEGER (0..127) OPTIONAL,
   --<first3GExtElem/>
   --<last3GExtElem/>
   causeValue [3] INTEGER (0..127),
   --<inline/>
   --<length fixed-size="0"/>
   diagnostics [4] OCTET STRING (SIZE (0..32))
}

-- 10.5.4.16 - High layer compatibility 
HighLayerCompatibility ::= SEQUENCE {
   --<is3GLength/>
   length [0] INTEGER (0..255),
   --<first3GExtElem/>
   --<last3GExtElem/>
   --<noPresentBit/>
   octet3 [1] SEQUENCE {
      codingStandard [0] CodingStandard,
      interpretation [1] INTEGER (0..7),
      presentMethOfProtoProf [2] INTEGER (0..3)
   } OPTIONAL,
   --<first3GExtElem/>
   --<noPresentBit/>
   highLayerCharacteristicsID [2] INTEGER (0..127) OPTIONAL,
   --<last3GExtElem/>
   extHighLayerCharacteristicsID [3] INTEGER (0..127) OPTIONAL
}

-- 10.5.4.17 - Keypad facility 
KeypadFacilityInfo ::= SEQUENCE {
   spare [0] BOOLEAN DEFAULT FALSE,
   value [1] INTEGER (0..127)
}

-- 10.5.4.19 - More data: IEI only 
-- 10.5.4.20 - Notification indicator 
NotificationIndicator ::= SEQUENCE {
   ext [0] BOOLEAN DEFAULT TRUE,
   value [1] INTEGER (0..127)
}

-- 10.5.4.21 - Progress indicator 
ProgressIndicator ::= SEQUENCE {
   --<is3GLength/>
   length [0] INTEGER (0..255) DEFAULT 2,
   --<first3GExtElem/>
   --<last3GExtElem/>
   octet3 [1] SEQUENCE {
      codingStandard [0] CodingStandard,
      spare [1] BOOLEAN DEFAULT FALSE,
      location [2] INTEGER (0..15)
   },
   --<first3GExtElem/>
   --<last3GExtElem/>
   description [2] INTEGER (0..127)
}

-- 10.5.4.21a Recall type $(CCBS)$
RecallType ::= SEQUENCE {
   spare [0] INTEGER (0..31) DEFAULT 0,
   value [1] INTEGER (0..7)
}

-- 10.5.4.25 - User-user 
UserUser ::= SEQUENCE {
   --<is3GLength/>
   length [0] INTEGER (1..129),
   uupd [1] INTEGER (0..255), -- User-user protocol discriminator 
   uuInfo [2] OCTET STRING -- User-user info 
}

-- 10.5.4.26 - Alerting Pattern $(NIA)$ 
AlertingPattern ::= SEQUENCE {
   --<is3GLength/>
   length [0] INTEGER (1),
   spare [1] INTEGER (0..15) DEFAULT 0,
   value [2] INTEGER (0..15)
}

-- 10.5.4.27 - Allowed actions $(CCBS)$ 
AllowedActions ::= SEQUENCE {
   --<is3GLength/>
   length [0] INTEGER (1),
   ccbs-activation [1] BOOLEAN,
   spare [2] INTEGER (0..127) DEFAULT 0
}

-- 10.5.4.28 - Stream Identifier 
StreamIdentifierValue ::= SEQUENCE {
   --<is3GLength/>
   length [0] INTEGER (1),
   value [1] INTEGER (0..255)
}

-- 10.5.4.29 - Network Call Control Capabilities 
NetCallCtrlCaps ::= SEQUENCE {
   --<is3GLength/>
   length [0] INTEGER (1),
   spare [1] INTEGER (0..127) DEFAULT 0,
   mcs [2] BOOLEAN
}

-- 10.5.4.30 - Cause of No CLI 
CauseOfNoCLI ::= SEQUENCE {
   --<is3GLength/>
   length [0] INTEGER (1),
   value [1] INTEGER (0..255)
}

-- 10.5.4.32 - Supported codec list 
SupportedCodec ::= SEQUENCE {
   sysID [0] INTEGER (0..255),
   codecBitmap [1] OCTET STRING (SIZE (1..2))
}

SupportedCodecList ::= SEQUENCE {
   --<is3GLength/>
   length [0] INTEGER (3..253),
   --<is3GVarLenList lengthElem="length"/>
   --<storage>array</storage>
   codecs [1] SEQUENCE (SIZE (1..83)) OF SupportedCodec
}

-- 10.5.4.33 Service category 
ServiceCategoryValue ::= SEQUENCE {
   spare [0] BOOLEAN DEFAULT FALSE,
   value [1] INTEGER (0..127)
}

-- 10.5.4.34 - Redial: IEI only 
-- 10.5.4.35 - Network-initiated Service Upgrade indicator: IEI only 
-- 10.5.5.0 - Additional update type 
AddnUpdateType ::= SEQUENCE {
   spare [0] INTEGER (0..7),
   autv [1] BOOLEAN
}

-- 10.5.5.1 - Attach result 
AttachResult ::= SEQUENCE {
   fop [0] BOOLEAN,
   resultOfAttach [1] INTEGER (0..7)
}

-- 10.5.5.2 - Attach type 
AttachType ::= SEQUENCE {
   for [0] BOOLEAN,
   typeOfAttach [1] INTEGER (0..7)
}

-- 10.5.5.3 - Ciphering algorithm 
CipheringAlgorithmType ::= SEQUENCE {
   spare [0] BOOLEAN DEFAULT FALSE,
   value [1] INTEGER (0..7)
}

-- 10.5.5.3a - Integrity algorithm 
IntegrityAlgorithmType ::= SEQUENCE {
   spare [0] BOOLEAN DEFAULT FALSE,
   value [1] INTEGER (0..7)
}

-- 10.5.5.4 - TMSI status 
TMSIStatus ::= SEQUENCE {
   spare [0] INTEGER (0..7) DEFAULT 0,
   flag [1] BOOLEAN
}

-- 10.5.5.5 - Detach type 
DetachType ::= SEQUENCE {
   powerOff [0] BOOLEAN,
   detachTypeValue [1] INTEGER (0..7)
}

-- 10.5.5.6 - DRX parameter 
DRXParameter ::= SEQUENCE {
   splitPGCycleCode [0] INTEGER (0..255),
   lenCoefAndValue [1] INTEGER (0..15),
   splitOnCCCH [2] BOOLEAN,
   nonDRXTimer [3] INTEGER (0..7)
}

-- 10.5.5.7 - Force to standby 
ForceToStandbyValue ::= SEQUENCE {
   spare [0] BOOLEAN DEFAULT FALSE,
   value [1] INTEGER (0..7)
}

-- 10.5.5.8 - P-TMSI signature 
P-TMSISignature ::= SEQUENCE {
   value [0] OCTET STRING (SIZE (3))
}

-- 10.5.5.8a - P-TMSI signature 2 
P-TMSISignature2 ::= SEQUENCE {
   --<is3GLength/>
   length [0] INTEGER (3) DEFAULT 3,
   value [1] OCTET STRING (SIZE (3))
}

-- 10.5.5.10 - IMEISV request 
IMEISVRequest ::= SEQUENCE {
   spare [0] BOOLEAN DEFAULT FALSE,
   value [1] INTEGER (0..7)
}

-- 10.5.5.11 - Receive N-PDU Numbers list 
ReceiveNPDUNumber ::= SEQUENCE {
   nsapi [0] INTEGER (1..15),
   numberValue [1] INTEGER (0..255)
}

--<aligned/>
ReceiveNPDUNumberList ::= SEQUENCE {
   --<is3GLength/>
   length [0] INTEGER (2..255),
   --<is3GVarLenList lengthElem="length"/>
   --<cDecSrcFname>TS24008IESDec_ReceiveNPDUNumber.c</cDecSrcFname>
   receiveNPDUNumber [1] SEQUENCE (SIZE (1..MAX)) OF ReceiveNPDUNumber
}

-- 10.5.5.12 - MS network capability 
--<aligned/>
MSNetworkCapability ::= SEQUENCE {
   --<is3GLength/>
   length [0] INTEGER (0..8),
   --<noPresentBit/>
   --<inline/>
   octet1 [1] SEQUENCE {
      gea1 [0] BOOLEAN,
      smCapDeicatedChan [1] BOOLEAN,
      smCapGPRSChan [2] BOOLEAN,
      ucs2Support [3] BOOLEAN,
      ssScreeningInd [4] INTEGER (0..3),
      soLSACap [5] BOOLEAN,
      revisionLevelInd [6] BOOLEAN
   } OPTIONAL,
   --<noPresentBit/>
   --<inline/>
   octet2 [2] SEQUENCE {
      pfcFeatureMode [0] BOOLEAN,
      extendedGEA [1] INTEGER (0..63),
      lcsVACap [2] BOOLEAN
   } OPTIONAL,
   --<noPresentBit/>
   --<inline/>
   octet3 [3] SEQUENCE {
      psInterRATHOToUTRANIuModeCap [0] BOOLEAN,
      psInterRATHOToEUTRANS1ModeCap [1] BOOLEAN,
      emmCombinedProcCap [2] BOOLEAN,
      isrSupport [3] BOOLEAN,
      srvccToGERAN-UTRANCap [4] BOOLEAN,
      epcCap [5] BOOLEAN,
      -- added in release 9
      nfCapability [6] BOOLEAN,
      -- added in release 11
      geranNetShareCap [7] BOOLEAN
   } OPTIONAL,
   --<noPresentBit/>
   --<inline/>
   octet4 [4] SEQUENCE {
      userPlaneIntegProtSupp [0] BOOLEAN,
      gia-4 [1] BOOLEAN,
      gia-5 [2] BOOLEAN,
      gia-6 [3] BOOLEAN,
      gia-7 [4] BOOLEAN,
      epcoIeIndicator [5] BOOLEAN,
      restrictUseEnhancedCovCap [6] BOOLEAN,
      dualConnEutraNRCap [7] BOOLEAN
   } OPTIONAL,
   -- spare bits used to pad out length > 4
   spareBits [5] BIT STRING 
}

-- 10.5.5.12a - MS Radio Access capability 
/* GMSK Multislot Power Profile (2 bit field)
   8-PSK Multislot Power Profile (2 bit field)
   For detailed definitions, see the Mobile Station Classmark 3 IE.*/
MultislotCapability ::= SEQUENCE {
   hscsdMultiSlotClass [0] INTEGER (0..31) OPTIONAL,
   gprsMSC [1] SEQUENCE {
      gprsMultiSlotClass [0] INTEGER (0..31),
      extGPRSDynAllocCap [1] BOOLEAN
   } OPTIONAL,
   value-SMS-SM [2] MSMeasurementCap OPTIONAL,
   ecsdMultiSlotClass [3] INTEGER (0..31) OPTIONAL,
   egprsMSC [4] SEQUENCE {
      egprsMultiSlotClass [0] INTEGER (0..31),
      extEGPRSDynAllocCap [1] BOOLEAN
   } OPTIONAL,
   /*	{ 0 | 1	< DTM GPRS Struct > }
   */
   dtmGPRSStruct [5] DTMGPRSStruct OPTIONAL
}

/*< Enhanced Flexible Timeslot Assignment struct > ::=
	{ 0 | 1 	< Alternative EFTA Multislot Class : bit(4) > 
			< EFTA Multislot Capability Reduction for 
                          Downlink Dual Carrier: bit (3) > };*/
EnhanFlexTimeSlotAssnStruct ::= SEQUENCE {
   alt-EFTA-MultislotClass [0] INTEGER (0..15),
   eFTA-Multislot-Cap-Reduct [1] INTEGER (0..7)
}

/*< Additional access technologies struct > ::=
	< Access Technology Type : bit (4) >
	< GMSK Power Class : bit (3) >
	< 8PSK Power Class : bit (2) > ;*/
AddAccessTechStruct ::= SEQUENCE {
   accessTechType [0] INTEGER (0..15),
   powerClass-GMSK [1] INTEGER (0..7),
   powerClass-8PSK [2] INTEGER (0..3)
}

--<is3GExtList post-eol="0"/>
AddAccessTechStructList ::= SEQUENCE OF AddAccessTechStruct

AdditionalAccessTech ::= SEQUENCE {
   --<is3GLength bitFieldSize="7" units="bits"/>
   length [0] INTEGER (0..127),
   content [1] AddAccessTechStructList,
   spareBits [2] BIT STRING 
}

DLMCCapability ::= SEQUENCE {
   --<inline/>
   dlmc [0] SEQUENCE {
      nonContigIntraBandRecep [0] DLMCNonContigIntraBandRecep,
      interBandRecep [1] BOOLEAN
   } OPTIONAL,
   maxBandwidth [1] ENUMERATED { bw5MHz(0), bw10MHz(1), bw15MHz(2), bw20MHz(3)
       },
   maxNumDLTimeSlots [2] INTEGER (0..63),
   maxNumDLCarriers [3] INTEGER (0..7) -- (n + 1) * 2
}

/*< Access capabilities struct > ::=
	< Length : bit (7) > -- length in bits of Content and spare bits
	<Access capabilities : <Content>> 
	<spare bits>** ; -- expands to the indicated length
			  -- may be used for future enhancements*/
AccessCapability ::= SEQUENCE {
   --<is3GLength bitFieldSize="7" units="bits"/>
   length [0] INTEGER (0..127),
   -- Content
   rfPowerCap [1] INTEGER (0..7),
   --<inline/>
   a5Bits [2] SEQUENCE {
      a5-1 [0] BOOLEAN,
      a5-2 [1] BOOLEAN,
      a5-3 [2] BOOLEAN,
      a5-4 [3] BOOLEAN,
      a5-5 [4] BOOLEAN,
      a5-6 [5] BOOLEAN,
      a5-7 [6] BOOLEAN
   } OPTIONAL,
   esInd [3] BOOLEAN,
   ps [4] BOOLEAN,
   vgcs [5] BOOLEAN,
   vbs [6] BOOLEAN,
   multislotCap [7] MultislotCapability OPTIONAL,
   powerCap8PSK [8] INTEGER (0..3) OPTIONAL,
   compactIMC [9] BOOLEAN,
   revisionLevelInd [10] BOOLEAN,
   umts-FDD-RATechCap [11] BOOLEAN,
   umts-384-Mcps-TDD-RA-TechCap [12] BOOLEAN,
   cdma-2000-RA-TechCap [13] BOOLEAN,
   ...,
   [[ 4:
      umts-128-Mcps-TDD-RA-TechCap [14] BOOLEAN,
      geranFeaturePackage1 [15] BOOLEAN,
      extGPRSMSC [16] SEQUENCE {
         extDtmGPRSMultiSlotClass [0] INTEGER (0..3),
         extDtmEGPRSMultiSlotClass [1] INTEGER (0..3)
      } OPTIONAL,
      moduleBasedMSCSupp [17] BOOLEAN
   ]],
   [[ 5:
      highMultislotCap [18] INTEGER (0..3) OPTIONAL,
      geranIuModeCap [19] GERANIuModeCap OPTIONAL,
      multislotPowerProfile-GMSK [20] INTEGER (0..3),
      multislotPowerProfile-8PSK [21] INTEGER (0..3)
   ]],
   [[ 6:
      multipleTBFCap [22] BOOLEAN,
      downlinkAdvRecPerf [23] INTEGER (0..3),
      extendedRMCMSCap [24] BOOLEAN,
      dtmEnhancementsCap [25] BOOLEAN,
      dtmGPRSHighMSC [26] SEQUENCE {
         dtmGPRSHighMultiSlotClass [0] INTEGER (0..7),
         dtmEGPRSHighMultiSlotClass [1] INTEGER (0..7) OPTIONAL
      } OPTIONAL,
      psHandoverCap [27] BOOLEAN
   ]],
   [[ 7:
      dtmHandoverCap [28] BOOLEAN,
      downlinkDualCarrierCap [29] SEQUENCE {
         mscReductForDownlinkDualCarrier [0] INTEGER (0..3),
         downlinkDualCarrierForDtmCap [1] BOOLEAN
      } OPTIONAL,
      flexibleTimeslotAssign [30] BOOLEAN,
      gan-PS-HandoverCap [31] BOOLEAN,
      rlcNonPersistentMode [32] BOOLEAN,
      reducedLatencyCap [33] BOOLEAN,
      uplinkEGPRS2 [34] INTEGER (0..3),
      downlinkEGPRS2 [35] INTEGER (0..3)
   ]],
   [[ 8:
      e-UTRA-FDD-Supp [36] BOOLEAN,
      e-UTRA-TDD-Supp [37] BOOLEAN,
      gERANToEUTRATransferMode [38] INTEGER (0..3),
      priBasedReselectionSupp [39] BOOLEAN
   ]],
   [[ 9:
      enhanFlexTimeSlotAssn [40] EnhanFlexTimeSlotAssnStruct OPTIONAL,
      upLayerPDUStartCapRLCUMInd [41] BOOLEAN,
      emstCapability [42] BOOLEAN,
      mttiCapability [43] BOOLEAN,
      utraCSGCellsReporting [44] BOOLEAN,
      e-utraCSGCellsReporting [45] BOOLEAN
   ]],
   [[ 10:
      dtrCapability [46] BOOLEAN,
      emsrCapability [47] BOOLEAN,
      fast-DL-Freq-Sw-Cap [48] BOOLEAN,
      tighterCapability [49] BOOLEAN
   ]],
   [[ 11:
      fanrCapability [50] BOOLEAN,
      ipaCapability [51] BOOLEAN,
      geranNetShareSupp [52] BOOLEAN,
      eUTRA-WB-RSRQ-MeasSupp [53] BOOLEAN
   ]],
   [[ 12:
      uTRA-MultFreqBandIndSupp [54] BOOLEAN,
      e-UTRA-MultFreqBandIndSupp [55] BOOLEAN,
      dlmcCap [56] DLMCCapability OPTIONAL,
      extTSCSetCapSupp [57] BOOLEAN,
      extEARFCNValRange [58] BOOLEAN
   ]],
   [[ 13:
      ec-pchMonSupp [59] ENUMERATED { pchSupported(0), ecPchSupported(1), 
         pchAndEcPchSupported(2), ec-pchMonReserved(3) }
   ]],
   [[ 14:
      msSyncAccuracy [60] INTEGER (0..15) OPTIONAL,
      ecULCoverageEnhanceSupp [61] BOOLEAN
   ]],
   [[ 15:
      mtaAccessSecuritySupp [62] BOOLEAN,
      ecPagingIndChanMonitorSupp [63] BOOLEAN
   ]],
   spareBits [64] BIT STRING 
}

MSRACapValuePartStruct ::= SEQUENCE {
   accessTechType [0] INTEGER (0..15),
   --<inline/>
   accessCapOrTech [1] EXPLICIT CHOICE {
      accessCapability [0] AccessCapability,
      --<selector element="accessTechType" value="15"/>
      additionalAccessTech [1] AdditionalAccessTech
   }
}

--<aligned/>
MSRadioAccessCapability ::= SEQUENCE {
   --<is3GLength/>
   length [0] INTEGER (0..50),
   firstRec [1] MSRACapValuePartStruct,
   --<inline/>
   --<is3GExtList post-eol="0"/>
   additionalRecs [2] SEQUENCE OF MSRACapValuePartStruct
}

-- 10.5.5.15a Routing area identification 2
RoutingAreaIdent2 ::= SEQUENCE {
   --<is3GLength/>
   length [0] INTEGER (6),
   value [1] RoutingAreaIdent
}

-- 10.5.5.17 - Update result 
UpdateResult ::= SEQUENCE {
   fop [0] BOOLEAN,
   value [1] INTEGER (0..7)
}

-- 10.5.5.18 - Update type 
UpdateType ::= SEQUENCE {
   for [0] BOOLEAN,
   value [1] INTEGER (0..7)
}

-- 10.5.5.20 - Service type 
ServiceType ::= SEQUENCE {
   spare [0] BOOLEAN DEFAULT FALSE,
   value [1] INTEGER (0..7)
}

-- 10.5.5.21 - Cell Notification: IEI only 
-- 10.5.5.22 - PS LCS Capability 
PS-LCSCapbility ::= SEQUENCE {
   --<is3GLength/>
   length [0] INTEGER (2),
   mta-E [1] BOOLEAN,
   mta-R [2] BOOLEAN,
   apc [3] BOOLEAN,
   otd-A [4] BOOLEAN,
   otd-B [5] BOOLEAN,
   gps-A [6] BOOLEAN,
   gps-B [7] BOOLEAN,
   gps-C [8] BOOLEAN,
   spare [9] INTEGER (0..63) DEFAULT 0,
   motd [10] BOOLEAN,
   mta-A [11] BOOLEAN
}

-- 10.5.5.23 - Network feature support 
NetFeatureSupp ::= SEQUENCE {
   lcs-molr [0] BOOLEAN,
   mbms [1] BOOLEAN,
   imsVoPS [2] BOOLEAN,
   emcBS [3] BOOLEAN
}

-- 10.5.5.23A - Additional network feature support 
AddnNetFeatureSupport ::= SEQUENCE {
   --<is3GLength/>
   length [0] INTEGER (1),
   spare [1] INTEGER (0..31) DEFAULT 0,
   epco [2] BOOLEAN, -- added in/before v15.3
   restrictEC [3] BOOLEAN, -- added in/before v15.3
   gprs-sms [4] BOOLEAN
}

-- 10.5.5.25 - Requested MS information 
RequestedMSInfo ::= SEQUENCE {
   i-RAT [0] BOOLEAN,
   i-RAT2 [1] BOOLEAN,
   spare [2] INTEGER (0..3) DEFAULT 0
}

-- 10.5.5.28 - Voice domain preference and UE's usage setting 
VoiceDomainPref ::= SEQUENCE {
   --<is3GLength/>
   length [0] INTEGER (1),
   spare [1] INTEGER (0..31) DEFAULT 0,
   usUsageSetting [2] BOOLEAN, -- TRUE = voice, FALSE = data
   enumValue [3] ENUMERATED { csVoiceOnly(0), imsPsVoiceOnly(1), csVoicePref(2)
      , imsPsVoicePref(3) }
}

-- 10.5.5.29 - P-TMSI type 
P-TMSI-Type ::= SEQUENCE {
   spare [0] INTEGER (0..7) DEFAULT 0,
   p-tmsi-type [1] BOOLEAN
}

-- 10.5.5.30 - Location Area Identification 2 
LocAreaIdent2 ::= SEQUENCE {
   --<is3GLength/>
   length [0] INTEGER (5),
   value [1] LocAreaIdent
}

-- 10.5.5.31 - Network Resource Indentifier Container 
NetResourceIdentContainer ::= SEQUENCE {
   --<is3GLength/>
   length [0] INTEGER (2),
   nriContValue [1] INTEGER (0..1023),
   spare [2] INTEGER (0..63) DEFAULT 0
}

-- 10.5.5.32 - Extended DRX parameters 
ExtDRXParams ::= SEQUENCE {
   --<is3GLength/>
   length [0] INTEGER (1),
   pagingTimeWindow [1] INTEGER (0..16),
   eDRXValue [2] INTEGER (0..16)
}

-- 10.5.5.34 - User plane integrity indicator 
UserPlaneIntegInd ::= SEQUENCE {
   spare4 [0] BOOLEAN DEFAULT FALSE,
   spare3 [1] BOOLEAN DEFAULT FALSE,
   spare2 [2] BOOLEAN DEFAULT FALSE,
   integInd [3] BOOLEAN
}

-- 10.5.5.36 - PLMN identity of the CN operator 
PlmnCnID ::= SEQUENCE {
   mcc-mnc [0] MCCMNCPair
}

-- 10.5.5.37 - Non-3GPP NW provided policies 
Non3GPPNetPolicies ::= SEQUENCE {
   spare4 [0] BOOLEAN DEFAULT FALSE,
   spare3 [1] BOOLEAN DEFAULT FALSE,
   spare2 [2] BOOLEAN DEFAULT FALSE,
   emergencyNum [3] BOOLEAN
}

-- 10.5.6.2 - Network service access point identifier 
NSAPIValue ::= SEQUENCE {
   spare [0] INTEGER (0..15) DEFAULT 0,
   value [1] INTEGER (0..15)
}

-- 10.5.6.3 - Protocol configuration options 
-- PCOUnit is used to describe both Protocol and Container fields 
PCOUnit ::= SEQUENCE {
   protocolID [0] INTEGER (0..65535),
   contents [1] OCTET STRING
}

/*   The contents member of struct below may contain one or more
   PCOUnit structures.  These are used to represent both Protocol ID 
   and Container ID structures.*/
ProtocolConfigOptions ::= SEQUENCE {
   --<is3GLength/>
   length [0] INTEGER (1..253),
   --<first3GExtElem/>
   --<last3GExtElem/>
   octet3 [1] SEQUENCE {
      spare [0] INTEGER (0..15) DEFAULT 0,
      configProtocol [1] INTEGER (0..7)
   },
   --<is3GVarLenList lengthElem="length"/>
   pcoUnits [2] SEQUENCE OF PCOUnit
}

ExtProtoConfigOptions ::= SEQUENCE {
   --<is3GLength bitFieldSize="16"/>
   length [0] INTEGER (1..65532),
   --<first3GExtElem/>
   --<last3GExtElem/>
   octet4 [1] SEQUENCE {
      spare [0] INTEGER (0..15) DEFAULT 0,
      configProtocol [1] INTEGER (0..7)
   },
   --<is3GVarLenList lengthElem="length"/>
   pcoUnits [2] SEQUENCE OF PCOUnit
}

-- 10.5.6.4 - Packet data protocol address 
/*   PDP type organization field
   All other values are reserved.*/
/*   PDP type number field
   All other values are reserved.*/
PacketDataProtoAddr ::= SEQUENCE {
   --<is3GLength/>
   length [0] INTEGER (2..22),
   spare [1] INTEGER (0..15) DEFAULT 0, -- should be set to 0
   pdpTypeOrg [2] INTEGER (0..15), -- PDP type organization 
   pdpTypeNum [3] INTEGER (0..255), -- PDP type number 
   --<inline/>
   --<length fixed-size="0"/>
   addressInfo [4] OCTET STRING (SIZE (0..20)) -- Address information 
}

-- 10.5.6.5 - Quality of service 
QualityOfService ::= SEQUENCE {
   --<is3GLength/>
   length [0] INTEGER (4..255),
   spare1 [1] INTEGER (0..3) DEFAULT 0,
   delayClass [2] INTEGER (0..7),
   reliabilityClass [3] INTEGER (0..7),
   peakThroughput [4] INTEGER (0..15),
   spare2 [5] INTEGER (0..1) DEFAULT 0,
   precedenceClass [6] INTEGER (0..7),
   spare3 [7] INTEGER (0..7) DEFAULT 0,
   meanThroughput [8] INTEGER (0..31),
   trafficClass [9] INTEGER (0..7),
   deliveryOrder [10] INTEGER (0..3),
   deliveryErroneousSDU [11] INTEGER (0..7),
   maxSDUSize [12] INTEGER (0..255),
   maxUplinkBR [13] INTEGER (0..255), -- BR = Bit rate 
   maxDownlinkBR [14] INTEGER (0..255),
   residualBER [15] INTEGER (0..15), -- BER = Bit error rate 
   sduErrorRatio [16] INTEGER (0..15),
   transferDelay [17] INTEGER (0..63),
   trafficHandlingPrio [18] INTEGER (0..3),
   guaranteedUplinkBR [19] INTEGER (0..255),
   guaranteedDownlinkBR [20] INTEGER (0..255),
   spare4 [21] INTEGER (0..7) DEFAULT 0,
   signallingIndication [22] BOOLEAN,
   sourceStatsDescriptor [23] INTEGER (0..15),
   --<is3GVarLenList lengthElem="length"/>
   --<storage>array</storage>
   extBitRate [24] SEQUENCE (SIZE (0..8)) OF INTEGER (0..255)
   -- Extension bit rate values, up to 8 can be specified as follows:
   --   0 : max downlink bitrate
   --   1 : guaranteed downlink bitrate
   --   2 : max uplink bitrate
   --   3 : guaranteed uplink bitrate
   --   4 : max downlink bitrate (extension 2)
   --   5 : guaranteed downlink bitrate (extension 2)
   --   6 : max uplink bitrate (extension 2)
   --   7 : guaranteed uplink bitrate (extension 2)
}

-- 10.5.6.5A - Re-attempt indicator 
ReattemptInd ::= SEQUENCE {
   --<is3GLength/>
   length [0] INTEGER (1),
   spare8 [1] BOOLEAN,
   spare7 [2] BOOLEAN,
   spare6 [3] BOOLEAN,
   spare5 [4] BOOLEAN,
   spare4 [5] BOOLEAN,
   spare3 [6] BOOLEAN,
   eplmNCValue [7] BOOLEAN,
   ratcValue [8] BOOLEAN
}

-- 10.5.6.5B - Extended quality of service 
ExtQualityOfService ::= SEQUENCE {
   maxBRUnit [0] INTEGER (0..255), -- BR = Bit rate 
   maxUplinkBR [1] INTEGER (0..65535),
   maxDownlinkBR [2] INTEGER (0..65535),
   guaranteedBRUnit [3] INTEGER (0..255),
   guaranteedUplinkBR [4] INTEGER (0..65535),
   guaranteedDownlinkBR [5] INTEGER (0..65535)
}

-- 10.5.6.7 - Linked TI 
--<cDecFuncFname>TS24008IESDec_LinkedTI.c</cDecFuncFname>
--<cEncFuncFname>TS24008IESEnc_LinkedTI.c</cEncFuncFname>
LinkedTI ::= SEQUENCE {
   flag [0] BOOLEAN,
   value [1] INTEGER (0..7),
   spare [2] INTEGER (0..15) DEFAULT 0
}

-- 10.5.6.9 - LLC service access point identifier 
LLCSAPIValue ::= SEQUENCE {
   spare [0] INTEGER (0..15) DEFAULT 0,
   value [1] INTEGER (0..15)
}

-- 10.5.6.10 - Tear down indicator 
TDIValue ::= SEQUENCE {
   spare [0] INTEGER (0..7) DEFAULT 0,
   tdiFlag [1] BOOLEAN
}

-- 10.5.6.11 - Packet Flow Identifier 
PacketFlowIdentValue ::= SEQUENCE {
   --<is3GLength/>
   length [0] INTEGER (1),
   spare [1] BOOLEAN DEFAULT FALSE,
   value [2] INTEGER (0..127)
}

-- 10.5.6.12 - Traffic Flow Template 
TFTOctet1 ::= SEQUENCE {
   tftOperationCode [0] ENUMERATED { ignoreThisIE(0), createTFT(1), 
      deleteTFT(2), addPktFilters(3), replPktFilters(4), delPktFilters(5), 
      noTFTOp(6) },
   eBit [1] BOOLEAN,
   numPacketFilters [2] INTEGER (0..15)
}

TFTPacketFilterItem ::= SEQUENCE {
                                   -- pf = packet filter 
   spare [0] INTEGER (0..3),
   pfDirection [1] INTEGER (0..3),
   pfIdentifier [2] INTEGER (0..15),
   pfEvaluationPrecedence [3] INTEGER (0..255),
   contents [4] OCTET STRING
}

TFTParam ::= SEQUENCE {
   paramIdentifier [0] INTEGER (0..255),
   contents [1] OCTET STRING
}

/*   The contents member of the struct below may consist of a packet filter
   list followed by a parameter list.
   The format of the packet filter list depends on the tftOperationCode
   field.  If the operation is "delete packet filters" (0x05), then the
   packet filter list will just be a seqence of packet filter identifiers
   (one octet each).
   If, however, the operation is "create new TFT" (0x01), "add packet filters
   to existing TFT" (0x03), or "replace packet filters in existing TFT"
   (0x04), then the packet filter list will be one or more of the
   TFTPacketFilterItem structs.
   The parameter list consists of one or more of the TFTParam
   structures.*/
TFT ::= SEQUENCE {
   --<is3GLength/>
   length [0] INTEGER (1..255),
   octet1 [1] TFTOctet1,
   -- choice alternatives below are based on tftOperationCode value
   -- if operation is delete, identifiers alternative is selected
   -- if operation is create, add, or replace, filter item list is used
   --<inline/>
   packetFilterList [2] EXPLICIT CHOICE {
      --<selector element="octet1.tftOperationCode" value="5"/>
      identifiers [0] OCTET STRING, -- each identifer is one octet in length
      filterItems [1] SEQUENCE OF TFTPacketFilterItem
   },
   --<inline/>
   paramList [3] SEQUENCE OF TFTParam
}

-- 10.5.6.14 - MBMS bearer capabilities 
MBMSBearerCaps ::= SEQUENCE {
   maxDownlinkBR [0] INTEGER (0..255), -- BR = bit rate 
   maxDownlinkBRExt [1] INTEGER (0..255)
}

-- 10.5.6.17 - Request type 
RequestTypeValue ::= SEQUENCE {
   spare [0] BOOLEAN DEFAULT FALSE,
   value [1] INTEGER (0..7)
}

-- 10.5.6.20 - WLAN offload acceptability 
WLANOffloadAccept ::= SEQUENCE {
   spare1 [0] BOOLEAN,
   spare2 [1] BOOLEAN,
   uTranOffloadAcceptValue [2] BOOLEAN,
   e-UTranOffloadAcceptValue [3] BOOLEAN
}

-- 10.5.7.1 - PDP context status 
PDPContextStatus ::= SEQUENCE {
   --<is3GLength/>
   length [0] INTEGER (0..255) DEFAULT 2,
   value [1] OCTET STRING (SIZE (2))
}

-- 10.5.7.3 - GPRS Timer 
GPRSTimer ::= SEQUENCE {
   unit [0] INTEGER (0..7),
   timerValue [1] INTEGER (0..31)
}

-- 10.5.7.4 - GPRS Timer 2 
GPRSTimer2 ::= SEQUENCE {
   --<is3GLength/>
   length [0] INTEGER (1),
   value [1] GPRSTimer
}

-- 10.5.7.4a - GPRS Timer 3 
GPRSTimer3 ::= SEQUENCE {
   --<is3GLength/>
   length [0] INTEGER (1),
   unit [1] ENUMERATED { valIncrMult10Mins(0), valIncrMult1Hr(1), 
      valIncrMult10hrs(2), valIncrMult2Secs(3), valIncrMult30Secs(4), 
      valIncrMult1Min(5), valIncrMult320Hrs(6), timerDeact(7) },
   timerValue [2] INTEGER (0..31)
}

-- 10.5.7.7 - Uplink data status 
UplinkDataStatus ::= SEQUENCE {
   --<is3GLength/>
   length [0] INTEGER (2) DEFAULT 2,
   value [1] OCTET STRING (SIZE (2))
}

-- 10.5.7.8 - Device properties 
DeviceProperties ::= SEQUENCE {
   spare [0] INTEGER (0..7) DEFAULT 0,
   lowPriority [1] BOOLEAN
}

-- Value assignments

unassignedCause INTEGER ::= 1

noRouteToDest INTEGER ::= 3

chanUnaccept INTEGER ::= 6

operDetBarring INTEGER ::= 8

callComplElsewhere INTEGER ::= 13

normCallClear INTEGER ::= 16

userBusy INTEGER ::= 17

noUserRespond INTEGER ::= 18

noAnswer INTEGER ::= 19

callRejected INTEGER ::= 21

numberChanged INTEGER ::= 22

callRejDestFeat INTEGER ::= 24

preemption INTEGER ::= 25

nonSelUserClr INTEGER ::= 26

destOutOfOrder INTEGER ::= 27

invNumberFmt INTEGER ::= 28

facilityReject INTEGER ::= 29

respToStatEnq INTEGER ::= 30

normalUnspec INTEGER ::= 31

noCircChanAvail INTEGER ::= 34

netOutOfOrder INTEGER ::= 38

tempFailure INTEGER ::= 41

swEquipCongest INTEGER ::= 42

accInfoDiscard INTEGER ::= 43

reqCircChanNotAvail INTEGER ::= 44

resourceUnavail INTEGER ::= 47

qosUnavail INTEGER ::= 49

reqFacNotSub INTEGER ::= 50

inCallsBarred INTEGER ::= 55

bearCapNotAuth INTEGER ::= 57

bearCapNotAvail INTEGER ::= 58

svcOptNotAvail INTEGER ::= 63

bearSvcNotImpl INTEGER ::= 65

acmEqOrGtMax INTEGER ::= 68

reqFacNotImpl INTEGER ::= 69

restDigInfoBearCap INTEGER ::= 70

svcOptNotImpl INTEGER ::= 79

invTransId INTEGER ::= 81

userNotMemOfCUG INTEGER ::= 87

incompatDest INTEGER ::= 88

invTransNetSel INTEGER ::= 91

semBadMsg INTEGER ::= 95

invMandInfo INTEGER ::= 96

noMsgType INTEGER ::= 97

incompatMsgType INTEGER ::= 98

noInfoElem INTEGER ::= 99

condIEErr INTEGER ::= 100

incompatMsg INTEGER ::= 101

recOnTimerExp INTEGER ::= 102

protocolErr INTEGER ::= 111

interworkErr INTEGER ::= 127


END
TS24008Msgs DEFINITIONS AUTOMATIC TAGS ::= BEGIN

IMPORTS

NAS-PROTOCOL-CLASS, SecProtMsgHeader, ProtoDiscr
FROM TS24007L3 

AC-Reference-Number, AccessPointName, AddnNetFeatureSupport, AddnUpdateParams, 
   AddnUpdateType, AlertingPattern, AllowedActions, AttachResult, AttachType, 
   AuthFailureParam, AuthParamAUTN, AuthParamRAND, AuthRespParam, 
   AuthRespParamExt, AuxiliaryStates, BackupBearerCapability, BearerCapability
   , CC-Establishment, CMServiceType, CallControlCapabilities, CallState, 
   CalledPartyBCDNumber, CallingPartyBCDNumber, Cause, CauseOfNoCLI, 
   CiphKeySeqNum, CipheringAlgorithmType, CongestionLevel, ConnectedNumber, 
   ConnectedSubaddress, ConnectivityType, DRXParameter, DaylightSavingTime, 
   DetachType, DeviceProperties, E-UTRANInterRATInfoContainer, 
   EmergencyNumberList, EnhancedNSAPIValue, ExtDRXParams, Facility, 
   FacilityNetworkToMS, ForceToStandbyValue, GMMCauseValue, GPRSTimer, 
   GPRSTimer2, GPRSTimer3, HighLayerCompatibility, IMEISVRequest, 
   IdentityType2Value, IdentityTypeValue, IntegrityAlgorithmType, 
   InterRATInfoContainer, KeypadFacilityInfo, LLCSAPIValue, LSAIdentifier, 
   LinkedTI, LocAreaIdent, LocAreaIdent2, LocationUpdatingType, 
   LowLayerCompatibility, MBMS-PCO, MBMSBearerCaps, MBMSContextStatus, MMTimer
   , MSNetworkCapability, MSNetFeatureSupport, MSRadioAccessCapability, 
   MobileIdentity, MobileStationClassmark1, MobileStationClassmark2, 
   MobileStationClassmark3, MsgAuthCode, NBIFOMContainer, NSAPIValue, 
   NetCallCtrlCaps, NetFeatureSupp, NetworkName, NetResourceIdentContainer, 
   NotificationIndicator, Notify, P-TMSISignature, P-TMSISignature2, 
   P-TMSI-Type, PDAndSAPI, PDPContextStatus, PLMNList, PS-LCSCapbility, 
   PacketDataProtoAddr, PacketFlowIdentValue, PartySubaddress, PriorityLevel, 
   ProgressIndicator, ProtocolConfigOptions, QualityOfService, 
   RadioPriorityValue, RadioPriorityValue2, ReattemptInd, RecallType, 
   ReceiveNPDUNumberList, RedirectingPartyBCDNumber, RejectCauseValue, 
   RepeatIndicator, RequestTypeValue, RequestedMSInfo, RetrieveReject, 
   RoutingAreaIdent, RoutingAreaIdent2, SecProtMsgHeader, SMCause2Value, 
   SMCauseValue, SMStatus, SSVersionIndicator, ServiceCategoryValue, 
   ServiceType, Setup-Container, Signal, SM-NotificationIndicator, StartCC, 
   StartDTMF, StartDTMFAck, StartDTMFReject, StreamIdentifierValue, 
   SupportedCodecList, TDIValue, TFT, TMGI, TMSIStatus, TimeZone, 
   TimeZoneAndTime, UENetCapability, UpdateResult, UpdateType, UplinkDataStatus
   , UserPlaneIntegInd, UserUser, VoiceDomainPref, WLANOffloadAccept, DcnID, 
   PlmnCnID, Non3GPPNetPolicies, ExtProtoConfigOptions, ExtQualityOfService
FROM TS24008IES ;

-- Productions

StartDTMF ::= SEQUENCE {
   --<iei format="tv" length="2">2C</iei>
   keypadFacility [0] KeypadFacilityInfo OPTIONAL
}

StartDTMFAck ::= StartDTMF

ActivatePDPCtxtReject ::= SEQUENCE {
   smCause [0] SMCauseValue,
   --<iei format="tlv">27</iei>
   protocolConfigOptions [1] ProtocolConfigOptions OPTIONAL,
   ...,
   [[ 10:
      t3396Value [2] GPRSTimer3 OPTIONAL
   ]],
   [[ 12:
      reattemptInd [3] ReattemptInd OPTIONAL
   ]],
   [[ 13:
      nbifomContainer [4] NBIFOMContainer OPTIONAL
   ]],
   [[ 14:
      extProtoConfigOptions [5] ExtProtoConfigOptions OPTIONAL
   ]]
}

ActivateSecondaryPDPCtxtRej ::= ActivatePDPCtxtReject

ModifyPDPCtxtRej ::= ActivatePDPCtxtReject

AuthenticationRequest ::= SEQUENCE {
   spare [0] INTEGER (0..15) DEFAULT 0,
   ciphKeySeqNum [1] CiphKeySeqNum,
   authParamRAND [2] AuthParamRAND,
   --<iei format="tlv">20</iei>
   authParamAUTN [3] AuthParamAUTN OPTIONAL
}

AuthenticationResponse ::= SEQUENCE {
   respParam [0] AuthRespParam,
   --<iei format="tlv">21</iei>
   respParamExt [1] AuthRespParamExt OPTIONAL
}

AuthenticationFailure ::= SEQUENCE {
   rejectCause [0] RejectCauseValue,
   --<iei format="tlv">22</iei>
   failParam [1] AuthFailureParam OPTIONAL
}

CMReestabRequest ::= SEQUENCE {
   spare [0] INTEGER (0..15) DEFAULT 0,
   ciphKeySeqNum [1] CiphKeySeqNum,
   mobileStationClassmark2 [2] MobileStationClassmark2,
   mobileIdentity [3] EXPLICIT MobileIdentity,
   --<iei format="tv" length="6">13</iei>
   locAreaIdent [4] LocAreaIdent OPTIONAL,
   ...,
   [[ 10:
      deviceProperties [5] DeviceProperties OPTIONAL
   ]]
}

CMServicePrompt ::= SEQUENCE {
   pdAndSAPI [0] PDAndSAPI
}

CMServiceReject ::= SEQUENCE {
   rejectCause [0] RejectCauseValue,
   ...,
   [[ 10:
      t3246Value [1] MMTimer OPTIONAL
   ]]
}

Abort ::= SEQUENCE {
   rejectCause [0] RejectCauseValue
}

CMServiceRequest ::= SEQUENCE {
   ciphKeySeqNum [0] CiphKeySeqNum,
   cmServiceType [1] CMServiceType,
   mobileStationClassmark2 [2] MobileStationClassmark2,
   mobileIdentity [3] EXPLICIT MobileIdentity,
   --<iei format="tv" length="1">8</iei>
   priorityLevel [4] PriorityLevel OPTIONAL,
   ...,
   [[ 10:
      addnUpdateParams [5] AddnUpdateParams OPTIONAL,
      deviceProperties [6] DeviceProperties OPTIONAL
   ]]
}

IdentityRequest ::= SEQUENCE {
   spare [0] INTEGER (0..15) DEFAULT 0,
   value [1] IdentityTypeValue
}

IdentityResponse ::= SEQUENCE {
   mobileIdentity [0] EXPLICIT MobileIdentity,
   ...,
   [[ 11:
      p-TMSI-Type [1] P-TMSI-Type OPTIONAL,
      routingAreaId [2] RoutingAreaIdent2 OPTIONAL,
      pTMSISignature [3] P-TMSISignature2 OPTIONAL
   ]]
}

IMSIDetachInd ::= SEQUENCE {
   mobileStationClassmark1 [0] MobileStationClassmark1,
   mobileIdentity [1] EXPLICIT MobileIdentity
}

LocUpdatingAccept ::= SEQUENCE {
   locAreaIdent [0] LocAreaIdent,
   --<iei format="tlv">17</iei>
   mobileIdentity [1] EXPLICIT MobileIdentity OPTIONAL,
   /* followOnProceed and ctsPermission contain no data, just IEI (tag) - 
      present flags are sufficient to indicate presence or absence */
   --<iei format="t">A1</iei>
   followOnProceed [2] NULL OPTIONAL,
   --<iei format="t">A2</iei>
   ctsPermission [3] NULL OPTIONAL,
   --<iei format="tlv">4A</iei>
   equivPLMNs [4] PLMNList OPTIONAL,
   --<iei format="tlv">34</iei>
   emergNumList [5] EmergencyNumberList OPTIONAL,
   ...,
   [[ 10:
      per-MS-T3212 [6] GPRSTimer3 OPTIONAL
   ]],
   [[ 14:
      non3GPPNetPolicies [7] Non3GPPNetPolicies OPTIONAL
   ]]
}

LocUpdatingReject ::= SEQUENCE {
   rejectCause [0] RejectCauseValue,
   ...,
   [[ 10:
      t3246Value [1] MMTimer OPTIONAL
   ]]
}

LocUpdatingRequest ::= SEQUENCE {
   ciphKeySeqNum [0] CiphKeySeqNum,
   locUpdatingType [1] LocationUpdatingType,
   locAreaIdent [2] LocAreaIdent,
   mobileStationClassmark1 [3] MobileStationClassmark1,
   mobileIdentity [4] EXPLICIT MobileIdentity,
   --<iei format="tlv">33</iei>
   mobStatCmark4UMTS [5] MobileStationClassmark2 OPTIONAL,
   ...,
   [[ 9:
      addnUpdateParams [6] AddnUpdateParams OPTIONAL
   ]],
   [[ 10:
      deviceProperties [7] DeviceProperties OPTIONAL,
      msNetFeatureSupport [8] MSNetFeatureSupport OPTIONAL
   ]]
}

MMInformation ::= SEQUENCE {
   --<iei format="tlv">43</iei>
   networkFullName [0] NetworkName OPTIONAL,
   --<iei format="tlv">45</iei>
   networkShortName [1] NetworkName OPTIONAL,
   --<iei format="tv" length="2">46</iei>
   localTimeZone [2] TimeZone OPTIONAL,
   --<iei format="tv" length="8">47</iei>
   univAndLocalTimeZone [3] TimeZoneAndTime OPTIONAL,
   --<iei format="tlv">48</iei>
   lsaIdentity [4] LSAIdentifier OPTIONAL,
   --<iei format="tlv">49</iei>
   networkDaylightSavingTime [5] DaylightSavingTime OPTIONAL
}

MMStatus ::= SEQUENCE {
   rejectCause [0] RejectCauseValue
}

TMSIReallocCmd ::= SEQUENCE {
   locAreaIdent [0] LocAreaIdent,
   mobileIdentity [1] EXPLICIT MobileIdentity
}

Alerting ::= SEQUENCE {
   --<iei format="tlv">1C</iei>
   facility [0] Facility OPTIONAL,
   --<iei format="tlv">1E</iei>
   progressInd [1] ProgressIndicator OPTIONAL,
   --<iei format="tlv">7E</iei>
   user-user [2] UserUser OPTIONAL,
   --<iei format="tlv">7F</iei>
   ssVersion [3] SSVersionIndicator OPTIONAL
}

CallConfirmed ::= SEQUENCE {
   --<iei format="tv" length="1">D</iei>
   repeatInd [0] RepeatIndicator OPTIONAL,
   --<iei format="tlv">04</iei>
   bearerCap1 [1] BearerCapability OPTIONAL,
   --<iei format="tlv">04</iei>
   bearerCap2 [2] BearerCapability OPTIONAL,
   --<iei format="tlv">08</iei>
   cause [3] Cause OPTIONAL,
   --<iei format="tlv">15</iei>
   callCtrlCap [4] CallControlCapabilities OPTIONAL,
   --<iei format="tlv">2D</iei>
   streamId [5] StreamIdentifierValue OPTIONAL,
   --<iei format="tlv">40</iei>
   supportedCodecs [6] SupportedCodecList OPTIONAL
}

CallProceeding ::= SEQUENCE {
   --<iei format="tv" length="1">D</iei>
   repeatInd [0] RepeatIndicator OPTIONAL,
   --<iei format="tlv">04</iei>
   bearerCap1 [1] BearerCapability OPTIONAL,
   --<iei format="tlv">04</iei>
   bearerCap2 [2] BearerCapability OPTIONAL,
   --<iei format="tlv">1C</iei>
   facility [3] Facility OPTIONAL,
   --<iei format="tlv">1E</iei>
   progressInd [4] ProgressIndicator OPTIONAL,
   --<iei format="tv" length="1">8</iei>
   priorityGranted [5] PriorityLevel OPTIONAL,
   --<iei format="tlv">2F</iei>
   netCallCtrlCap [6] NetCallCtrlCaps OPTIONAL
}

CongestionControl ::= SEQUENCE {
   spare [0] INTEGER (0..15) DEFAULT 0,
   congestionLevel [1] CongestionLevel,
   --<iei format="tlv">08</iei>
   cause [2] Cause OPTIONAL
}

Connect ::= SEQUENCE {
   --<iei format="tlv">1C</iei>
   facility [0] Facility OPTIONAL,
   --<iei format="tlv">1E</iei>
   progressInd [1] ProgressIndicator OPTIONAL,
   --<iei format="tlv">4C</iei>
   connNumber [2] ConnectedNumber OPTIONAL,
   --<iei format="tlv">4D</iei>
   connSubaddr [3] ConnectedSubaddress OPTIONAL,
   --<iei format="tlv">7E</iei>
   user-user [4] UserUser OPTIONAL,
   --<iei format="tlv">7F</iei>
   ssVersion [5] SSVersionIndicator OPTIONAL,
   --<iei format="tlv">2D</iei>
   streamId [6] StreamIdentifierValue OPTIONAL
}

Disconnect ::= SEQUENCE {
   cause [0] Cause,
   --<iei format="tlv">1C</iei>
   facility [1] Facility OPTIONAL,
   --<iei format="tlv">1E</iei>
   progressInd [2] ProgressIndicator OPTIONAL,
   --<iei format="tlv">7E</iei>
   user-user [3] UserUser OPTIONAL,
   --<iei format="tlv">7B</iei>
   allowedActions [4] AllowedActions OPTIONAL,
   --<iei format="tlv">7F</iei>
   ssVersion [5] SSVersionIndicator OPTIONAL
}

EmergencySetup ::= SEQUENCE {
   --<iei format="tlv">04</iei>
   bearerCap [0] BearerCapability OPTIONAL,
   --<iei format="tlv">2D</iei>
   streamId [1] StreamIdentifierValue OPTIONAL,
   --<iei format="tlv">40</iei>
   supportedCodecs [2] SupportedCodecList OPTIONAL,
   --<iei format="tlv">2E</iei>
   emergencyCat [3] ServiceCategoryValue OPTIONAL
}

FacilityMsg ::= SEQUENCE {
   facility [0] Facility,
   --<iei format="tlv">7F</iei>
   ssVersion [1] SSVersionIndicator OPTIONAL
}

Modify ::= SEQUENCE {
   bearerCap [0] BearerCapability,
   --<iei format="tlv">7C</iei>
   lowLayerComp [1] LowLayerCompatibility OPTIONAL,
   --<iei format="tlv">7D</iei>
   highLayerComp [2] HighLayerCompatibility OPTIONAL,
   --<iei format="t" length="1">A3</iei>
   revCallSetupDirection [3] NULL OPTIONAL,
   --<iei format="t" length="1">A4</iei>
   netInitServUpgrdInd [4] NULL OPTIONAL
}

ModifyComplete ::= SEQUENCE {
   bearerCap [0] BearerCapability,
   --<iei format="tlv">7C</iei>
   lowLayerComp [1] LowLayerCompatibility OPTIONAL,
   --<iei format="tlv">7D</iei>
   highLayerComp [2] HighLayerCompatibility OPTIONAL,
   --<iei format="t" length="1">A3</iei>
   revCallSetupDirection [3] NULL OPTIONAL
}

ModifyReject ::= SEQUENCE {
   bearerCap [0] BearerCapability,
   cause [1] Cause,
   --<iei format="tlv">7C</iei>
   lowLayerComp [2] LowLayerCompatibility OPTIONAL,
   --<iei format="tlv">7D</iei>
   highLayerComp [3] HighLayerCompatibility OPTIONAL
}

Progress ::= SEQUENCE {
   progressInd [0] ProgressIndicator,
   --<iei format="tlv">7E</iei>
   user-user [1] UserUser OPTIONAL
}

CC-EstablishmentConfirmed ::= SEQUENCE {
   --<iei format="tv" length="1">D</iei>
   repeatInd [0] RepeatIndicator OPTIONAL,
   --<iei format="tlv">04</iei>
   bearerCap1 [1] BearerCapability OPTIONAL,
   --<iei format="tlv">04</iei>
   bearerCap2 [2] BearerCapability OPTIONAL,
   --<iei format="tlv">08</iei>
   cause [3] Cause OPTIONAL,
   --<iei format="tlv">40</iei>
   supportedCodecs [4] SupportedCodecList OPTIONAL
}

Release ::= SEQUENCE {
   --<iei format="tlv">08</iei>
   cause [0] Cause OPTIONAL,
   --<iei format="tlv">08</iei>
   secondCause [1] Cause OPTIONAL,
   --<iei format="tlv">1C</iei>
   facility [2] Facility OPTIONAL,
   --<iei format="tlv">7E</iei>
   user-user [3] UserUser OPTIONAL,
   --<iei format="tlv">7F</iei>
   ssVersion [4] SSVersionIndicator OPTIONAL
}

Recall ::= SEQUENCE {
   recallType [0] RecallType,
   facility [1] Facility
}

ReleaseComplete ::= SEQUENCE {
   --<iei format="tlv">08</iei>
   cause [0] Cause OPTIONAL,
   --<iei format="tlv">1C</iei>
   facility [1] Facility OPTIONAL,
   --<iei format="tlv">7E</iei>
   user-user [2] UserUser OPTIONAL,
   --<iei format="tlv">7F</iei>
   ssVersion [3] SSVersionIndicator OPTIONAL
}

Setup ::= SEQUENCE {
   --<iei format="tv" length="1">D</iei>
   bcRepeatInd [0] RepeatIndicator OPTIONAL,
   --<iei format="tlv">04</iei>
   bearerCapability1 [1] BearerCapability OPTIONAL,
   --<iei format="tlv">04</iei>
   bearerCapability2 [2] BearerCapability OPTIONAL,
   --<iei format="tlv">1C</iei>
   facility [3] Facility OPTIONAL,
   --<iei format="tlv">1E</iei>
   progressInd [4] ProgressIndicator OPTIONAL,
   --<iei format="tv" length="2">34</iei>
   signal [5] Signal OPTIONAL,
   --<iei format="tlv">5C</iei>
   callingPartyNumber [6] CallingPartyBCDNumber OPTIONAL,
   --<iei format="tlv">5D</iei>
   callingPartySubaddress [7] PartySubaddress OPTIONAL,
   --<iei format="tlv">5E</iei>
   calledPartyNumber [8] CalledPartyBCDNumber OPTIONAL,
   --<iei format="tlv">6D</iei>
   calledPartySubaddress [9] PartySubaddress OPTIONAL,
   --<iei format="tlv">74</iei>
   redirectingPartyNumber [10] RedirectingPartyBCDNumber OPTIONAL,
   --<iei format="tlv">75</iei>
   redirectingPartySubaddress [11] PartySubaddress OPTIONAL,
   --<iei format="tv" length="1">D</iei>
   llcRepeatInd [12] RepeatIndicator OPTIONAL,
   --<iei format="tlv">7C</iei>
   lowLayerCompat1 [13] LowLayerCompatibility OPTIONAL,
   --<iei format="tlv">7C</iei>
   lowLayerCompat2 [14] LowLayerCompatibility OPTIONAL,
   --<iei format="tv" length="1">D</iei>
   hlcRepeatInd [15] RepeatIndicator OPTIONAL,
   --<iei format="tlv">7D</iei>
   highLayerCompat1 [16] HighLayerCompatibility OPTIONAL,
   --<iei format="tlv">7D</iei>
   highLayerCompat2 [17] HighLayerCompatibility OPTIONAL,
   --<iei format="tlv">7E</iei>
   userUser [18] UserUser OPTIONAL,
   -- the following IE's are present in mobile terminated only
   --<iei format="tv" length="1">8</iei>
   priorityLevel [19] PriorityLevel OPTIONAL,
   --<iei format="tlv">19</iei>
   alertingPattern [20] AlertingPattern OPTIONAL,
   --<iei format="tlv">2F</iei>
   netCallCtrlCaps [21] NetCallCtrlCaps OPTIONAL,
   --<iei format="tlv">3A</iei>
   causeOfNoCLI [22] CauseOfNoCLI OPTIONAL,
   --<iei format="tlv">41</iei>
   backupBearerCapability [23] BackupBearerCapability OPTIONAL,
   -- the following IE's are present in mobile originated only
   --<iei format="tlv">7F</iei>
   ssVersion [24] SSVersionIndicator OPTIONAL,
   --<iei format="t" length="1">A1</iei>
   clirSuppression [25] NULL OPTIONAL,
   --<iei format="t" length="1">A2</iei>
   clirInvocation [26] NULL OPTIONAL,
   --<iei format="tlv">15</iei>
   callCtrlCap [27] CallControlCapabilities OPTIONAL,
   --<iei format="tlv">1D</iei>
   facilityAdvRecallAlign [28] Facility OPTIONAL,
   --<iei format="tlv">1B</iei>
   facilityRecallAlignNotEssential [29] Facility OPTIONAL,
   --<iei format="tlv">2D</iei>
   streamId [30] StreamIdentifierValue OPTIONAL,
   --<iei format="tlv">40</iei>
   supportedCodecs [31] SupportedCodecList OPTIONAL,
   --<iei format="t">A3</iei>
   redial [32] NULL OPTIONAL
}

StartCC ::= SEQUENCE {
   --<iei format="tlv">15</iei>
   ccCapabilities [0] CallControlCapabilities OPTIONAL
}

Status ::= SEQUENCE {
   cause [0] Cause,
   callState [1] CallState,
   --<iei format="tlv">24</iei>
   auxStates [2] AuxiliaryStates OPTIONAL
}

UserInfo ::= SEQUENCE {
   userUser [0] UserUser,
   -- 10.5.4.19 More Data is IEI only 
   --<iei format="t">A0</iei>
   moreData [1] NULL OPTIONAL
}

AttachRequest ::= SEQUENCE {
   msNetCapability [0] MSNetworkCapability,
   gprsCiphKeySeq [1] CiphKeySeqNum,
   attachType [2] AttachType,
   drxParameter [3] DRXParameter,
   pTMSIOrIMSI [4] EXPLICIT MobileIdentity,
   oldRoutingAreaId [5] RoutingAreaIdent,
   msRACapability [6] MSRadioAccessCapability,
   --<iei format="tv" length="4">19</iei>
   oldPTMSISignature [7] P-TMSISignature OPTIONAL,
   --<iei format="tv" length="2">17</iei>
   reqREADYTimerValue [8] GPRSTimer OPTIONAL,
   --<iei format="tv" length="1">9</iei>
   tmsiStatus [9] TMSIStatus OPTIONAL,
   --<iei format="tlv">33</iei>
   psLCSCap [10] PS-LCSCapbility OPTIONAL,
   --<iei format="tlv">11</iei>
   msClassmark2 [11] MobileStationClassmark2 OPTIONAL,
   --<iei format="tlv">20</iei>
   msClassmark3 [12] MobileStationClassmark3 OPTIONAL,
   --<iei format="tlv">40</iei>
   supportedCodecs [13] SupportedCodecList OPTIONAL,
   --<iei format="tlv">58</iei>
   ueNetCap [14] UENetCapability OPTIONAL,
   --<iei format="tlv">1A</iei>
   addnMobileId [15] EXPLICIT MobileIdentity OPTIONAL,
   --<iei format="tlv">1B</iei>
   addnOldRoutingAreaId [16] RoutingAreaIdent2 OPTIONAL,
   ...,
   [[ 9:
      voiceDomainPref [17] VoiceDomainPref OPTIONAL
   ]],
   [[ 10:
      deviceProperties [18] DeviceProperties OPTIONAL,
      p-TMSI-Type [19] P-TMSI-Type OPTIONAL,
      msNetFeatureSupport [20] MSNetFeatureSupport OPTIONAL,
      oldLocAreaIdent [21] LocAreaIdent2 OPTIONAL
   ]],
   [[ 11:
      addnUpdateType [22] AddnUpdateType OPTIONAL,
      tmsiBasedNRICont [23] NetResourceIdentContainer OPTIONAL
   ]],
   [[ 12:
      t3324Value [24] GPRSTimer2 OPTIONAL,
      t3312ExtValue [25] GPRSTimer3 OPTIONAL
   ]],
   [[ 13:
      extDRXParams [26] ExtDRXParams OPTIONAL
   ]]
}

AttachAccept ::= SEQUENCE {
   forceToStandby [0] ForceToStandbyValue,
   attachResult [1] AttachResult,
   periodicRAUpdateTimer [2] GPRSTimer,
   radioPriForTOM8 [3] RadioPriorityValue2,
   radioPriForSMS [4] RadioPriorityValue,
   routingAreaIdent [5] RoutingAreaIdent,
   --<iei format="tv" length="4">19</iei>
   pTMSISignature [6] P-TMSISignature OPTIONAL,
   --<iei format="tv" length="2">17</iei>
   negotiatedREADYTimerValue [7] GPRSTimer OPTIONAL,
   --<iei format="tlv">18</iei>
   allocatedPTMSI [8] EXPLICIT MobileIdentity OPTIONAL,
   --<iei format="tlv">23</iei>
   msIdentity [9] EXPLICIT MobileIdentity OPTIONAL,
   --<iei format="tv" length="2">25</iei>
   gmmCause [10] GMMCauseValue OPTIONAL,
   --<iei format="tlv">2A</iei>
   t3302Value [11] GPRSTimer2 OPTIONAL,
   --<iei format="t">8C</iei>
   cellNotification [12] NULL OPTIONAL,
   --<iei format="tlv">4A</iei>
   equivalentPLMNs [13] PLMNList OPTIONAL,
   --<iei format="tv" length="1">B</iei>
   netFeatureSupport [14] NetFeatureSupp OPTIONAL,
   --<iei format="tlv">34</iei>
   emergencyNumList [15] EmergencyNumberList OPTIONAL,
   --<iei format="tv" length="1">A</iei>
   requestedMSInfo [16] RequestedMSInfo OPTIONAL,
   --<iei format="tlv">37</iei>
   t3319Value [17] GPRSTimer2 OPTIONAL,
   --<iei format="tlv">38</iei>
   t3323Value [18] GPRSTimer2 OPTIONAL,
   ...,
   [[ 10:
      t3312Value [19] GPRSTimer3 OPTIONAL
   ]],
   [[ 11:
      addnNetFeatureSupport [20] AddnNetFeatureSupport OPTIONAL
   ]],
   [[ 12:
      t3324Value [21] GPRSTimer2 OPTIONAL
   ]],
   [[ 13:
      extDRXParams [22] ExtDRXParams OPTIONAL,
      userPlaneIntegInd [23] UserPlaneIntegInd OPTIONAL,
      replayMSNetCapability [24] MSNetworkCapability OPTIONAL,
      replayMSRadioAccessCap [25] MSRadioAccessCapability OPTIONAL
   ]],
   [[ 14:
      dcnId [26] DcnID OPTIONAL,
      plmnCnId [27] PlmnCnID OPTIONAL,
      non3GPPNetPolicies [28] Non3GPPNetPolicies OPTIONAL
   ]]
}

AttachComplete ::= SEQUENCE {
   --<iei format="tlv">27</iei>
   erRATInfoContainer [0] InterRATInfoContainer OPTIONAL,
   --<iei format="tlv">2B</iei>
   eUTRANInterRATInfoContainer [1] E-UTRANInterRATInfoContainer OPTIONAL
}

AttachReject ::= SEQUENCE {
   gmmCause [0] GMMCauseValue,
   --<iei format="tlv">2A</iei>
   t3302Value [1] GPRSTimer2 OPTIONAL,
   ...,
   [[ 10:
      t3346Value [2] GPRSTimer2 OPTIONAL
   ]]
}

DetachRequest ::= SEQUENCE {
   detachType [0] DetachType,
   forceToStandby [1] ForceToStandbyValue, -- spare in mobile originated
   -- this IE is used in mobile terminated only
   --<iei format="tv" length="2">25</iei>
   gmmCause [2] GMMCauseValue OPTIONAL,
   -- thess IE's are used in mobile originated only
   --<iei format="tlv">18</iei>
   pTMSI [3] EXPLICIT MobileIdentity OPTIONAL,
   --<iei format="tlv">19</iei>
   pTMSISignature [4] P-TMSISignature2 OPTIONAL
}

DetachAccept ::= SEQUENCE {
   -- present flag must be set to false in mobile terminated case and 
   -- custom encoder will simply omit the value
   forceToStandby [0] ForceToStandbyValue OPTIONAL
}

P-TMSIReallocCmd ::= SEQUENCE {
   allocatedPTMSI [0] EXPLICIT MobileIdentity,
   routingAreaIdent [1] RoutingAreaIdent,
   forceToStandby [2] ForceToStandbyValue,
   spare [3] INTEGER (0..15) DEFAULT 0,
   --<iei format="tv" length="4">19</iei>
   pTMSISignature [4] P-TMSISignature OPTIONAL,
   ...,
   [[ 14:
      dcnId [5] DcnID OPTIONAL
   ]]
}

AuthAndCiphRequest ::= SEQUENCE {
   cipheringAlgorithm [0] CipheringAlgorithmType,
   imeisvRequest [1] IMEISVRequest,
   forceToStandby [2] ForceToStandbyValue,
   acRefNumber [3] AC-Reference-Number,
   --<iei format="tv" length="17">21</iei>
   authParamRAND [4] AuthParamRAND OPTIONAL,
   --<iei format="tv" length="1">8</iei>
   ciphKeySeqNum [5] CiphKeySeqNum OPTIONAL,
   --<iei format="tlv">28</iei>
   authParamAUTN [6] AuthParamAUTN OPTIONAL,
   ...,
   [[ 13:
      replayMSNetCapability [7] MSNetworkCapability OPTIONAL,
      integAlgorithm [8] IntegrityAlgorithmType OPTIONAL,
      msgAuthCode [9] MsgAuthCode OPTIONAL,
      replayMSRadioAccessCap [10] MSRadioAccessCapability OPTIONAL
   ]]
}

AuthAndCiphResponse ::= SEQUENCE {
   spare [0] INTEGER (0..15) DEFAULT 0,
   acRefNumber [1] AC-Reference-Number,
   --<iei format="tv" length="5">22</iei>
   authRespParam [2] AuthRespParam OPTIONAL,
   --<iei format="tlv">23</iei>
   imeisv [3] EXPLICIT MobileIdentity OPTIONAL,
   --<iei format="tlv">29</iei>
   authRespParamExt [4] AuthRespParamExt OPTIONAL,
   ...,
   [[ 13:
      msgAuthCode [5] MsgAuthCode OPTIONAL
   ]]
}

AuthAndCiphFailure ::= SEQUENCE {
   gmmCause [0] GMMCauseValue,
   --<iei format="tlv">30</iei>
   authFailureParam [1] AuthFailureParam OPTIONAL
}

GMMIdentityRequest ::= SEQUENCE {
   forceToStandby [0] ForceToStandbyValue,
   identityType [1] IdentityType2Value
}

GMMIdentityResponse ::= SEQUENCE {
   mobileIdentity [0] EXPLICIT MobileIdentity
}

RoutingAreaUpdateRequest ::= SEQUENCE {
   gprsCiphKeySeq [0] CiphKeySeqNum,
   updateType [1] UpdateType,
   oldRoutingAreaId [2] RoutingAreaIdent,
   msRACapability [3] MSRadioAccessCapability,
   --<iei format="tv" length="4">19</iei>
   oldPTMSISignature [4] P-TMSISignature OPTIONAL,
   --<iei format="tv" length="2">17</iei>
   reqREADYTimerValue [5] GPRSTimer OPTIONAL,
   --<iei format="tv" length="3">27</iei>
   drxParameter [6] DRXParameter OPTIONAL,
   --<iei format="tv" length="1">9</iei>
   tmsiStatus [7] TMSIStatus OPTIONAL,
   --<iei format="tlv">18</iei>
   pTMSI [8] EXPLICIT MobileIdentity OPTIONAL,
   --<iei format="tlv">31</iei>
   msNetCapability [9] MSNetworkCapability OPTIONAL,
   --<iei format="tlv">32</iei>
   pdpContextStatus [10] PDPContextStatus OPTIONAL,
   --<iei format="tlv">33</iei>
   psLCSCap [11] PS-LCSCapbility OPTIONAL,
   --<iei format="tlv">35</iei>
   mbmsContextStatus [12] MBMSContextStatus OPTIONAL,
   --<iei format="tlv">58</iei>
   ueNetCap [13] UENetCapability OPTIONAL,
   --<iei format="tlv">1A</iei>
   addnMobileId [14] EXPLICIT MobileIdentity OPTIONAL,
   --<iei format="tlv">1B</iei>
   addnOldRoutingAreaId [15] RoutingAreaIdent2 OPTIONAL,
   --<iei format="tlv">11</iei>
   msClassmark2 [16] MobileStationClassmark2 OPTIONAL,
   --<iei format="tlv">20</iei>
   msClassmark3 [17] MobileStationClassmark3 OPTIONAL,
   --<iei format="tlv">40</iei>
   supportedCodecs [18] SupportedCodecList OPTIONAL,
   ...,
   [[ 9:
      voiceDomainPref [19] VoiceDomainPref OPTIONAL
   ]],
   [[ 10:
      p-TMSI-Type [20] P-TMSI-Type OPTIONAL,
      deviceProperties [21] DeviceProperties OPTIONAL,
      msNetFeatureSupport [22] MSNetFeatureSupport OPTIONAL,
      oldLocAreaIdent [23] LocAreaIdent2 OPTIONAL
   ]],
   [[ 11:
      addnUpdateType [24] AddnUpdateType OPTIONAL,
      tmsiBasedNRICont [25] NetResourceIdentContainer OPTIONAL
   ]],
   [[ 12:
      t3324Value [26] GPRSTimer2 OPTIONAL,
      t3312ExtValue [27] GPRSTimer3 OPTIONAL
   ]],
   [[ 13:
      extDRXParams [28] ExtDRXParams OPTIONAL
   ]]
}

RoutingAreaUpdateAccept ::= SEQUENCE {
   forceToStandby [0] ForceToStandbyValue,
   updateResult [1] UpdateResult,
   periodicRAUpdateTimer [2] GPRSTimer,
   routingAreaIdent [3] RoutingAreaIdent,
   --<iei format="tv" length="4">19</iei>
   pTMSISignature [4] P-TMSISignature OPTIONAL,
   --<iei format="tlv">18</iei>
   allocatedPTMSI [5] EXPLICIT MobileIdentity OPTIONAL,
   --<iei format="tlv">23</iei>
   msIdentity [6] EXPLICIT MobileIdentity OPTIONAL,
   --<iei format="tlv">26</iei>
   receiveNPDUNumberList [7] ReceiveNPDUNumberList OPTIONAL,
   --<iei format="tv" length="2">17</iei>
   negotiatedREADYTimerValue [8] GPRSTimer OPTIONAL,
   --<iei format="tv" length="2">25</iei>
   gmmCause [9] GMMCauseValue OPTIONAL,
   --<iei format="tlv">2A</iei>
   t3302Value [10] GPRSTimer2 OPTIONAL,
   --<iei format="t">8C</iei>
   cellNotification [11] NULL OPTIONAL,
   --<iei format="tlv">4A</iei>
   equivalentPLMNs [12] PLMNList OPTIONAL,
   --<iei format="tlv">32</iei>
   pdpContextStatus [13] PDPContextStatus OPTIONAL,
   --<iei format="tv" length="1">B</iei>
   netFeatureSupport [14] NetFeatureSupp OPTIONAL,
   --<iei format="tlv">34</iei>
   emergencyNumList [15] EmergencyNumberList OPTIONAL,
   --<iei format="tlv">35</iei>
   mbmsContextStatus [16] MBMSContextStatus OPTIONAL,
   --<iei format="tv" length="1">A</iei>
   requestedMSInfo [17] RequestedMSInfo OPTIONAL,
   --<iei format="tlv">37</iei>
   t3319Value [18] GPRSTimer2 OPTIONAL,
   --<iei format="tlv">38</iei>
   t3323Value [19] GPRSTimer2 OPTIONAL,
   ...,
   [[ 10:
      t3312Value [20] GPRSTimer3 OPTIONAL
   ]],
   [[ 11:
      addnNetFeatureSupport [21] AddnNetFeatureSupport OPTIONAL
   ]],
   [[ 12:
      t3324Value [22] GPRSTimer2 OPTIONAL
   ]],
   [[ 13:
      extDRXParams [23] ExtDRXParams OPTIONAL,
      userPlaneIntegInd [24] UserPlaneIntegInd OPTIONAL,
      replayMSNetCapability [25] MSNetworkCapability OPTIONAL,
      replayMSRadioAccessCap [26] MSRadioAccessCapability OPTIONAL
   ]],
   [[ 14:
      dcnId [27] DcnID OPTIONAL,
      plmnCnId [28] PlmnCnID OPTIONAL,
      non3GPPNetPolicies [29] Non3GPPNetPolicies OPTIONAL
   ]]
}

RoutingAreaUpdateComplete ::= SEQUENCE {
   --<iei format="tlv">26</iei>
   receiveNPDUNumberList [0] ReceiveNPDUNumberList OPTIONAL,
   --<iei format="tlv">27</iei>
   interRATInfoContainer [1] InterRATInfoContainer OPTIONAL,
   --<iei format="tlv">2B</iei>
   eUTRANInterRATInfoContainer [2] E-UTRANInterRATInfoContainer OPTIONAL
}

RoutingAreaUpdateReject ::= SEQUENCE {
   gmmCause [0] GMMCauseValue,
   spare [1] INTEGER (0..15) DEFAULT 0,
   forceToStandby [2] ForceToStandbyValue,
   --<iei format="tlv">2A</iei>
   gprsTimer2 [3] GPRSTimer2 OPTIONAL,
   ...,
   [[ 10:
      t3346Value [4] GPRSTimer2 OPTIONAL
   ]]
}

GMMInformation ::= SEQUENCE {
   --<iei format="tlv">43</iei>
   fullNetName [0] NetworkName OPTIONAL,
   --<iei format="tlv">45</iei>
   shortNetName [1] NetworkName OPTIONAL,
   --<iei format="tv" length="2">46</iei>
   localTimeZone [2] TimeZone OPTIONAL,
   --<iei format="tv" length="8">47</iei>
   universalAndLocalTimeZone [3] TimeZoneAndTime OPTIONAL,
   --<iei format="tlv">48</iei>
   lsaIdentity [4] LSAIdentifier OPTIONAL,
   --<iei format="tlv">49</iei>
   networkDST [5] DaylightSavingTime OPTIONAL
}

ServiceRequest ::= SEQUENCE {
   serviceType [0] ServiceType,
   ciphKeySeqNum [1] CiphKeySeqNum,
   mobileIdentity [2] EXPLICIT MobileIdentity,
   --<iei format="tlv">32</iei>
   pdpContextStatus [3] PDPContextStatus OPTIONAL,
   --<iei format="tlv">35</iei>
   mbmsContextStatus [4] MBMSContextStatus OPTIONAL,
   --<iei format="tlv">36</iei>
   uplinkDataStatus [5] UplinkDataStatus OPTIONAL,
   ...,
   [[ 10:
      deviceProperties [6] DeviceProperties OPTIONAL
   ]]
}

ServiceAccept ::= SEQUENCE {
   --<iei format="tlv">32</iei>
   pdpContextStatus [0] PDPContextStatus OPTIONAL,
   --<iei format="tlv">35</iei>
   mbmsContextStatus [1] MBMSContextStatus OPTIONAL
}

ServiceReject ::= SEQUENCE {
   gmmCause [0] GMMCauseValue,
   ...,
   [[ 10:
      t3346Value [1] GPRSTimer2 OPTIONAL
   ]]
}

ActivatePDPCtxtReq ::= SEQUENCE {
   requestedNSAPI [0] NSAPIValue,
   requestedLLCSAPI [1] LLCSAPIValue,
   requestedQOS [2] QualityOfService,
   requestedPDPAddr [3] PacketDataProtoAddr,
   --<iei format="tlv">28</iei>
   accessPointName [4] AccessPointName OPTIONAL,
   --<iei format="tlv">27</iei>
   protocolConfigOptions [5] ProtocolConfigOptions OPTIONAL,
   --<iei format="tv" length="1">A</iei>
   requestType [6] RequestTypeValue OPTIONAL,
   ...,
   [[ 10:
      deviceProperties [7] DeviceProperties OPTIONAL
   ]],
   [[ 13:
      nbifomContainer [8] NBIFOMContainer OPTIONAL
   ]],
   [[ 14:
      extProtoConfigOptions [9] ExtProtoConfigOptions OPTIONAL
   ]],
   [[ 15:
      extQOS [10] ExtQualityOfService OPTIONAL
   ]]
}

ActivatePDPCtxtAccept ::= SEQUENCE {
   negotiatedLLCSAPI [0] LLCSAPIValue,
   negotiatedQOS [1] QualityOfService,
   spare [2] INTEGER (0..15) DEFAULT 0,
   radioPriority [3] RadioPriorityValue,
   --<iei format="tlv">2B</iei>
   pdpAddress [4] PacketDataProtoAddr OPTIONAL,
   --<iei format="tlv">27</iei>
   protocolConfigOptions [5] ProtocolConfigOptions OPTIONAL,
   --<iei format="tlv">34</iei>
   packetFlowIdent [6] PacketFlowIdentValue OPTIONAL,
   --<iei format="tlv">39</iei>
   smCause [7] SMCause2Value OPTIONAL,
   ...,
   [[ 10:
      connectivityType [8] ConnectivityType OPTIONAL
   ]],
   [[ 12:
      wlanOffloadInd [9] WLANOffloadAccept OPTIONAL
   ]],
   [[ 13:
      nbifomContainer [10] NBIFOMContainer OPTIONAL
   ]],
   [[ 14:
      extProtoConfigOptions [11] ExtProtoConfigOptions OPTIONAL
   ]],
   [[ 15:
      extQOS [12] ExtQualityOfService OPTIONAL
   ]]
}

ActivateSecondaryPDPCtxtRqst ::= SEQUENCE {
   requestedNSAPI [0] NSAPIValue,
   requestedLLCSAPI [1] LLCSAPIValue,
   requestedQOS [2] QualityOfService,
   linkedTI [3] LinkedTI,
   --<iei format="tlv">36</iei>
   trafficFlowTemplate [4] TFT OPTIONAL,
   --<iei format="tlv">27</iei>
   protocolConfigOptions [5] ProtocolConfigOptions OPTIONAL,
   ...,
   [[ 10:
      deviceProperties [6] DeviceProperties OPTIONAL
   ]],
   [[ 13:
      nbifomContainer [7] NBIFOMContainer OPTIONAL
   ]],
   [[ 14:
      extProtoConfigOptions [8] ExtProtoConfigOptions OPTIONAL
   ]],
   [[ 15:
      extQOS [9] ExtQualityOfService OPTIONAL
   ]]
}

ActivateSecondaryPDPCtxtAcc ::= SEQUENCE {
   negotiatedLLCSAPI [0] LLCSAPIValue,
   negotiatedQOS [1] QualityOfService,
   spare [2] INTEGER (0..15) DEFAULT 0,
   radioPriority [3] RadioPriorityValue,
   --<iei format="tlv">34</iei>
   packetFlowIdent [4] PacketFlowIdentValue OPTIONAL,
   --<iei format="tlv">27</iei>
   protocolConfigOptions [5] ProtocolConfigOptions OPTIONAL,
   ...,
   [[ 12:
      wlanOffloadInd [6] WLANOffloadAccept OPTIONAL
   ]],
   [[ 13:
      nbifomContainer [7] NBIFOMContainer OPTIONAL
   ]],
   [[ 14:
      extProtoConfigOptions [8] ExtProtoConfigOptions OPTIONAL
   ]],
   [[ 15:
      extQOS [9] ExtQualityOfService OPTIONAL
   ]]
}

RequestPDPCtxtAct ::= SEQUENCE {
   offeredPDPAddress [0] PacketDataProtoAddr,
   --<iei format="tlv">28</iei>
   accessPointName [1] AccessPointName OPTIONAL,
   --<iei format="tlv">27</iei>
   protocolConfigOptions [2] ProtocolConfigOptions OPTIONAL,
   ...,
   [[ 13:
      nbifomContainer [3] NBIFOMContainer OPTIONAL
   ]],
   [[ 14:
      extProtoConfigOptions [4] ExtProtoConfigOptions OPTIONAL
   ]]
}

RequestPDPCtxtActRej ::= SEQUENCE {
   smCause [0] SMCauseValue,
   --<iei format="tlv">27</iei>
   protocolConfigOptions [1] ProtocolConfigOptions OPTIONAL,
   ...,
   [[ 13:
      nbifomContainer [2] NBIFOMContainer OPTIONAL
   ]],
   [[ 14:
      extProtoConfigOptions [3] ExtProtoConfigOptions OPTIONAL
   ]]
}

ModifyPDPCtxtRqstNetToMS ::= SEQUENCE {
   spare [0] INTEGER (0..15) DEFAULT 0,
   radioPriority [1] RadioPriorityValue,
   requestedLLCSAPI [2] LLCSAPIValue,
   newQOS [3] QualityOfService,
   --<iei format="tlv">2B</iei>
   pdpAddress [4] PacketDataProtoAddr OPTIONAL,
   --<iei format="tlv">34</iei>
   packetFlowIdent [5] PacketFlowIdentValue OPTIONAL,
   --<iei format="tlv">27</iei>
   protocolConfigOptions [6] ProtocolConfigOptions OPTIONAL,
   --<iei format="tlv">36</iei>
   trafficFlowTemplate [7] TFT OPTIONAL,
   ...,
   [[ 12:
      wlanOffloadInd [8] WLANOffloadAccept OPTIONAL
   ]],
   [[ 13:
      nbifomContainer [9] NBIFOMContainer OPTIONAL
   ]],
   [[ 14:
      extProtoConfigOptions [10] ExtProtoConfigOptions OPTIONAL
   ]],
   [[ 15:
      extQOS [11] ExtQualityOfService OPTIONAL
   ]]
}

ModifyPDPCtxtRqstMSToNet ::= SEQUENCE {
   --<iei format="tv" length="2">32</iei>
   requestedLLCSAPI [0] LLCSAPIValue OPTIONAL,
   --<iei format="tlv">30</iei>
   requestedNewQOS [1] QualityOfService OPTIONAL,
   --<iei format="tlv">31</iei>
   newTFT [2] TFT OPTIONAL,
   --<iei format="tlv">27</iei>
   protocolConfigOptions [3] ProtocolConfigOptions OPTIONAL,
   ...,
   [[ 10:
      deviceProperties [4] DeviceProperties OPTIONAL
   ]],
   [[ 13:
      nbifomContainer [5] NBIFOMContainer OPTIONAL
   ]],
   [[ 14:
      extProtoConfigOptions [6] ExtProtoConfigOptions OPTIONAL
   ]],
   [[ 15:
      extQOS [7] ExtQualityOfService OPTIONAL
   ]]
}

ModifyPDPCtxtAccMSToNet ::= SEQUENCE {
   --<iei format="tlv">27</iei>
   protocolConfigOptions [0] ProtocolConfigOptions OPTIONAL,
   ...,
   [[ 13:
      nbifomContainer [1] NBIFOMContainer OPTIONAL
   ]],
   [[ 14:
      extProtoConfigOptions [2] ExtProtoConfigOptions OPTIONAL
   ]]
}

ModifyPDPCtxtAccNetToMS ::= SEQUENCE {
   --<iei format="tlv">30</iei>
   negotiatedQOS [0] QualityOfService OPTIONAL,
   --<iei format="tv" length="2">32</iei>
   negotiatedLLCSAPI [1] LLCSAPIValue OPTIONAL,
   --<iei format="tv" length="1">8</iei>
   newRadioPriority [2] RadioPriorityValue OPTIONAL,
   --<iei format="tlv">34</iei>
   packetFlowIdent [3] PacketFlowIdentValue OPTIONAL,
   --<iei format="tlv">27</iei>
   protocolConfigOptions [4] ProtocolConfigOptions OPTIONAL,
   ...,
   [[ 12:
      wlanOffloadInd [5] WLANOffloadAccept OPTIONAL
   ]],
   [[ 13:
      nbifomContainer [6] NBIFOMContainer OPTIONAL
   ]],
   [[ 14:
      extProtoConfigOptions [7] ExtProtoConfigOptions OPTIONAL
   ]],
   [[ 15:
      extQOS [8] ExtQualityOfService OPTIONAL
   ]]
}

DeactivatePDPCtxtReq ::= SEQUENCE {
   smCause [0] SMCauseValue,
   --<iei format="tv" length="1">9</iei>
   tearDownIndicator [1] TDIValue OPTIONAL,
   --<iei format="tlv">27</iei>
   protocolConfigOptions [2] ProtocolConfigOptions OPTIONAL,
   --<iei format="tlv">35</iei>
   mbmsPCO [3] MBMS-PCO OPTIONAL,
   ...,
   [[ 11:
      t3396Value [4] GPRSTimer3 OPTIONAL
   ]],
   [[ 12:
      wlanOffloadInd [5] WLANOffloadAccept OPTIONAL
   ]],
   [[ 14:
      extProtoConfigOptions [6] ExtProtoConfigOptions OPTIONAL
   ]]
}

DeactivatePDPCtxtAcc ::= SEQUENCE {
   --<iei format="tlv">27</iei>
   protocolConfigOptions [0] ProtocolConfigOptions OPTIONAL,
   --<iei format="tlv">35</iei>
   mbmsPCO [1] MBMS-PCO OPTIONAL,
   ...,
   [[ 14:
      extProtoConfigOptions [2] ExtProtoConfigOptions OPTIONAL
   ]]
}

RqstSecondaryPDPCtxtAct ::= SEQUENCE {
   requiredQOS [0] QualityOfService,
   linkedTI [1] LinkedTI,
   --<iei format="tlv">36</iei>
   trafficFlowTemplate [2] TFT OPTIONAL,
   --<iei format="tlv">27</iei>
   protocolConfigOptions [3] ProtocolConfigOptions OPTIONAL,
   ...,
   [[ 12:
      wlanOffloadInd [4] WLANOffloadAccept OPTIONAL
   ]],
   [[ 13:
      nbifomContainer [5] NBIFOMContainer OPTIONAL
   ]],
   [[ 14:
      extProtoConfigOptions [6] ExtProtoConfigOptions OPTIONAL
   ]],
   [[ 15:
      extQOS [7] ExtQualityOfService OPTIONAL
   ]]
}

RqstSecondaryPDPCtxtActRej ::= SEQUENCE {
   smCause [0] SMCauseValue,
   --<iei format="tlv">27</iei>
   protocolConfigOptions [1] ProtocolConfigOptions OPTIONAL,
   ...,
   [[ 13:
      nbifomContainer [2] NBIFOMContainer OPTIONAL
   ]],
   [[ 14:
      extProtoConfigOptions [3] ExtProtoConfigOptions OPTIONAL
   ]]
}

ActivateMBMSCtxtReq ::= SEQUENCE {
   requestedMBMSNSAPI [0] EnhancedNSAPIValue,
   requestedLLCSAPI [1] LLCSAPIValue,
   supportedMBMSBearerCaps [2] MBMSBearerCaps,
   requestedMulticastAddr [3] PacketDataProtoAddr,
   accessPointName [4] AccessPointName,
   --<iei format="tlv">35</iei>
   mbmsPCO [5] MBMS-PCO OPTIONAL,
   ...,
   [[ 10:
      deviceProperties [6] DeviceProperties OPTIONAL
   ]]
}

ActivateMBMSCtxtAcc ::= SEQUENCE {
   tmgi [0] TMGI, -- Temporary mobile group identity 
   negotiatedLLCSAPI [1] LLCSAPIValue,
   --<iei format="tlv">35</iei>
   mbmsPCO [2] MBMS-PCO OPTIONAL
}

ActivateMBMSCtxtRej ::= SEQUENCE {
   smCause [0] SMCauseValue,
   --<iei format="tlv">35</iei>
   mbmsPCO [1] MBMS-PCO OPTIONAL,
   ...,
   [[ 10:
      t3396Value [2] GPRSTimer3 OPTIONAL
   ]],
   [[ 13:
      reattemptInd [3] ReattemptInd OPTIONAL
   ]]
}

RequestMBMSCtxtAct ::= SEQUENCE {
   linkedNSAPI [0] NSAPIValue,
   offeredMulticastAddr [1] PacketDataProtoAddr,
   accessPointName [2] AccessPointName,
   --<iei format="tlv">35</iei>
   mbmsPCO [3] MBMS-PCO OPTIONAL
}

RequestMBMSCtxtActRej ::= SEQUENCE {
   smCause [0] SMCauseValue,
   --<iei format="tlv">35</iei>
   mbmsPCO [1] MBMS-PCO OPTIONAL
}

PDU ::= SEQUENCE {
   -- L3 header, octet 1, bits 5 thru 8
   --<inline/>
   --<cDecSrcFname>TS24008MsgDec_PDU_l3HdrOpts.c</cDecSrcFname>
   l3HdrOpts [0] EXPLICIT CHOICE {
      skipInd [0] INTEGER (0..15),
      --<inline/>
      --<selector element="protoDiscr" value="callCtrl,sessMgmt"/>
      transId [1] SEQUENCE {
         flag [0] BOOLEAN,
         --<cEncSrcFname>TS24008MsgEnc_PDU_transId.c</cEncSrcFname>
         value [1] INTEGER (0..255)
      }
   },
   protoDiscr [1] NAS-PROTOCOL-CLASS.&protoDiscr ({TS24008-IE-OBJECTSET}),
   --<cEncSrcFname>TS24008MsgEnc_PDU_sendSeqNum.c</cEncSrcFname>
   --<cDecSrcFname>TS24008MsgDec_PDU_sendSeqNum.c</cDecSrcFname>
   sendSeqNum [2] INTEGER (0..3) OPTIONAL,
   --<cEncSrcFname>TS24008MsgEnc_PDU_msgType.c</cEncSrcFname>
   --<cDecSrcFname>TS24008MsgDec_PDU_msgType.c</cDecSrcFname>
   msgType [3] NAS-PROTOCOL-CLASS.&msgType ({TS24008-IE-OBJECTSET}) (0..255),
   data [4] EXPLICIT NAS-PROTOCOL-CLASS.&Value ({TS24008-IE-OBJECTSET}{@
      protoDiscr,@msgType})
}

-- Value assignments

mt-AuthenticationReject INTEGER ::= 17

mt-AuthenticationRequest INTEGER ::= 18

mt-AuthenticationResponse INTEGER ::= 20

mt-AuthenticationFailure INTEGER ::= 28

mt-CMReestabRequest INTEGER ::= 40

mt-CMServiceAccept INTEGER ::= 33

mt-CMServicePrompt INTEGER ::= 37

mt-CMServiceReject INTEGER ::= 34

mt-CMServiceAbort INTEGER ::= 35

mt-Abort INTEGER ::= 41

mt-CMServiceRequest INTEGER ::= 36

mt-IdentityRequest INTEGER ::= 24

mt-IdentityResponse INTEGER ::= 25

mt-IMSIDetachInd INTEGER ::= 1

mt-LocUpdatingAccept INTEGER ::= 2

mt-LocUpdatingReject INTEGER ::= 4

mt-LocUpdatingRequest INTEGER ::= 8

mt-MMInformation INTEGER ::= 50

mt-MMStatus INTEGER ::= 49

mt-TMSIReallocCmd INTEGER ::= 26

mt-TMSIReallocCmplt INTEGER ::= 27

mt-MMNull INTEGER ::= 48

mt-Alerting INTEGER ::= 1

mt-CallConfirmed INTEGER ::= 8

mt-CallProceeding INTEGER ::= 2

mt-CongestionControl INTEGER ::= 57

mt-Connect INTEGER ::= 7

mt-ConnectAck INTEGER ::= 15

mt-Disconnect INTEGER ::= 37

mt-EmergencySetup INTEGER ::= 14

mt-FacilityMsg INTEGER ::= 58

mt-Hold INTEGER ::= 24

mt-HoldAck INTEGER ::= 25

mt-HoldReject INTEGER ::= 26

mt-Modify INTEGER ::= 23

mt-ModifyComplete INTEGER ::= 31

mt-ModifyReject INTEGER ::= 19

mt-Notify INTEGER ::= 62

mt-Progress INTEGER ::= 3

mt-CC-Establishment INTEGER ::= 4

mt-CC-EstablishmentConfirmed INTEGER ::= 6

mt-Release INTEGER ::= 45

mt-Recall INTEGER ::= 11

mt-ReleaseComplete INTEGER ::= 42

mt-Retrieve INTEGER ::= 28

mt-RetrieveAck INTEGER ::= 29

mt-RetrieveReject INTEGER ::= 30

mt-Setup INTEGER ::= 5

mt-StartCC INTEGER ::= 9

mt-StartDTMF INTEGER ::= 53

mt-StartDTMFAck INTEGER ::= 54

mt-StartDTMFReject INTEGER ::= 55

mt-Status INTEGER ::= 61

mt-StatusEnquiry INTEGER ::= 52

mt-StopDTMF INTEGER ::= 49

mt-StopDTMFAck INTEGER ::= 50

mt-UserInfo INTEGER ::= 16

mt-AttachRequest INTEGER ::= 1

mt-AttachAccept INTEGER ::= 2

mt-AttachComplete INTEGER ::= 3

mt-AttachReject INTEGER ::= 4

mt-DetachRequest INTEGER ::= 5

mt-DetachAccept INTEGER ::= 6

mt-P-TMSIReallocCmd INTEGER ::= 16

mt-P-TMSIReallocCmplt INTEGER ::= 17

mt-AuthAndCiphRequest INTEGER ::= 18

mt-AuthAndCiphResponse INTEGER ::= 19

mt-AuthAndCiphFailure INTEGER ::= 28

mt-AuthAndCiphReject INTEGER ::= 20

mt-GMMIdentityRequest INTEGER ::= 21

mt-GMMIdentityResponse INTEGER ::= 22

mt-RoutingAreaUpdateRequest INTEGER ::= 8

mt-RoutingAreaUpdateAccept INTEGER ::= 9

mt-RoutingAreaUpdateComplete INTEGER ::= 10

mt-RoutingAreaUpdateReject INTEGER ::= 11

mt-GMMStatus INTEGER ::= 32

mt-GMMInformation INTEGER ::= 33

mt-ServiceRequest INTEGER ::= 12

mt-ServiceAccept INTEGER ::= 13

mt-ServiceReject INTEGER ::= 14

mt-ActivatePDPCtxtReq INTEGER ::= 65

mt-ActivatePDPCtxtAccept INTEGER ::= 66

mt-ActivatePDPCtxtReject INTEGER ::= 67

mt-ActivateSecondaryPDPCtxtRqst INTEGER ::= 77

mt-ActivateSecondaryPDPCtxtAcc INTEGER ::= 78

mt-ActivateSecondaryPDPCtxtRej INTEGER ::= 79

mt-RequestPDPCtxtAct INTEGER ::= 68

mt-RequestPDPCtxtActRej INTEGER ::= 69

mt-ModifyPDPCtxtRqstNetToMS INTEGER ::= 72

mt-ModifyPDPCtxtRqstMSToNet INTEGER ::= 74

mt-ModifyPDPCtxtAccMSToNet INTEGER ::= 73

mt-ModifyPDPCtxtAccNetToMS INTEGER ::= 75

mt-ModifyPDPCtxtRej INTEGER ::= 76

mt-DeactivatePDPCtxtReq INTEGER ::= 70

mt-DeactivatePDPCtxtAcc INTEGER ::= 71

mt-RqstSecondaryPDPCtxtAct INTEGER ::= 91

mt-RqstSecondaryPDPCtxtActRej INTEGER ::= 92

mt-Notification INTEGER ::= 93

mt-SMStatus INTEGER ::= 85

mt-ActivateMBMSCtxtReq INTEGER ::= 86

mt-ActivateMBMSCtxtAcc INTEGER ::= 87

mt-ActivateMBMSCtxtRej INTEGER ::= 88

mt-RequestMBMSCtxtAct INTEGER ::= 89

mt-RequestMBMSCtxtActRej INTEGER ::= 90


-- Information Object definitions

obj-AuthenticationReject NAS-PROTOCOL-CLASS ::= {
   &protoDiscr mobMgmt, 
   &msgType mt-AuthenticationReject, 
   &Value NULL
}


obj-AuthenticationRequest NAS-PROTOCOL-CLASS ::= {
   &protoDiscr mobMgmt, 
   &msgType mt-AuthenticationRequest, 
   &Value AuthenticationRequest
}


obj-AuthenticationResponse NAS-PROTOCOL-CLASS ::= {
   &protoDiscr mobMgmt, 
   &msgType mt-AuthenticationResponse, 
   &Value AuthenticationResponse
}


obj-AuthenticationFailure NAS-PROTOCOL-CLASS ::= {
   &protoDiscr mobMgmt, 
   &msgType mt-AuthenticationFailure, 
   &Value AuthenticationFailure
}


obj-CMReestabRequest NAS-PROTOCOL-CLASS ::= {
   &protoDiscr mobMgmt, 
   &msgType mt-CMReestabRequest, 
   &Value CMReestabRequest
}


obj-CMServiceAccept NAS-PROTOCOL-CLASS ::= {
   &protoDiscr mobMgmt, 
   &msgType mt-CMServiceAccept, 
   &Value NULL
}


obj-CMServicePrompt NAS-PROTOCOL-CLASS ::= {
   &protoDiscr mobMgmt, 
   &msgType mt-CMServicePrompt, 
   &Value CMServicePrompt
}


obj-CMServiceReject NAS-PROTOCOL-CLASS ::= {
   &protoDiscr mobMgmt, 
   &msgType mt-CMServiceReject, 
   &Value CMServiceReject
}


obj-CMServiceAbort NAS-PROTOCOL-CLASS ::= {
   &protoDiscr mobMgmt, 
   &msgType mt-CMServiceAbort, 
   &Value NULL
}


obj-Abort NAS-PROTOCOL-CLASS ::= {
   &protoDiscr mobMgmt, 
   &msgType mt-Abort, 
   &Value Abort
}


obj-CMServiceRequest NAS-PROTOCOL-CLASS ::= {
   &protoDiscr mobMgmt, 
   &msgType mt-CMServiceRequest, 
   &Value CMServiceRequest
}


obj-IdentityRequest NAS-PROTOCOL-CLASS ::= {
   &protoDiscr mobMgmt, 
   &msgType mt-IdentityRequest, 
   &Value IdentityRequest
}


obj-IdentityResponse NAS-PROTOCOL-CLASS ::= {
   &protoDiscr mobMgmt, 
   &msgType mt-IdentityResponse, 
   &Value IdentityResponse
}


obj-IMSIDetachInd NAS-PROTOCOL-CLASS ::= {
   &protoDiscr mobMgmt, 
   &msgType mt-IMSIDetachInd, 
   &Value IMSIDetachInd
}


obj-LocUpdatingAccept NAS-PROTOCOL-CLASS ::= {
   &protoDiscr mobMgmt, 
   &msgType mt-LocUpdatingAccept, 
   &Value LocUpdatingAccept
}


obj-LocUpdatingReject NAS-PROTOCOL-CLASS ::= {
   &protoDiscr mobMgmt, 
   &msgType mt-LocUpdatingReject, 
   &Value LocUpdatingReject
}


obj-LocUpdatingRequest NAS-PROTOCOL-CLASS ::= {
   &protoDiscr mobMgmt, 
   &msgType mt-LocUpdatingRequest, 
   &Value LocUpdatingRequest
}


obj-MMInformation NAS-PROTOCOL-CLASS ::= {
   &protoDiscr mobMgmt, 
   &msgType mt-MMInformation, 
   &Value MMInformation
}


obj-MMStatus NAS-PROTOCOL-CLASS ::= {
   &protoDiscr mobMgmt, 
   &msgType mt-MMStatus, 
   &Value MMStatus
}


obj-TMSIReallocCmd NAS-PROTOCOL-CLASS ::= {
   &protoDiscr mobMgmt, 
   &msgType mt-TMSIReallocCmd, 
   &Value TMSIReallocCmd
}


obj-TMSIReallocCmplt NAS-PROTOCOL-CLASS ::= {
   &protoDiscr mobMgmt, 
   &msgType mt-TMSIReallocCmplt, 
   &Value NULL
}


obj-MMNull NAS-PROTOCOL-CLASS ::= {
   &protoDiscr mobMgmt, 
   &msgType mt-MMNull, 
   &Value NULL
}


obj-Alerting NAS-PROTOCOL-CLASS ::= {
   &protoDiscr callCtrl, 
   &msgType mt-Alerting, 
   &Value Alerting
}


obj-CallConfirmed NAS-PROTOCOL-CLASS ::= {
   &protoDiscr callCtrl, 
   &msgType mt-CallConfirmed, 
   &Value CallConfirmed
}


obj-CallProceeding NAS-PROTOCOL-CLASS ::= {
   &protoDiscr callCtrl, 
   &msgType mt-CallProceeding, 
   &Value CallProceeding
}


obj-CongestionControl NAS-PROTOCOL-CLASS ::= {
   &protoDiscr callCtrl, 
   &msgType mt-CongestionControl, 
   &Value CongestionControl
}


obj-Connect NAS-PROTOCOL-CLASS ::= {
   &protoDiscr callCtrl, 
   &msgType mt-Connect, 
   &Value Connect
}


obj-ConnectAck NAS-PROTOCOL-CLASS ::= {
   &protoDiscr callCtrl, 
   &msgType mt-ConnectAck, 
   &Value NULL
}


obj-Disconnect NAS-PROTOCOL-CLASS ::= {
   &protoDiscr callCtrl, 
   &msgType mt-Disconnect, 
   &Value Disconnect
}


obj-EmergencySetup NAS-PROTOCOL-CLASS ::= {
   &protoDiscr callCtrl, 
   &msgType mt-EmergencySetup, 
   &Value EmergencySetup
}


obj-FacilityMsg NAS-PROTOCOL-CLASS ::= {
   &protoDiscr callCtrl, 
   &msgType mt-FacilityMsg, 
   &Value FacilityMsg
}


obj-Hold NAS-PROTOCOL-CLASS ::= {
   &protoDiscr callCtrl, 
   &msgType mt-Hold, 
   &Value NULL
}


obj-HoldAck NAS-PROTOCOL-CLASS ::= {
   &protoDiscr callCtrl, 
   &msgType mt-HoldAck, 
   &Value NULL
}


obj-HoldReject NAS-PROTOCOL-CLASS ::= {
   &protoDiscr callCtrl, 
   &msgType mt-HoldReject, 
   &Value Cause
}


obj-Modify NAS-PROTOCOL-CLASS ::= {
   &protoDiscr callCtrl, 
   &msgType mt-Modify, 
   &Value Modify
}


obj-ModifyComplete NAS-PROTOCOL-CLASS ::= {
   &protoDiscr callCtrl, 
   &msgType mt-ModifyComplete, 
   &Value ModifyComplete
}


obj-ModifyReject NAS-PROTOCOL-CLASS ::= {
   &protoDiscr callCtrl, 
   &msgType mt-ModifyReject, 
   &Value ModifyReject
}


obj-Notify NAS-PROTOCOL-CLASS ::= {
   &protoDiscr callCtrl, 
   &msgType mt-Notify, 
   &Value NotificationIndicator
}


obj-Progress NAS-PROTOCOL-CLASS ::= {
   &protoDiscr callCtrl, 
   &msgType mt-Progress, 
   &Value Progress
}


obj-CC-Establishment NAS-PROTOCOL-CLASS ::= {
   &protoDiscr callCtrl, 
   &msgType mt-CC-Establishment, 
   &Value Setup-Container
}


obj-CC-EstablishmentConfirmed NAS-PROTOCOL-CLASS ::= {
   &protoDiscr callCtrl, 
   &msgType mt-CC-EstablishmentConfirmed, 
   &Value CC-EstablishmentConfirmed
}


obj-Release NAS-PROTOCOL-CLASS ::= {
   &protoDiscr callCtrl, 
   &msgType mt-Release, 
   &Value Release
}


obj-Recall NAS-PROTOCOL-CLASS ::= {
   &protoDiscr callCtrl, 
   &msgType mt-Recall, 
   &Value Recall
}


obj-ReleaseComplete NAS-PROTOCOL-CLASS ::= {
   &protoDiscr callCtrl, 
   &msgType mt-ReleaseComplete, 
   &Value ReleaseComplete
}


obj-Retrieve NAS-PROTOCOL-CLASS ::= {
   &protoDiscr callCtrl, 
   &msgType mt-Retrieve, 
   &Value NULL
}


obj-RetrieveAck NAS-PROTOCOL-CLASS ::= {
   &protoDiscr callCtrl, 
   &msgType mt-RetrieveAck, 
   &Value NULL
}


obj-RetrieveReject NAS-PROTOCOL-CLASS ::= {
   &protoDiscr callCtrl, 
   &msgType mt-RetrieveReject, 
   &Value Cause
}


obj-Setup NAS-PROTOCOL-CLASS ::= {
   &protoDiscr callCtrl, 
   &msgType mt-Setup, 
   &Value Setup
}


obj-StartCC NAS-PROTOCOL-CLASS ::= {
   &protoDiscr callCtrl, 
   &msgType mt-StartCC, 
   &Value StartCC
}


obj-StartDTMF NAS-PROTOCOL-CLASS ::= {
   &protoDiscr callCtrl, 
   &msgType mt-StartDTMF, 
   &Value StartDTMF
}


obj-StartDTMFAck NAS-PROTOCOL-CLASS ::= {
   &protoDiscr callCtrl, 
   &msgType mt-StartDTMFAck, 
   &Value StartDTMFAck
}


obj-StartDTMFReject NAS-PROTOCOL-CLASS ::= {
   &protoDiscr callCtrl, 
   &msgType mt-StartDTMFReject, 
   &Value Cause
}


obj-Status NAS-PROTOCOL-CLASS ::= {
   &protoDiscr callCtrl, 
   &msgType mt-Status, 
   &Value Status
}


obj-StatusEnquiry NAS-PROTOCOL-CLASS ::= {
   &protoDiscr callCtrl, 
   &msgType mt-StatusEnquiry, 
   &Value NULL
}


obj-StopDTMF NAS-PROTOCOL-CLASS ::= {
   &protoDiscr callCtrl, 
   &msgType mt-StopDTMF, 
   &Value NULL
}


obj-StopDTMFAck NAS-PROTOCOL-CLASS ::= {
   &protoDiscr callCtrl, 
   &msgType mt-StopDTMFAck, 
   &Value NULL
}


obj-UserInfo NAS-PROTOCOL-CLASS ::= {
   &protoDiscr callCtrl, 
   &msgType mt-UserInfo, 
   &Value UserInfo
}


obj-AttachRequest NAS-PROTOCOL-CLASS ::= {
   &protoDiscr gprsMobMgmt, 
   &msgType mt-AttachRequest, 
   &Value AttachRequest
}


obj-AttachAccept NAS-PROTOCOL-CLASS ::= {
   &protoDiscr gprsMobMgmt, 
   &msgType mt-AttachAccept, 
   &Value AttachAccept
}


obj-AttachComplete NAS-PROTOCOL-CLASS ::= {
   &protoDiscr gprsMobMgmt, 
   &msgType mt-AttachComplete, 
   &Value AttachComplete
}


obj-AttachReject NAS-PROTOCOL-CLASS ::= {
   &protoDiscr gprsMobMgmt, 
   &msgType mt-AttachReject, 
   &Value AttachReject
}


obj-DetachRequest NAS-PROTOCOL-CLASS ::= {
   &protoDiscr gprsMobMgmt, 
   &msgType mt-DetachRequest, 
   &Value DetachRequest
}


obj-DetachAccept NAS-PROTOCOL-CLASS ::= {
   &protoDiscr gprsMobMgmt, 
   &msgType mt-DetachAccept, 
   &Value DetachAccept
}


obj-P-TMSIReallocCmd NAS-PROTOCOL-CLASS ::= {
   &protoDiscr gprsMobMgmt, 
   &msgType mt-P-TMSIReallocCmd, 
   &Value P-TMSIReallocCmd
}


obj-P-TMSIReallocCmplt NAS-PROTOCOL-CLASS ::= {
   &protoDiscr gprsMobMgmt, 
   &msgType mt-P-TMSIReallocCmplt, 
   &Value NULL
}


obj-AuthAndCiphRequest NAS-PROTOCOL-CLASS ::= {
   &protoDiscr gprsMobMgmt, 
   &msgType mt-AuthAndCiphRequest, 
   &Value AuthAndCiphRequest
}


obj-AuthAndCiphResponse NAS-PROTOCOL-CLASS ::= {
   &protoDiscr gprsMobMgmt, 
   &msgType mt-AuthAndCiphResponse, 
   &Value AuthAndCiphResponse
}


obj-AuthAndCiphFailure NAS-PROTOCOL-CLASS ::= {
   &protoDiscr gprsMobMgmt, 
   &msgType mt-AuthAndCiphFailure, 
   &Value AuthAndCiphFailure
}


obj-AuthAndCiphReject NAS-PROTOCOL-CLASS ::= {
   &protoDiscr gprsMobMgmt, 
   &msgType mt-AuthAndCiphReject, 
   &Value NULL
}


obj-GMMIdentityRequest NAS-PROTOCOL-CLASS ::= {
   &protoDiscr gprsMobMgmt, 
   &msgType mt-GMMIdentityRequest, 
   &Value GMMIdentityRequest
}


obj-GMMIdentityResponse NAS-PROTOCOL-CLASS ::= {
   &protoDiscr gprsMobMgmt, 
   &msgType mt-GMMIdentityResponse, 
   &Value GMMIdentityResponse
}


obj-RoutingAreaUpdateRequest NAS-PROTOCOL-CLASS ::= {
   &protoDiscr gprsMobMgmt, 
   &msgType mt-RoutingAreaUpdateRequest, 
   &Value RoutingAreaUpdateRequest
}


obj-RoutingAreaUpdateAccept NAS-PROTOCOL-CLASS ::= {
   &protoDiscr gprsMobMgmt, 
   &msgType mt-RoutingAreaUpdateAccept, 
   &Value RoutingAreaUpdateAccept
}


obj-RoutingAreaUpdateComplete NAS-PROTOCOL-CLASS ::= {
   &protoDiscr gprsMobMgmt, 
   &msgType mt-RoutingAreaUpdateComplete, 
   &Value RoutingAreaUpdateComplete
}


obj-RoutingAreaUpdateReject NAS-PROTOCOL-CLASS ::= {
   &protoDiscr gprsMobMgmt, 
   &msgType mt-RoutingAreaUpdateReject, 
   &Value RoutingAreaUpdateReject
}


obj-GMMStatus NAS-PROTOCOL-CLASS ::= {
   &protoDiscr gprsMobMgmt, 
   &msgType mt-GMMStatus, 
   &Value GMMCauseValue
}


obj-GMMInformation NAS-PROTOCOL-CLASS ::= {
   &protoDiscr gprsMobMgmt, 
   &msgType mt-GMMInformation, 
   &Value GMMInformation
}


obj-ServiceRequest NAS-PROTOCOL-CLASS ::= {
   &protoDiscr gprsMobMgmt, 
   &msgType mt-ServiceRequest, 
   &Value ServiceRequest
}


obj-ServiceAccept NAS-PROTOCOL-CLASS ::= {
   &protoDiscr gprsMobMgmt, 
   &msgType mt-ServiceAccept, 
   &Value ServiceAccept
}


obj-ServiceReject NAS-PROTOCOL-CLASS ::= {
   &protoDiscr gprsMobMgmt, 
   &msgType mt-ServiceReject, 
   &Value ServiceReject
}


obj-ActivatePDPCtxtReq NAS-PROTOCOL-CLASS ::= {
   &protoDiscr sessMgmt, 
   &msgType mt-ActivatePDPCtxtReq, 
   &Value ActivatePDPCtxtReq
}


obj-ActivatePDPCtxtAccept NAS-PROTOCOL-CLASS ::= {
   &protoDiscr sessMgmt, 
   &msgType mt-ActivatePDPCtxtAccept, 
   &Value ActivatePDPCtxtAccept
}


obj-ActivatePDPCtxtReject NAS-PROTOCOL-CLASS ::= {
   &protoDiscr sessMgmt, 
   &msgType mt-ActivatePDPCtxtReject, 
   &Value ActivatePDPCtxtReject
}


obj-ActivateSecondaryPDPCtxtRqst NAS-PROTOCOL-CLASS ::= {
   &protoDiscr sessMgmt, 
   &msgType mt-ActivateSecondaryPDPCtxtRqst, 
   &Value ActivateSecondaryPDPCtxtRqst
}


obj-ActivateSecondaryPDPCtxtAcc NAS-PROTOCOL-CLASS ::= {
   &protoDiscr sessMgmt, 
   &msgType mt-ActivateSecondaryPDPCtxtAcc, 
   &Value ActivateSecondaryPDPCtxtAcc
}


obj-ActivateSecondaryPDPCtxtRej NAS-PROTOCOL-CLASS ::= {
   &protoDiscr sessMgmt, 
   &msgType mt-ActivateSecondaryPDPCtxtRej, 
   &Value ActivateSecondaryPDPCtxtRej
}


obj-RequestPDPCtxtAct NAS-PROTOCOL-CLASS ::= {
   &protoDiscr sessMgmt, 
   &msgType mt-RequestPDPCtxtAct, 
   &Value RequestPDPCtxtAct
}


obj-RequestPDPCtxtActRej NAS-PROTOCOL-CLASS ::= {
   &protoDiscr sessMgmt, 
   &msgType mt-RequestPDPCtxtActRej, 
   &Value RequestPDPCtxtActRej
}


obj-ModifyPDPCtxtRqstNetToMS NAS-PROTOCOL-CLASS ::= {
   &protoDiscr sessMgmt, 
   &msgType mt-ModifyPDPCtxtRqstNetToMS, 
   &Value ModifyPDPCtxtRqstNetToMS
}


obj-ModifyPDPCtxtRqstMSToNet NAS-PROTOCOL-CLASS ::= {
   &protoDiscr sessMgmt, 
   &msgType mt-ModifyPDPCtxtRqstMSToNet, 
   &Value ModifyPDPCtxtRqstMSToNet
}


obj-ModifyPDPCtxtAccMSToNet NAS-PROTOCOL-CLASS ::= {
   &protoDiscr sessMgmt, 
   &msgType mt-ModifyPDPCtxtAccMSToNet, 
   &Value ModifyPDPCtxtAccMSToNet
}


obj-ModifyPDPCtxtAccNetToMS NAS-PROTOCOL-CLASS ::= {
   &protoDiscr sessMgmt, 
   &msgType mt-ModifyPDPCtxtAccNetToMS, 
   &Value ModifyPDPCtxtAccNetToMS
}


obj-ModifyPDPCtxtRej NAS-PROTOCOL-CLASS ::= {
   &protoDiscr sessMgmt, 
   &msgType mt-ModifyPDPCtxtRej, 
   &Value ModifyPDPCtxtRej
}


obj-DeactivatePDPCtxtReq NAS-PROTOCOL-CLASS ::= {
   &protoDiscr sessMgmt, 
   &msgType mt-DeactivatePDPCtxtReq, 
   &Value DeactivatePDPCtxtReq
}


obj-DeactivatePDPCtxtAcc NAS-PROTOCOL-CLASS ::= {
   &protoDiscr sessMgmt, 
   &msgType mt-DeactivatePDPCtxtAcc, 
   &Value DeactivatePDPCtxtAcc
}


obj-RqstSecondaryPDPCtxtAct NAS-PROTOCOL-CLASS ::= {
   &protoDiscr sessMgmt, 
   &msgType mt-RqstSecondaryPDPCtxtAct, 
   &Value RqstSecondaryPDPCtxtAct
}


obj-RqstSecondaryPDPCtxtActRej NAS-PROTOCOL-CLASS ::= {
   &protoDiscr sessMgmt, 
   &msgType mt-RqstSecondaryPDPCtxtActRej, 
   &Value RqstSecondaryPDPCtxtActRej
}


obj-Notification NAS-PROTOCOL-CLASS ::= {
   &protoDiscr sessMgmt, 
   &msgType mt-Notification, 
   &Value SM-NotificationIndicator
}


obj-SMStatus NAS-PROTOCOL-CLASS ::= {
   &protoDiscr sessMgmt, 
   &msgType mt-SMStatus, 
   &Value SMCauseValue
}


obj-ActivateMBMSCtxtReq NAS-PROTOCOL-CLASS ::= {
   &protoDiscr sessMgmt, 
   &msgType mt-ActivateMBMSCtxtReq, 
   &Value ActivateMBMSCtxtReq
}


obj-ActivateMBMSCtxtAcc NAS-PROTOCOL-CLASS ::= {
   &protoDiscr sessMgmt, 
   &msgType mt-ActivateMBMSCtxtAcc, 
   &Value ActivateMBMSCtxtAcc
}


obj-ActivateMBMSCtxtRej NAS-PROTOCOL-CLASS ::= {
   &protoDiscr sessMgmt, 
   &msgType mt-ActivateMBMSCtxtRej, 
   &Value ActivateMBMSCtxtRej
}


obj-RequestMBMSCtxtAct NAS-PROTOCOL-CLASS ::= {
   &protoDiscr sessMgmt, 
   &msgType mt-RequestMBMSCtxtAct, 
   &Value RequestMBMSCtxtAct
}


obj-RequestMBMSCtxtActRej NAS-PROTOCOL-CLASS ::= {
   &protoDiscr sessMgmt, 
   &msgType mt-RequestMBMSCtxtActRej, 
   &Value RequestMBMSCtxtActRej
}


-- Information Object Set definitions

TS24008-IE-OBJECTSET NAS-PROTOCOL-CLASS ::= {obj-AuthenticationReject | 
   obj-AuthenticationRequest | obj-AuthenticationResponse | 
   obj-AuthenticationFailure | obj-CMReestabRequest | obj-CMServiceAccept | 
   obj-CMServicePrompt | obj-CMServiceReject | obj-CMServiceAbort | obj-Abort
    | obj-CMServiceRequest | obj-IdentityRequest | obj-IdentityResponse | 
   obj-IMSIDetachInd | obj-LocUpdatingAccept | obj-LocUpdatingReject | 
   obj-LocUpdatingRequest | obj-MMInformation | obj-MMStatus | 
   obj-TMSIReallocCmd | obj-TMSIReallocCmplt | obj-MMNull | obj-Alerting | 
   obj-CallConfirmed | obj-CallProceeding | obj-CongestionControl | obj-Connect
    | obj-ConnectAck | obj-Disconnect | obj-EmergencySetup | obj-FacilityMsg | 
   obj-Hold | obj-HoldAck | obj-HoldReject | obj-Modify | obj-ModifyComplete | 
   obj-ModifyReject | obj-Notify | obj-Progress | obj-CC-Establishment | 
   obj-CC-EstablishmentConfirmed | obj-Release | obj-Recall | 
   obj-ReleaseComplete | obj-Retrieve | obj-RetrieveAck | obj-RetrieveReject | 
   obj-Setup | obj-StartCC | obj-StartDTMF | obj-StartDTMFAck | 
   obj-StartDTMFReject | obj-Status | obj-StatusEnquiry | obj-StopDTMF | 
   obj-StopDTMFAck | obj-UserInfo | obj-AttachRequest | obj-AttachAccept | 
   obj-AttachComplete | obj-AttachReject | obj-DetachRequest | obj-DetachAccept
    | obj-P-TMSIReallocCmd | obj-P-TMSIReallocCmplt | obj-AuthAndCiphRequest | 
   obj-AuthAndCiphResponse | obj-AuthAndCiphFailure | obj-AuthAndCiphReject | 
   obj-GMMIdentityRequest | obj-GMMIdentityResponse | 
   obj-RoutingAreaUpdateRequest | obj-RoutingAreaUpdateAccept | 
   obj-RoutingAreaUpdateComplete | obj-RoutingAreaUpdateReject | obj-GMMStatus
    | obj-GMMInformation | obj-ServiceRequest | obj-ServiceAccept | 
   obj-ServiceReject | obj-ActivatePDPCtxtReq | obj-ActivatePDPCtxtAccept | 
   obj-ActivatePDPCtxtReject | obj-ActivateSecondaryPDPCtxtRqst | 
   obj-ActivateSecondaryPDPCtxtAcc | obj-ActivateSecondaryPDPCtxtRej | 
   obj-RequestPDPCtxtAct | obj-RequestPDPCtxtActRej | 
   obj-ModifyPDPCtxtRqstNetToMS | obj-ModifyPDPCtxtRqstMSToNet | 
   obj-ModifyPDPCtxtAccMSToNet | obj-ModifyPDPCtxtAccNetToMS | 
   obj-ModifyPDPCtxtRej | obj-DeactivatePDPCtxtReq | obj-DeactivatePDPCtxtAcc
    | obj-RqstSecondaryPDPCtxtAct | obj-RqstSecondaryPDPCtxtActRej | 
   obj-SMStatus | obj-ActivateMBMSCtxtReq | obj-ActivateMBMSCtxtAcc | 
   obj-ActivateMBMSCtxtRej | obj-RequestMBMSCtxtAct | obj-RequestMBMSCtxtActRej
   ,...}

END
TS24011IES DEFINITIONS AUTOMATIC TAGS ::= BEGIN

IMPORTS

TBCDString
FROM TS24008IES ;

-- Productions

-- 8.1.3 Message type 
-- 8.1.4.1 CP-User data element 
CPUserData ::= OCTET STRING (SIZE (0..249))

-- 8.2.2 Message type indicator (MTI) 
-- 8.2.5.1 Originator address element 
RPAddress ::= SEQUENCE {
   --<is3GLength/>
   length [0] INTEGER (0..11),
   --<first3GExtElem/>
   --<last3GExtElem/>
   octet3 [1] SEQUENCE {
      typeOfNumber [0] INTEGER (0..7),
      numberingPlanID [1] INTEGER (0..15)
   },
   --<length fixed-size="0"/>
   number [2] TBCDString
}

RPOriginatorAddress ::= RPAddress

-- 8.2.5.2 Destination address element 
RPDestinationAddress ::= RPAddress

-- 8.2.5.3 RP-User data element 
RPUserData ::= OCTET STRING (SIZE (0..233))

-- 8.1.4.2 CP-Cause element 
CPCauseValue ::= SEQUENCE {
   ext [0] BOOLEAN DEFAULT FALSE,
   value [1] INTEGER (0..127)
}

-- 8.2.5.4 RP-Cause element 
RPCauseElem ::= SEQUENCE {
   --<is3GLength/>
   length [0] INTEGER (1..2) DEFAULT 1,
   ext [1] BOOLEAN DEFAULT FALSE,
   causeValue [2] INTEGER (0..127),
   --<is3GVarLenList lengthElem="length"/>
   --<storage>array</storage>
   diagField [3] SEQUENCE (SIZE (0..1)) OF INTEGER (0..255)
}

END
TS24011Msgs DEFINITIONS AUTOMATIC TAGS ::= BEGIN

IMPORTS

L3HdrOptions, NAS-PROTOCOL-CLASS, SecProtMsgHeader, ProtoDiscr
FROM TS24007L3 

CPCauseValue, CPUserData, RPCauseElem, RPDestinationAddress, 
   RPOriginatorAddress, RPUserData
FROM TS24011IES ;

-- Productions

CPDATA ::= SEQUENCE {
   cpUserData [0] CPUserData
}

CPERROR ::= SEQUENCE {
   cpCause [0] CPCauseValue
}

CP-PDU ::= SEQUENCE {
   l3HdrOpts [0] EXPLICIT L3HdrOptions, -- L3 header, octet 1, bits 5 thru 8
   --<cDecSrcFname>PDU_protoDiscr.c</cDecSrcFname>
   protoDiscr [1] NAS-PROTOCOL-CLASS.&protoDiscr ({TS24011-OBJECTSET}),
   msgType [2] NAS-PROTOCOL-CLASS.&msgType ({TS24011-OBJECTSET}) (0..255),
   data [3] EXPLICIT NAS-PROTOCOL-CLASS.&Value ({TS24011-OBJECTSET}{@protoDiscr
      ,@msgType})
}

-- RP Message header 
RPHeader ::= SEQUENCE {
   spare [0] INTEGER (0..31) DEFAULT 0, -- should be set to 0
   rpMsgType [1] INTEGER (0..7),
   rpMsgRef [2] INTEGER (0..255)
}

-- 7.3.1.2 RP-DATA (MS To Network) 
--<is3GMessage/>
RPDataMSOriginating ::= SEQUENCE {
   origAddrLen [0] INTEGER (0..255) DEFAULT 0,
   destAddress [1] RPDestinationAddress,
   userData [2] RPUserData
}

-- 7.3.1.1 RP-DATA (Network to MS) 
--<is3GMessage/>
RPDataMSTerminated ::= SEQUENCE {
   origAddress [0] RPOriginatorAddress,
   destAddrLen [1] INTEGER (0..255) DEFAULT 0,
   userData [2] RPUserData
}

-- 7.3.2 RP-SMMA 
-- 7.3.3 RP-ACK 
--<is3GMessage/>
RP-ACK ::= SEQUENCE {
   --<iei format="tlv">41</iei>
   userData [0] RPUserData OPTIONAL
}

-- 7.3.4 RP-ERROR 
--<is3GMessage/>
RP-ERROR ::= SEQUENCE {
   rpCause [0] RPCauseElem,
   --<iei format="tlv">41</iei>
   userData [1] RPUserData OPTIONAL
}

RP-PDU ::= SEQUENCE {
   header [0] RPHeader,
   --<inline/>
   infoElem [1] EXPLICIT CHOICE {
      --<selector element="header.rpMsgType" value="0"/>
      dataToNet [0] RPDataMSOriginating,
      --<selector element="header.rpMsgType" value="1"/>
      dataToMS [1] RPDataMSTerminated,
      --<selector element="header.rpMsgType" value="2"/>
      ackToNet [2] RP-ACK,
      --<selector element="header.rpMsgType" value="3"/>
      ackToMS [3] RP-ACK,
      --<selector element="header.rpMsgType" value="4"/>
      errorToNet [4] RP-ERROR,
      --<selector element="header.rpMsgType" value="5"/>
      errorToMS [5] RP-ERROR,
      --<selector element="header.rpMsgType" value="6"/>
      smma [6] NULL
   }
}

-- Value assignments

mt-CP-DATA INTEGER ::= 1

mt-CP-ACK INTEGER ::= 4

mt-CP-ERROR INTEGER ::= 16


-- Information Object definitions

obj-CP-DATA NAS-PROTOCOL-CLASS ::= {
   &protoDiscr sms, 
   &msgType mt-CP-DATA, 
   &Value CPDATA
}


obj-CP-ACK NAS-PROTOCOL-CLASS ::= {
   &protoDiscr sms, 
   &msgType mt-CP-ACK, 
   &Value NULL
}


obj-CP-ERROR NAS-PROTOCOL-CLASS ::= {
   &protoDiscr sms, 
   &msgType mt-CP-ERROR, 
   &Value CPERROR
}


-- Information Object Set definitions

TS24011-OBJECTSET NAS-PROTOCOL-CLASS ::= {obj-CP-DATA | obj-CP-ACK | 
   obj-CP-ERROR}

END
TS24301IES DEFINITIONS AUTOMATIC TAGS ::= BEGIN

IMPORTS

IMEI, IMSI, MCCMNCPair, TBCDString, TimeZoneAndTime
FROM TS24008IES ;

-- Productions

-- 9.9.3.4 - Authentication response parameter 
AuthRespParam ::= OCTET STRING (SIZE (4..16))

-- 9.9.3.9 - EMM cause 
EMMCause ::= ENUMERATED { imsiUnkInHSS(2), illegalUE(3), imeiNotAccept(5), 
   illegalME(6), epsSvcNotAllowed(7), epsAndNonEPSSvcNotAllowed(8), 
   ueIdentNotDeriv(9), implDetach(10), plmnNotAllowed(11), 
   trkAreaNotAllowed(12), roamNotAllowed(13), epsSvcNotAllowInPLMN(14), 
   noCellsInTrkArea(15), mscTempNotReach(16), networkFailure(17), 
   csDomainNotAvail(18), esmFailure(19), macFailure(20), synchFailure(21), 
   congestion(22), ueSecCapMismat(23), secModeReject(24), notAuthForCSG(25), 
   nonEPSAuthUnaccept(26), redirTo5GRequired(31), reqSvcOptNotAuth(35), 
   csSvcTempUnavail(39), noEPSBearerCtxtAct(40), severeNetFailure(42), 
   semIncorrectMsg(95), invMandInfo(96), msgTypeNotExist(97), 
   msgTypeNotCompat(98), infoElemNotExist(99), condIEError(100), 
   msgNotCompat(101), unspecProtoErr(111), eMMCauseMAX(255) }

-- 9.9.3.15 - ESM message container 
--<length fixed-size="2"/>
ESMMessageContainer ::= OCTET STRING (SIZE (0..65535))

-- 9.9.3.22 - NAS message container 
NASMessageContainer ::= OCTET STRING (SIZE (2..251))

-- 9.9.3.25 - Nonce 
Nonce ::= OCTET STRING (SIZE (4))

-- 9.9.3.27 - Service type 
ServiceType ::= INTEGER { moCSFallback(0), mtCSFallBack(1), moCSFBEmergCall(2)
   , pktSvcsViaS1(8) } (0..15)

-- 9.9.3.28 - Short MAC 
ShortMAC ::= OCTET STRING (SIZE (2))

TrackingAreaCode ::= OCTET STRING (SIZE (2))

-- 9.9.3.39 - SS Code 
SSCode ::= INTEGER (0..255)

-- 9.9.3.40 - LCS indicator 
LCSIndicator ::= INTEGER (0..255)

-- 9.9.3.41 - LCS client identity 
LCSClientIdentity ::= OCTET STRING (SIZE (1..255))

-- 9.9.3.42 - Generic message container type 
GenMsgContainerType ::= ENUMERATED { lppMsgCont(1), lcsMsgCont(2), 
   genMsgContainerTypeMAX(255) }

-- 9.9.3.43 - Generic message container 
--<length fixed-size="2"/>
GenMessageContainer ::= OCTET STRING (SIZE (0..65535))

InformationType ::= ENUMERATED { itUEPagingProbInfo(0), itMAX(7) }

-- 9.9.4.4 - ESM cause 
ESMCause ::= ENUMERATED { operDeterBarring(8), insuffResources(26), 
   unkOrMissAPN(27), unknownPDNType(28), userAutheFailed(29), 
   reqRejectByServingGW(30), reqRejectUnspecified(31), svcOptNotSupp(32), 
   reqSvcOptNotSubscr(33), svcOptTempOutOfOrder(34), ptiAlreadyInUse(35), 
   regularDeactivation(36), epsQoSNotAccepted(37), networkFailure(38), 
   reactivateRequest(39), semErrorInTFTOp(41), synErrorInTFTOp(42), 
   invEPSBearerIdent(43), semErrorsInPktFilt(44), synErrorsInPktFilt(45), 
   ptiMismatch(47), lastPDNDisconnNotAllow(49), pdnTypeIPv4OnlyAllow(50), 
   pdnTypeIPv6OnlyAllow(51), singleAddrBearersOnlyAllow(52), esmInfoNotRcvd(53)
   , pdnConnNotExist(54), multPDNConnsForAPNNotAllow(55), 
   collWithNetwInitReq(56), pdnTypeIPv4v6OnlyAllow(57), 
   pdnTypeNonIPOnlyAllow(58), unsuppQCIValue(59), bearerHandlingNotSupp(60), 
   pdnTypeEthOnlyAllow(61), maxNumEPSBearersReached(65), reqAPNNotSupp(66), 
   invPTIValue(81), semIncorrectMessage(95), invMandatoryInfo(96), 
   msgTypeNonExistOrNotImpl(97), msgTypeNotCompatWithProtoState(98), 
   ieNonExistOrNotImpl(99), condIEError(100), msgNotCompatWithProtoState(101), 
   protocolErrorUnspecified(111), apnRestrValIncompWithBearerCtxt(112), 
   multAccToPdnNotAllowed(113), eSMCauseMAX(255) }

-- 9.9.4.6 - Linked EPS bearer identity 
LinkedEPSBearerIdent ::= INTEGER (0..15)

PDNTypeValue ::= ENUMERATED { ipv4(1), ipv6(2), ipv4v6(3), nonip(5), eth(6), 
   pdnMAX(7) }

RemoteUEAddrType ::= ENUMERATED { remUENoIp(0), remUEIpv4(1), remUEIpv6(2), 
   remUEMAX(7) }

-- 9.9.4.28 - Serving PLMN rate control 
ServPLMNRateCtrl ::= OCTET STRING (SIZE (2))

-- Common types
-- 9.9.2.1 - EPS bearer context status 
EPSBearerContextStatus ::= SEQUENCE {
   --<is3GLength/>
   length [0] INTEGER (2),
   -- first octet
   ebi7 [1] BOOLEAN,
   ebi6 [2] BOOLEAN,
   ebi5 [3] BOOLEAN,
   ebi4 [4] BOOLEAN,
   ebi3 [5] BOOLEAN,
   ebi2 [6] BOOLEAN,
   ebi1 [7] BOOLEAN,
   ebi0 [8] BOOLEAN DEFAULT FALSE,
   -- 2nd octet
   ebi15 [9] BOOLEAN,
   ebi14 [10] BOOLEAN,
   ebi13 [11] BOOLEAN,
   ebi12 [12] BOOLEAN,
   ebi11 [13] BOOLEAN,
   ebi10 [14] BOOLEAN,
   ebi9 [15] BOOLEAN,
   ebi8 [16] BOOLEAN
}

-- 9.9.2.6 - NAS security parameters from E-UTRA 
NASSecParamsFromEUTRA ::= SEQUENCE {
   spare [0] INTEGER (0..15) DEFAULT 0,
   dlNASCount [1] INTEGER (0..15)
}

-- 9.9.2.7 - NAS security parameters to E-UTRA 
NASSecParamsToEUTRA ::= SEQUENCE {
   nonceMMEValue [0] OCTET STRING (SIZE (4)),
   spare1 [1] BOOLEAN DEFAULT FALSE,
   typeOfCiphAlg [2] INTEGER (0..7),
   spare2 [3] BOOLEAN DEFAULT FALSE,
   typeOfProtAlg [4] INTEGER (0..7),
   spare3 [5] INTEGER (0..15) DEFAULT 0,
   tsc [6] BOOLEAN,
   nasKeySetIdent [7] INTEGER (0..7)
}

-- 9.9.3 - EPS Mobility Management (EMM) information elements 
-- 9.9.3.0A - Additional update result 
AddnUpdateResult ::= SEQUENCE {
   spare [0] INTEGER (0..3) DEFAULT 0,
   value [1] ENUMERATED { noInfo(0), csFbNotPref(1), smsOnly(2), reserved(3) }
}

-- 9.9.3.0B - Additional update type 
AddnUpdateType ::= SEQUENCE {
   pnb_CIoT [0] ENUMERATED { noAddInfo(0), cpCIotEpsPref(1), upCIotEpsPref(2), 
      reserved(3) },
   saf [1] BOOLEAN,
   autv [2] BOOLEAN
}

-- 9.9.3.4B - SMS services status 
SMSServicesStatus ::= SEQUENCE {
   spare [0] BOOLEAN DEFAULT FALSE,
   value [1] INTEGER (0..7)
}

-- 9.9.3.5 - CSFB response 
CSFBResponse ::= SEQUENCE {
   spare [0] BOOLEAN DEFAULT FALSE,
   value [1] INTEGER (0..7)
}

-- 9.9.3.7 - Detach type 
DetachType ::= SEQUENCE {
   switchOff [0] BOOLEAN,
   typeOfDetach [1] INTEGER (0..7)
}

-- 9.9.3.10 - EPS attach result 
EPSAttachResult ::= SEQUENCE {
   spare [0] BOOLEAN DEFAULT FALSE,
   result [1] INTEGER (0..7)
}

-- 9.9.3.11 - EPS attach type 
EPSAttachType ::= SEQUENCE {
   spare [0] BOOLEAN DEFAULT FALSE,
   value [1] INTEGER (0..7)
}

-- 9.9.3.12 - EPS mobile identity 
EPSMobileIdentity-GUTI ::= SEQUENCE {
   mcc-mnc [0] MCCMNCPair,
   mmeGroupID [1] OCTET STRING (SIZE (2)),
   mmeCode [2] INTEGER (0..255),
   tmsi [3] OCTET STRING (SIZE (4))
}

EPSMobileIdentity ::= SEQUENCE {
   --<is3GLength/>
   length [0] INTEGER (0..255),
   filler [1] INTEGER (0..15) DEFAULT 15,
   oddEvenInd [2] BOOLEAN,
   typeOfIdent [3] ENUMERATED { imsi(1), imei(3), guti(6) },
   --<inline/>
   content [4] EXPLICIT CHOICE {
      --<selector element="typeOfIdent" value="6"/>
      guti [0] EPSMobileIdentity-GUTI,
      --<selector element="typeOfIdent" value="1"/>
      imsi [1] IMSI,
      --<selector element="typeOfIdent" value="3"/>
      imei [2] IMEI
   }
}

-- 9.9.3.12A - EPS network feature support 
EPSNetworkFeatureSupport ::= SEQUENCE {
   --<is3GLength/>
   length [0] INTEGER (1..2) DEFAULT 1,
   cpCIoT [1] BOOLEAN,
   erNoPDN [2] BOOLEAN,
   esr [3] BOOLEAN,
   csLCS [4] INTEGER (0..3),
   epcLCS [5] BOOLEAN,
   emcBS [6] BOOLEAN,
   imsVoPS [7] BOOLEAN,
   --<noPresentBit/>
   --<inline/>
   octet4 [8] SEQUENCE {
      sigEPSBC [0] BOOLEAN,
      iwkN26 [1] BOOLEAN,
      rDCNR [2] BOOLEAN,
      rEC [3] BOOLEAN,
      ePCO [4] BOOLEAN,
      hcCpCIoT [5] BOOLEAN,
      s1DT [6] BOOLEAN,
      upCIot [7] BOOLEAN
   } OPTIONAL
}

-- 9.9.3.13 - EPS update result 
EPSUpdateResult ::= SEQUENCE {
   spare [0] BOOLEAN DEFAULT FALSE,
   result [1] INTEGER (0..7)
}

-- 9.9.3.14 - EPS update type 
EPSUpdateType ::= SEQUENCE {
   active [0] BOOLEAN,
   value [1] INTEGER (0..7)
}

-- 9.9.3.19 - KSI and sequence number 
KSIAndSequenceNumber ::= SEQUENCE {
   ksi [0] INTEGER (0..7),
   seqNo [1] INTEGER (0..31)
}

-- 9.9.3.21 - NAS key set identifier 
NASKeySetIdentifier ::= SEQUENCE {
   tsc [0] BOOLEAN,
   ident [1] INTEGER (0..7)
}

-- 9.9.3.23 - NAS security algorithms 
NASSecurityAlgorithms ::= SEQUENCE {
   spare1 [0] BOOLEAN DEFAULT FALSE,
   typeOfCiph [1] ENUMERATED { eea0(0), x128-eea1(1), x128-eea2(2), eea3(3), 
      eea4(4), eea5(5), eea6(6), eea7(7) },
   spare2 [2] BOOLEAN DEFAULT FALSE,
   typeOfProt [3] ENUMERATED { eia0(0), x128-eia1(1), x128-eia2(2), eia3(3), 
      eia4(4), eia5(5), eia6(6), eia7(7) }
}

-- 9.9.3.25A - Paging identity 
PagingIdentity ::= SEQUENCE {
   spare [0] INTEGER (0..127) DEFAULT 0,
   ident [1] ENUMERATED { imsi(0), tmsi(1) }
}

-- 9.9.3.26A - Extended EMM cause 
ExtEMMCause ::= SEQUENCE {
   spare [0] BOOLEAN DEFAULT FALSE,
   nbiotAllowed [1] BOOLEAN,
   epsOptInfo [2] BOOLEAN,
   e-UTRAN-NotAllowed [3] BOOLEAN
}

-- 9.9.3.32 - Tracking area identity 
TrackingAreaIdent ::= SEQUENCE {
   mcc-mnc [0] MCCMNCPair,
   tac [1] TrackingAreaCode
}

TrackingAreaIdentListItem ::= SEQUENCE {
   spare [0] BOOLEAN DEFAULT FALSE,
   typeOfList [1] INTEGER (0..2),
   numElements [2] INTEGER (0..31),
   --<inline/>
   elements [3] EXPLICIT CHOICE {
      --<selector element="typeOfList" value="0"/>
      --<asn1typename>PartialTrkAreaIdent0</asn1typename>
      partTrkIdentList0 [0] SEQUENCE {
         mcc-mnc [0] MCCMNCPair,
         --<inline/>
         --<length expr="@...numElements+1"/>
         tacs [1] SEQUENCE (SIZE (1..32)) OF tac TrackingAreaCode
      },
      --<selector element="typeOfList" value="1"/>
      --<asn1typename>PartialTrkAreaIdent1</asn1typename>
      partTrkIdentList1 [1] SEQUENCE {
         mcc-mnc [0] MCCMNCPair,
         tac [1] TrackingAreaCode
      },
      --<selector element="typeOfList" value="2"/>
      --<asn1typename>PartialTrkAreaIdent2</asn1typename>
      --<length expr="@.numElements+1"/>
      partTrkIdentList2 [2] SEQUENCE (SIZE (1..32)) OF TrackingAreaIdent
   }
}

-- 9.9.3.33 - Tracking area identity list 
TrackingAreaIdentList ::= SEQUENCE {
   --<is3GLength/>
   length [0] INTEGER (6..96),
   --<is3GVarLenList lengthElem="length"/>
   --<storage>array</storage>
   idents [1] SEQUENCE (SIZE (1..16)) OF TrackingAreaIdentListItem
}

EPSEncryptAlgsSupported ::= SEQUENCE {
   eea0 [0] BOOLEAN,
   x128-eea1 [1] BOOLEAN,
   x128-eea2 [2] BOOLEAN,
   eea3 [3] BOOLEAN,
   eea4 [4] BOOLEAN,
   eea5 [5] BOOLEAN,
   eea6 [6] BOOLEAN,
   eea7 [7] BOOLEAN
}

EPSIntegAlgsSupported ::= SEQUENCE {
   eia0 [0] BOOLEAN,
   eia1 [1] BOOLEAN,
   eia2 [2] BOOLEAN,
   eia3 [3] BOOLEAN,
   eia4 [4] BOOLEAN,
   eia5 [5] BOOLEAN,
   eia6 [6] BOOLEAN,
   eia7 [7] BOOLEAN
}

UMTSEncryptAlgsSupported ::= SEQUENCE {
   uea0 [0] BOOLEAN,
   uea1 [1] BOOLEAN,
   uea2 [2] BOOLEAN,
   uea3 [3] BOOLEAN,
   uea4 [4] BOOLEAN,
   uea5 [5] BOOLEAN,
   uea6 [6] BOOLEAN,
   uea7 [7] BOOLEAN
}

UMTSIntegAlgsSupported ::= SEQUENCE {
   uia1 [0] BOOLEAN,
   uia2 [1] BOOLEAN,
   uia3 [2] BOOLEAN,
   uia4 [3] BOOLEAN,
   uia5 [4] BOOLEAN,
   uia6 [5] BOOLEAN,
   uia7 [6] BOOLEAN
}

-- 9.9.3.34 - UE network capability 
UENetworkCapability ::= SEQUENCE {
   --<is3GLength/>
   length [0] INTEGER (1..255),
   -- EPS encryption algorithms supported
   epsEncryptAlgs [1] EPSEncryptAlgsSupported,
   -- EPS integrity algorithms supported 
   epsIntegAlgs [2] EPSIntegAlgsSupported,
   -- UMTS encryption algorithms supported
   --<noPresentBit/>
   umtsEncryptAlgs [3] UMTSEncryptAlgsSupported OPTIONAL,
   --<noPresentBit/>
   --<inline/>
   octet6 [4] SEQUENCE {
      -- UCS2 character string support
      ucs2 [0] BOOLEAN,
      -- UMTS integrity algorithms supported 
      umtsIntegAlgs [1] UMTSIntegAlgsSupported
   } OPTIONAL,
   --<noPresentBit/>
   --<inline/>
   octet7 [5] SEQUENCE {
      proSedd [0] BOOLEAN,
      proSe [1] BOOLEAN,
      h245-ash [2] BOOLEAN,
      acc-csfb [3] BOOLEAN,
      lpp [4] BOOLEAN,
      lcs [5] BOOLEAN,
      x1xSR-VCC [6] BOOLEAN,
      nf [7] BOOLEAN
   } OPTIONAL,
   --<noPresentBit/>
   --<inline/>
   octet8 [6] SEQUENCE {
      ePCO [0] BOOLEAN,
      hc-CP-CIoT [1] BOOLEAN,
      erwoPDN [2] BOOLEAN,
      s1-Udata [3] BOOLEAN,
      upCIoT [4] BOOLEAN,
      cpCIoT [5] BOOLEAN,
      prose-relay [6] BOOLEAN,
      proSedc [7] BOOLEAN
   } OPTIONAL,
   --<noPresentBit/>
   --<inline/>
   octet9 [7] SEQUENCE {
      bearers [0] BOOLEAN,
      sgc [1] BOOLEAN,
      n1Mode [2] BOOLEAN,
      dcnr [3] BOOLEAN,
      cpBackoff [4] BOOLEAN,
      restrictEC [5] BOOLEAN,
      v2xPC5 [6] BOOLEAN,
      multDRB [7] BOOLEAN
   } OPTIONAL,
   --<noPresentBit/>
   --<inline/>
   octet10 [8] SEQUENCE {
      spare [0] INTEGER (0..63) DEFAULT 0,
      wusa [1] BOOLEAN,
      racs [2] BOOLEAN
   } OPTIONAL,
   --<length fixed-size="0"/>
   --<noPresentBit/>
   spare4 [9] OCTET STRING OPTIONAL
}

GPRSIntegAlgsSupported ::= SEQUENCE {
   gea1 [0] BOOLEAN,
   gea2 [1] BOOLEAN,
   gea3 [2] BOOLEAN,
   gea4 [3] BOOLEAN,
   gea5 [4] BOOLEAN,
   gea6 [5] BOOLEAN,
   gea7 [6] BOOLEAN
}

-- 9.9.3.35 - UE radio capability information update needed 
UERadioCapInfoUpdateNeeded ::= SEQUENCE {
   spare [0] INTEGER (0..7),
   value [1] BOOLEAN
}

-- 9.9.3.36 - UE security capability 
UESecurityCapability ::= SEQUENCE {
   --<is3GLength/>
   length [0] INTEGER (2..13),
   -- EPS encryption algorithms supported
   epsEncryptAlgs [1] EPSEncryptAlgsSupported,
   -- EPS integrity algorithms supported 
   epsIntegAlgs [2] EPSIntegAlgsSupported,
   -- UMTS encryption algorithms supported
   --<noPresentBit/>
   umtsEncryptAlgs [3] UMTSEncryptAlgsSupported OPTIONAL,
   -- EPS integrity algorithms supported 
   --<noPresentBit/>
   --<inline/>
   octet6 [4] SEQUENCE {
      spare [0] BOOLEAN DEFAULT FALSE,
      umtsIntegAlgs [1] UMTSIntegAlgsSupported
   } OPTIONAL,
   -- GPRS integrity algorithms supported 
   --<noPresentBit/>
   --<inline/>
   octet7 [5] SEQUENCE {
      spare [0] BOOLEAN DEFAULT FALSE,
      gprsIntegAlgs [1] GPRSIntegAlgsSupported
   } OPTIONAL
}

-- 9.9.3.37a - Extended emergency number list 
ExtEmergencyNumberInfo ::= SEQUENCE {
   number [0] SEQUENCE {
      --<is3GLength/>
      length [0] INTEGER (0..255),
      --<length fixed-size="0"/>
      digits [1] TBCDString
   },
   subservices [1] SEQUENCE {
      --<is3GLength/>
      subservicesLen [0] INTEGER (0..255),
      --<length fixed-size="0"/>
      subservices [1] OCTET STRING
   }
}

ExtEmergencyNumberList ::= SEQUENCE {
   --<is3GLength/>
   length [0] INTEGER (0..255),
   spare [1] INTEGER (0..127) DEFAULT 0,
   catValue [2] BOOLEAN,
   --<is3GVarLenList lengthElem="length"/>
   --<storage>array</storage>
   numberInfo [3] SEQUENCE OF ExtEmergencyNumberInfo
}

-- 9.9.3.38 - CLI 
CLI ::= SEQUENCE {
   --<is3GLength/>
   length [0] INTEGER (0..255),
   --<length fixed-size="0"/>
   value [1] TBCDString
}

-- 9.9.3.45 - GUTI type 
GUTIType ::= SEQUENCE {
   spare [0] INTEGER (0..7) DEFAULT 0,
   mapped [1] BOOLEAN -- FALSE = native
}

-- 9.9.3.47 - Control Plane Service Type 
CtrlPlaneSvcType ::= SEQUENCE {
   activeFlag [0] BOOLEAN,
   svcTypeValue [1] INTEGER (0..7)
      -- 0 = mobile originating request
      -- 1 = mobile terminating request
      -- 2 thru 7 - not used
}

-- 9.9.3.50 - Hash MME 
HashMME ::= SEQUENCE {
   length [0] INTEGER (0..255),
   hashValue [1] OCTET STRING (SIZE (8))
}

-- 9.9.3.51 - Replayed NAS message container 
ReplayedNASMsgContainer ::= SEQUENCE {
   length [0] INTEGER (0..65535),
   contents [1] OCTET STRING (SIZE (1..65535))
}

-- 9.9.3.52 - Network policy 
NetworkPolicy ::= SEQUENCE {
   spare [0] INTEGER (0..7) DEFAULT 0,
   redirPolicy [1] BOOLEAN
}

-- 9.9.3.53 - UE additional security capability 
UEAddlSecurityCapability ::= SEQUENCE {
   length [0] INTEGER (0..255),
   contents [1] SEQUENCE (SIZE (32)) OF BOOLEAN
}

-- 9.9.3.54 - UE status 
UEStatus ::= SEQUENCE {
   length [0] INTEGER (0..255) DEFAULT 1,
   spare [1] INTEGER (0..63) DEFAULT 0,
   n1RegStatus [2] BOOLEAN,
   s1RegStatus [3] BOOLEAN
}

-- 9.9.3.55 - Additional information requested 
AdditionalInfoReq ::= SEQUENCE {
   spare [0] INTEGER (0..127) DEFAULT 0,
   dataRequested [1] BOOLEAN
}

-- 9.9.3.56 - Ciphering key data 
CipherDataSet ::= SEQUENCE {
   cipherKey [0] OCTET STRING (SIZE (16)),
   spare [1] INTEGER (0..7) DEFAULT 0,
   c0Len [2] INTEGER (0..31),
   --<length expr="@c0Len"/>
   c0 [3] OCTET STRING,
   posSIBType [4] SEQUENCE (SIZE (27)) OF BOOLEAN,
   spare2 [5] INTEGER (0..31) DEFAULT 0,
   validityStartTime [6] TimeZoneAndTime,
   validityDuration [7] INTEGER (0..65535),
   taiList [8] TrackingAreaIdentList
}

CipherKeyData ::= SEQUENCE {
   --<is3GLength/>
   length [0] INTEGER (0..255),
   --<is3GVarLenList lengthElem="length"/>
   --<storage>array</storage>
   dataSet [1] SEQUENCE (SIZE (1..16)) OF CipherDataSet
}

-- 9.9.3.57 - N1 UE network capability 
N1UENetCapability ::= SEQUENCE {
   length [0] INTEGER (0..255),
   spare [1] INTEGER (0..3) DEFAULT 0,
   pnbCIoT [2] INTEGER (0..3),
   upCIoT [3] BOOLEAN,
   hcCpCIoT [4] BOOLEAN,
   n3Data [5] BOOLEAN,
   cpCIoT [6] BOOLEAN
}

-- 9.9.3.58 - UE radio capability ID availability 
UERadioCapIdAvailability ::= SEQUENCE {
   spare [0] BOOLEAN DEFAULT FALSE,
   value [1] INTEGER (0..7)
}

-- 9.9.3.59 - UE radio capability ID request 
UERadioCapIdRequest ::= SEQUENCE {
   spare [0] INTEGER (0..127) DEFAULT 0,
   urcid-A [1] BOOLEAN
}

-- 9.9.3.60 - UE radio capability ID 
UERadioCapId ::= SEQUENCE {
   length [0] INTEGER (1..255),
   capId [1] OCTET STRING
}

-- 9.9.3.61 - UE radio capability ID deletion indication 
UERadioCapIdDeletionInd ::= SEQUENCE {
   spare [0] BOOLEAN DEFAULT FALSE,
   deletionReq [1] INTEGER (0..7)
}

WUSAssistInfoType ::= SEQUENCE {
   infoType [0] InformationType,
   infoValue [1] INTEGER (0..31)
}

-- 9.9.3.62 - WUS assistance information - STILL MOSTLY TBD AS OF 16.3 
WUSAssistanceInfo ::= SEQUENCE {
   --<is3GLength/>
   length [0] INTEGER (0..255),
   --<is3GVarLenList lengthElem="length"/>
   --<storage>array</storage>
   types [1] SEQUENCE (SIZE (1..255)) OF WUSAssistInfoType
}

APNAggMaxBitRateExt ::= SEQUENCE {
   apnAmbrforDL [0] INTEGER (0..255),
   apnAmbrforUL [1] INTEGER (0..255)
}

-- 9.9.4 - EPS Session Management (ESM) information elements 
-- 9.9.4.2 - APN aggregate maximum bit rate 
APNAggMaxBitRate ::= SEQUENCE {
   --<is3GLength/>
   length [0] INTEGER (2..6),
   apnAmbrforDL [1] INTEGER (0..255),
   apnAmbrforUL [2] INTEGER (0..255),
   --<is3GVarLenList lengthElem="length"/>
   --<storage>array</storage>
   ext [3] SEQUENCE (SIZE (0..2)) OF APNAggMaxBitRateExt
}

EPSQoSBitRates ::= SEQUENCE {
   maxBitRateforUL [0] INTEGER (0..255),
   maxBitRateforDL [1] INTEGER (0..255),
   guarBitRateforUL [2] INTEGER (0..255),
   guarBitRateforDL [3] INTEGER (0..255)
}

-- 9.9.4.3 - EPS quality of service 
EPSQualityOfService ::= SEQUENCE {
   --<is3GLength/>
   length [0] INTEGER (1 | 5 | 9 | 13),
   qci [1] INTEGER (0..255),
   --<is3GVarLenList lengthElem="length"/>
   --<storage>array</storage>
   bitRates [2] SEQUENCE (SIZE (0..3)) OF EPSQoSBitRates
}

-- 9.9.4.5 - ESM information transfer flag 
ESMInfoXferFlag ::= SEQUENCE {
   spare [0] INTEGER (0..7) DEFAULT 0,
   eitValue [1] BOOLEAN
}

-- 9.9.4.9 - PDN address 
PDNAddress ::= SEQUENCE {
   --<is3GLength/>
   length [0] INTEGER (5..13),
   spare [1] INTEGER (0..31) DEFAULT 0,
   pdnTypeValue [2] PDNTypeValue,
   --<inline/>
   --<length fixed-size="0"/>
   pdnAddrInfo [3] OCTET STRING (SIZE (4..12))
}

-- 9.9.4.10 - PDN type 
PDNType ::= SEQUENCE {
   spare [0] BOOLEAN DEFAULT FALSE,
   pdnTypeValue [1] PDNTypeValue
}

-- 9.9.4.13A - Reattempt indicator 
ReattemptInd ::= SEQUENCE {
   spare [0] INTEGER (0..63) DEFAULT 0,
   eplmNcValue [1] BOOLEAN,
   ratcValue [2] BOOLEAN
}

RemoteUECtxt ::= SEQUENCE {
   --<is3GLength/>
   length [0] INTEGER (0..255),
   numUserIdents [1] INTEGER (0..255),
   userIdentLength [2] INTEGER (0..255),
   --<is3GVarLenList lengthElem="length"/>
   userIdents [3] SEQUENCE OF OCTET STRING
}

-- 9.9.4.20 - Remote UE context list 
RemoteUECtxtList ::= SEQUENCE {
   --<is3GLength bitFieldSize="16"/>
   length [0] INTEGER (5..65535),
   numRemUECtxts [1] INTEGER (1..255),
   --<is3GVarLenList lengthElem="length"/>
   remUECtxts [2] SEQUENCE OF RemoteUECtxt,
   spare [3] INTEGER (0..31) DEFAULT 0,
   addrType [4] RemoteUEAddrType,
   addrInfo [5] OCTET STRING (SIZE (6..8))
}

PKMFAddressType ::= SEQUENCE {
   spare [0] INTEGER (0..32) DEFAULT 0,
   addrType [1] INTEGER (0..7), -- 1 = ipv4, 2 = ipv6
   --<length fixed-size="0"/>
   addrInfo [2] OCTET STRING (SIZE (0..16))
}

-- 9.9.4.21 - PKMF address IE 
PKMFAddress ::= SEQUENCE {
   --<is3GLength/>
   length [0] INTEGER (0..255),
   --<is3GVarLenList lengthElem="length"/>
   addrs [1] SEQUENCE OF PKMFAddressType
}

-- 9.9.4.22 - Header compression configuration 
HdrCompressConfig ::= SEQUENCE {
   --<is3GLength/>
   length [0] INTEGER (3..255),
   spare1 [1] BOOLEAN DEFAULT FALSE,
   profile104 [2] BOOLEAN,
   profile103 [3] BOOLEAN,
   profile102 [4] BOOLEAN,
   profile006 [5] BOOLEAN,
   profile004 [6] BOOLEAN,
   profile003 [7] BOOLEAN,
   profile002 [8] BOOLEAN,
   maxCID [9] OCTET STRING (SIZE (2)),
   addlSetupType [10] OCTET STRING,
   addlSetupContainer [11] OCTET STRING (SIZE (1..251))
}

-- 9.9.4.23 - Control Plane Only Indication 
CtrlPlaneOnlyInd ::= SEQUENCE {
   spare4 [0] BOOLEAN DEFAULT FALSE,
   spare3 [1] BOOLEAN DEFAULT FALSE,
   spare2 [2] BOOLEAN DEFAULT FALSE,
   cpoiValue [3] BOOLEAN
}

-- 9.9.4.25 - Release assistance indication 
ReleaseAssistInd ::= SEQUENCE {
   spare4 [0] BOOLEAN DEFAULT FALSE,
   spare3 [1] BOOLEAN DEFAULT FALSE,
   ddx [2] ENUMERATED { ddxNoInfo(0), ddxNoTrans(1), ddxSingleDLTrans(2), 
      ddxReserved(3) }
}

-- 9.9.4.27 - Header compression configuration status 
HdrCompressConfigStat ::= SEQUENCE {
   --<is3GLength/>
   length [0] INTEGER (2),
   ebi [1] OCTET STRING (SIZE (2))
}

-- 9.9.4.29 - Extended APN aggregate maximum bit rate 
ExtAPNAggMaxBitRate ::= SEQUENCE {
   extApnAmbrUnitForDL [0] INTEGER (0..255),
   extApnAmbrForDL [1] OCTET STRING (SIZE (2)),
   extApnAmbrUnitForUL [2] INTEGER (0..255),
   extApnAmbrForUL [3] OCTET STRING (SIZE (2))
}

END
TS24301Msgs DEFINITIONS AUTOMATIC TAGS ::= BEGIN

IMPORTS

L3HdrOptions, NAS-PROTOCOL-CLASS, ProtoDiscr, SecProtMsgHeader
FROM TS24007L3 

AccessPointName, AuthFailureParam, AuthParamAUTN, AuthParamRAND, 
   DaylightSavingTime, CiphKeySeqNum, ConnectivityType, DeviceProperties, 
   DRXParameter, EmergencyNumberList, ExtDRXParams, ExtProtoConfigOptions, 
   GPRSTimer, GPRSTimer2, GPRSTimer3, IdentityType2Value, IMEISVRequest, 
   LinkedTI, LLCSAPIValue, LocAreaIdent, MobileIdentity, 
   MobileStationClassmark2, MobileStationClassmark3, MSNetworkCapability, 
   MSNetFeatureSupport, NBIFOMContainer, NetworkName, NetResourceIdentContainer
   , P-TMSISignature, PacketFlowIdentValue, PLMNList, ProtocolConfigOptions, 
   ReattemptInd, RequestTypeValue, QualityOfService, RadioPriorityValue, 
   SupportedCodecList, TFT, TimeZone, TimeZoneAndTime, TMSIStatus, 
   VoiceDomainPref, WLANOffloadAccept, DcnID, Non3GPPNetPolicies, 
   ExtQualityOfService
FROM TS24008IES 

AddnUpdateResult, AddnUpdateType, APNAggMaxBitRate, AuthRespParam, CLI, 
   CtrlPlaneOnlyInd, CtrlPlaneSvcType, CSFBResponse, DetachType, EMMCause, 
   EPSAttachType, EPSAttachResult, EPSBearerContextStatus, EPSMobileIdentity, 
   EPSMobileIdentity-GUTI, EPSNetworkFeatureSupport, EPSQualityOfService, 
   EPSUpdateResult, EPSUpdateType, ESMMessageContainer, ESMCause, 
   ESMInfoXferFlag, ExtEMMCause, GenMessageContainer, GenMsgContainerType, 
   GUTIType, HdrCompressConfig, HdrCompressConfigStat, KSIAndSequenceNumber, 
   LCSClientIdentity, LCSIndicator, LinkedEPSBearerIdent, NASKeySetIdentifier, 
   NASMessageContainer, NASSecurityAlgorithms, Nonce, PagingIdentity, 
   PDNAddress, PDNType, PKMFAddress, ReleaseAssistInd, RemoteUECtxtList, 
   ServiceType, ServPLMNRateCtrl, ShortMAC, SMSServicesStatus, SSCode, 
   TrackingAreaIdent, TrackingAreaIdentList, UENetworkCapability, 
   UERadioCapInfoUpdateNeeded, UESecurityCapability, NetworkPolicy, 
   ExtEmergencyNumberList, CipherKeyData, UEAddlSecurityCapability, UEStatus, 
   AdditionalInfoReq, HashMME, ReplayedNASMsgContainer, ExtAPNAggMaxBitRate, 
   N1UENetCapability, UERadioCapIdAvailability, UERadioCapIdRequest, 
   UERadioCapId, UERadioCapIdDeletionInd
FROM TS24301IES ;

-- Productions

AttachComplete ::= ESMMessageContainer

AuthResponse ::= AuthRespParam

DLNASTransport ::= NASMessageContainer

EMMStatus ::= EMMCause

IdentResp ::= MobileIdentity

SecModeReject ::= EMMCause

ULNASTransport ::= NASMessageContainer

GenNASTransport ::= SEQUENCE {
   genMsgContainerType [0] GenMsgContainerType,
   genMsgContainer [1] GenMessageContainer,
   --<iei format="tlv">65</iei>
   addnInfo [2] OCTET STRING (SIZE (0..253)) OPTIONAL
}

DLGenNASTransport ::= GenNASTransport

ULGenNASTransport ::= GenNASTransport

ESMStatus ::= ESMCause

RemoteUEReportResp ::= NULL

AttachAccept ::= SEQUENCE {
   spare [0] INTEGER (0..15) DEFAULT 0,
   result [1] EPSAttachResult,
   t3412Value [2] GPRSTimer,
   taiList [3] TrackingAreaIdentList,
   esmMessageContainer [4] ESMMessageContainer,
   --<iei format="tlv">50</iei>
   guti [5] EPSMobileIdentity OPTIONAL,
   --<iei format="tv" length="6">13</iei>
   locAreaIdent [6] LocAreaIdent OPTIONAL,
   --<iei format="tlv">23</iei>
   msIdentity [7] EXPLICIT MobileIdentity OPTIONAL,
   --<iei format="tv" length="2">53</iei>
   emmCause [8] EMMCause OPTIONAL,
   --<iei format="tv" length="2">17</iei>
   t3402 [9] GPRSTimer OPTIONAL,
   --<iei format="tv" length="2">59</iei>
   t3423 [10] GPRSTimer OPTIONAL,
   --<iei format="tlv">4A</iei>
   equivPLMNs [11] PLMNList OPTIONAL,
   --<iei format="tlv">34</iei>
   emergNumList [12] EmergencyNumberList OPTIONAL,
   --<iei format="tlv">64</iei>
   epsNetFeatSupp [13] EPSNetworkFeatureSupport OPTIONAL,
   --<iei format="tv" length="1">F</iei>
   addnUpdateResult [14] AddnUpdateResult OPTIONAL,
   ...,
   [[ 10:
      t3412ExtValue [15] GPRSTimer3 OPTIONAL
   ]],
   [[ 12:
      t3324Value [16] GPRSTimer2 OPTIONAL
   ]],
   [[ 13:
      extDRXParams [17] ExtDRXParams OPTIONAL,
      dcnId [18] DcnID OPTIONAL,
      smsServicesStatus [19] SMSServicesStatus OPTIONAL
   ]],
   [[ 14:
      non3GPPNetPolicies [20] Non3GPPNetPolicies OPTIONAL,
      t3448Value [21] GPRSTimer2 OPTIONAL,
      networkPolicy [22] NetworkPolicy OPTIONAL
   ]],
   [[ 15:
      t3447Value [23] GPRSTimer3 OPTIONAL,
      extEmergencyNumberList [24] ExtEmergencyNumberList OPTIONAL,
      cipherKeyData [25] CipherKeyData OPTIONAL
   ]],
   [[ 16:
      ueradioCapabilityID [26] UERadioCapId OPTIONAL,
      ueradioCapIDDeleteInd [27] UERadioCapIdDeletionInd OPTIONAL
   ]]
}

AttachReject ::= SEQUENCE {
   emmCause [0] EMMCause,
   --<iei format="tlv-e">78</iei>
   esmMsgCont [1] ESMMessageContainer OPTIONAL,
   ...,
   [[ 10:
      t3346Value [2] GPRSTimer2 OPTIONAL,
      t3402Value [3] GPRSTimer2 OPTIONAL
   ]],
   [[ 12:
      extEMMCause [4] ExtEMMCause OPTIONAL
   ]]
}

AttachRequest ::= SEQUENCE {
   nasKeySetIdentifier [0] NASKeySetIdentifier,
   epsAttachType [1] EPSAttachType,
   oldGUTIOrIMSI [2] EPSMobileIdentity,
   ueNetworkCapability [3] UENetworkCapability,
   esmMessageContainer [4] ESMMessageContainer,
   --<iei format="tv" length="4">19</iei>
   oldP-TMSISignature [5] P-TMSISignature OPTIONAL,
   --<iei format="tlv">50</iei>
   additionalGUTI [6] EPSMobileIdentity OPTIONAL,
   --<iei format="tv" length="6">52</iei>
   lastVisitedRegisteredTAI [7] TrackingAreaIdent OPTIONAL,
   --<iei format="tv" length="3">5C</iei>
   drxParameter [8] DRXParameter OPTIONAL,
   --<iei format="tlv">31</iei>
   msNetworkCapability [9] MSNetworkCapability OPTIONAL,
   --<iei format="tv" length="6">13</iei>
   oldLocAreaIdent [10] LocAreaIdent OPTIONAL,
   --<iei format="tv" length="1">9</iei>
   tmsiStatus [11] TMSIStatus OPTIONAL,
   --<iei format="tlv">11</iei>
   mobileStationClassmark2 [12] MobileStationClassmark2 OPTIONAL,
   --<iei format="tlv">20</iei>
   mobileStationClassmark3 [13] MobileStationClassmark3 OPTIONAL,
   --<iei format="tlv">40</iei>
   supportedCodecs [14] SupportedCodecList OPTIONAL,
   --<iei format="tv" length="1">F</iei>
   addnUpdateType [15] AddnUpdateType OPTIONAL,
   ...,
   [[ 9:
      voiceDomainPref [16] VoiceDomainPref OPTIONAL
   ]],
   [[ 10:
      deviceProperties [17] DeviceProperties OPTIONAL,
      oldGUTIType [18] GUTIType OPTIONAL,
      msNetFeatureSupport [19] MSNetFeatureSupport OPTIONAL
   ]],
   [[ 11:
      tmsiBasedNRIContainer [20] NetResourceIdentContainer OPTIONAL
   ]],
   [[ 12:
      t3324Value [21] GPRSTimer2 OPTIONAL,
      t3412ExtValue [22] GPRSTimer3 OPTIONAL
   ]],
   [[ 13:
      extDRXParams [23] ExtDRXParams OPTIONAL
   ]],
   [[ 15:
      addlSecurityCapability [24] UEAddlSecurityCapability OPTIONAL,
      ueStatus [25] UEStatus OPTIONAL,
      addlInfoReq [26] AdditionalInfoReq OPTIONAL
   ]],
   [[ 16:
      n1UENetworkCapability [27] N1UENetCapability OPTIONAL
   ]]
}

AuthFailure ::= SEQUENCE {
   emmCause [0] EMMCause,
   --<iei format="tlv">30</iei>
   authFailureParam [1] AuthFailureParam OPTIONAL
}

AuthRequest ::= SEQUENCE {
   spare [0] INTEGER (0..15) DEFAULT 0,
   nasKeySetIdent [1] NASKeySetIdentifier,
   authParamRAND [2] AuthParamRAND,
   authParamAUTN [3] AuthParamAUTN
}

CSServiceNotif ::= SEQUENCE {
   pagingIdentity [0] PagingIdentity,
   --<iei format="tlv">60</iei>
   cli [1] CLI OPTIONAL,
   --<iei format="tv" length="2">61</iei>
   ssCode [2] SSCode OPTIONAL,
   --<iei format="tv" length="2">62</iei>
   lcsIndicator [3] LCSIndicator OPTIONAL,
   --<iei format="tlv">63</iei>
   lcsClientIdentity [4] LCSClientIdentity OPTIONAL
}

DetachRequestUEOrig ::= SEQUENCE {
   nasKeySetIdent [0] NASKeySetIdentifier,
   detachType [1] DetachType,
   gUTIOrIMSI [2] EPSMobileIdentity
}

DetachRequestUETerm ::= SEQUENCE {
   spare [0] INTEGER (0..15) DEFAULT 0,
   detachType [1] DetachType,
   --<iei format="tv" length="2">53</iei>
   emmCause [2] EMMCause OPTIONAL
}

--<cEncFuncFname>TS24301MsgEnc_DetachRequest.c</cEncFuncFname>
--<cDecFuncFname>TS24301MsgDec_DetachRequest.c</cDecFuncFname>
DetachRequest ::= CHOICE {
   ueOrig [0] DetachRequestUEOrig,
   ueTerm [1] DetachRequestUETerm
}

EMMInformation ::= SEQUENCE {
   --<iei format="tlv">43</iei>
   fullNameForNetwork [0] NetworkName OPTIONAL,
   --<iei format="tlv">45</iei>
   shortNameForNetwork [1] NetworkName OPTIONAL,
   --<iei format="tv" length="2">46</iei>
   localTimeZone [2] TimeZone OPTIONAL,
   --<iei format="tv" length="8">47</iei>
   univTimeAndLclTimeZone [3] TimeZoneAndTime OPTIONAL,
   --<iei format="tlv">49</iei>
   networkDaylightSavingTime [4] DaylightSavingTime OPTIONAL
}

ExtServiceReq ::= SEQUENCE {
   nasKeySetIdentifier [0] NASKeySetIdentifier,
   serviceType [1] ServiceType,
   m-tmsi [2] EXPLICIT MobileIdentity,
   --<iei format="tv" length="1">B</iei>
   csfbResponse [3] CSFBResponse OPTIONAL,
   ...,
   [[ 9:
      epsBearerContextStatus [4] EPSBearerContextStatus OPTIONAL
   ]],
   [[ 10:
      deviceProperties [5] DeviceProperties OPTIONAL
   ]]
}

GUTIReallocCmd ::= SEQUENCE {
   guti [0] EPSMobileIdentity,
   --<iei format="tlv">54</iei>
   taiList [1] TrackingAreaIdentList OPTIONAL,
   ...,
   [[ 14:
      dcnId [2] DcnID OPTIONAL
   ]]
}

IdentReq ::= SEQUENCE {
   spare [0] INTEGER (0..15) DEFAULT 0,
   identType [1] IdentityType2Value
}

SecModeCmd ::= SEQUENCE {
   selNASSecurityAlgs [0] NASSecurityAlgorithms,
   spare [1] INTEGER (0..15) DEFAULT 0,
   nasKeySetIdentifier [2] NASKeySetIdentifier,
   replayedUESecurityCapabilities [3] UESecurityCapability,
   --<iei format="tv" length="1">C</iei>
   imeisvRequest [4] IMEISVRequest OPTIONAL,
   --<iei format="tv" length="5">55</iei>
   replayedNonce [5] Nonce OPTIONAL,
   --<iei format="tv" length="5">56</iei>
   nonce [6] Nonce OPTIONAL,
   ...,
   [[ 14:
      hashMME [7] HashMME OPTIONAL
   ]],
   [[ 15:
      addlSecurityCapability [8] UEAddlSecurityCapability OPTIONAL
   ]],
   [[ 16:
      ueRadioCapabilityIdRequest [9] UERadioCapIdRequest OPTIONAL
   ]]
}

SecModeCmplt ::= SEQUENCE {
   --<iei format="tlv">23</iei>
   imeisv [0] EXPLICIT MobileIdentity OPTIONAL,
   ...,
   [[ 14:
      replayedNASMsgContainer [1] ReplayedNASMsgContainer OPTIONAL
   ]],
   [[ 16:
      ueradioCapabilityID [2] UERadioCapId OPTIONAL
   ]]
}

ServiceRequest ::= SEQUENCE {
   secHdr [0] INTEGER (0..15),
   protoDiscr [1] ProtoDiscr,
   ksiAndSequenceNumber [2] KSIAndSequenceNumber,
   shortMAC [3] ShortMAC
}

ServiceReject ::= SEQUENCE {
   emmCause [0] EMMCause,
   --<iei format="tv" length="2">5B</iei>
   t3442Value [1] GPRSTimer OPTIONAL,
   ...,
   [[ 10:
      t3346Value [2] GPRSTimer2 OPTIONAL
   ]],
   [[ 14:
      t3448Value [3] GPRSTimer2 OPTIONAL
   ]]
}

TrkAreaUpdAccept ::= SEQUENCE {
   spare [0] INTEGER (0..15) DEFAULT 0,
   epsUpdateResult [1] EPSUpdateResult,
   --<iei format="tv" length="2">5A</iei>
   t3412Value [2] GPRSTimer OPTIONAL,
   --<iei format="tlv">50</iei>
   guti [3] EPSMobileIdentity OPTIONAL,
   --<iei format="tlv">54</iei>
   taiList [4] TrackingAreaIdentList OPTIONAL,
   --<iei format="tlv">57</iei>
   epsBearerContextStatus [5] EPSBearerContextStatus OPTIONAL,
   --<iei format="tv" length="6">13</iei>
   locAreaIdent [6] LocAreaIdent OPTIONAL,
   --<iei format="tlv">23</iei>
   msIdentity [7] EXPLICIT MobileIdentity OPTIONAL,
   --<iei format="tv" length="2">53</iei>
   emmCause [8] EMMCause OPTIONAL,
   --<iei format="tv" length="2">17</iei>
   t3402Value [9] GPRSTimer OPTIONAL,
   --<iei format="tv" length="2">59</iei>
   t3423Value [10] GPRSTimer OPTIONAL,
   --<iei format="tlv">4A</iei>
   equivalentPLMNs [11] PLMNList OPTIONAL,
   --<iei format="tlv">34</iei>
   emergencyNumberList [12] EmergencyNumberList OPTIONAL,
   --<iei format="tlv">64</iei>
   epsNetworkFeatureSupport [13] EPSNetworkFeatureSupport OPTIONAL,
   --<iei format="tv" length="1">F</iei>
   addnUpdateResult [14] AddnUpdateResult OPTIONAL,
   ...,
   [[ 10:
      t3412ExtValue [15] GPRSTimer3 OPTIONAL
   ]],
   [[ 12:
      t3324Value [16] GPRSTimer2 OPTIONAL
   ]],
   [[ 13:
      extDRXParams [17] ExtDRXParams OPTIONAL,
      hdrCompressConfigStat [18] HdrCompressConfigStat OPTIONAL,
      dcnId [19] DcnID OPTIONAL,
      smsServicesStatus [20] SMSServicesStatus OPTIONAL
   ]],
   [[ 14:
      non3GPPNetPolicies [21] Non3GPPNetPolicies OPTIONAL,
      t3448Value [22] GPRSTimer2 OPTIONAL,
      networkPolicy [23] NetworkPolicy OPTIONAL
   ]],
   [[ 15:
      t3447Value [24] GPRSTimer3 OPTIONAL,
      extEmergencyNumberList [25] ExtEmergencyNumberList OPTIONAL,
      cipherKeyData [26] CipherKeyData OPTIONAL
   ]],
   [[ 16:
      ueRadioCapabilityId [27] UERadioCapId OPTIONAL,
      ueRadioCapIdDeleteInd [28] UERadioCapIdDeletionInd OPTIONAL
   ]]
}

TrkAreaUpdReject ::= SEQUENCE {
   cause [0] EMMCause,
   ...,
   [[ 10:
      t3346Value [1] GPRSTimer2 OPTIONAL
   ]],
   [[ 12:
      extEMMCause [2] ExtEMMCause OPTIONAL
   ]]
}

TrkAreaUpdRequest ::= SEQUENCE {
   nasKeySetIdentifier [0] NASKeySetIdentifier,
   epsUpdateType [1] EPSUpdateType,
   oldGUTI [2] EPSMobileIdentity,
   --<iei format="tv" length="1">B</iei>
   nonCurrNativeNASKeySetIdent [3] NASKeySetIdentifier OPTIONAL,
   --<iei format="tv" length="1">8</iei>
   gprsCiphKeySeqNum [4] CiphKeySeqNum OPTIONAL,
   --<iei format="tv" length="4">19</iei>
   oldP-TMSISignature [5] P-TMSISignature OPTIONAL,
   --<iei format="tlv">50</iei>
   additionalGUTI [6] EPSMobileIdentity OPTIONAL,
   --<iei format="tv" length="5">55</iei>
   nonce [7] Nonce OPTIONAL,
   --<iei format="tlv">58</iei>
   ueNetworkCapability [8] UENetworkCapability OPTIONAL,
   --<iei format="tv" length="6">52</iei>
   lastVisitedRegisteredTAI [9] TrackingAreaIdent OPTIONAL,
   --<iei format="tv" length="3">5C</iei>
   drxParameter [10] DRXParameter OPTIONAL,
   --<iei format="tv" length="1">A</iei>
   ueRadioCapInfoUpdateNeeded [11] UERadioCapInfoUpdateNeeded OPTIONAL,
   --<iei format="tlv">57</iei>
   epsBearerContextStatus [12] EPSBearerContextStatus OPTIONAL,
   --<iei format="tlv">31</iei>
   msNetworkCapability [13] MSNetworkCapability OPTIONAL,
   --<iei format="tv" length="6">13</iei>
   oldLocAreaIdent [14] LocAreaIdent OPTIONAL,
   --<iei format="tv" length="1">9</iei>
   tmsiStatus [15] TMSIStatus OPTIONAL,
   --<iei format="tlv">11</iei>
   mobileStationClassmark2 [16] MobileStationClassmark2 OPTIONAL,
   --<iei format="tlv">20</iei>
   mobileStationClassmark3 [17] MobileStationClassmark3 OPTIONAL,
   --<iei format="tlv">40</iei>
   supportedCodecs [18] SupportedCodecList OPTIONAL,
   --<iei format="tv" length="1">F</iei>
   addnUpdateType [19] AddnUpdateType OPTIONAL,
   ...,
   [[ 9:
      voiceDomainPref [20] VoiceDomainPref OPTIONAL
   ]],
   [[ 10:
      oldGUTIType [21] GUTIType OPTIONAL,
      deviceProperties [22] DeviceProperties OPTIONAL,
      msNetFeatureSupport [23] MSNetFeatureSupport OPTIONAL
   ]],
   [[ 11:
      tmsiBasedNRIContainer [24] NetResourceIdentContainer OPTIONAL
   ]],
   [[ 12:
      t3324Value [25] GPRSTimer2 OPTIONAL,
      t3412ExtValue [26] GPRSTimer3 OPTIONAL
   ]],
   [[ 13:
      extDRXParams [27] ExtDRXParams OPTIONAL
   ]],
   [[ 15:
      addlSecurityCapability [28] UEAddlSecurityCapability OPTIONAL,
      ueStatus [29] UEStatus OPTIONAL,
      addlInfoReq [30] AdditionalInfoReq OPTIONAL
   ]],
   [[ 16:
      n1UENetworkCapability [31] N1UENetCapability OPTIONAL
   ]]
}

ActvDedEPSBearerCtxtAcc ::= SEQUENCE {
   --<iei format="tlv">27</iei>
   protocolConfigOptions [0] ProtocolConfigOptions OPTIONAL,
   ...,
   [[ 13:
      nbifomContainer [1] NBIFOMContainer OPTIONAL,
      extProtoConfigOpts [2] ExtProtoConfigOptions OPTIONAL
   ]]
}

ActvDedEPSBearerCtxtRej ::= SEQUENCE {
   esmCause [0] ESMCause,
   --<iei format="tlv">27</iei>
   protocolConfigOptions [1] ProtocolConfigOptions OPTIONAL,
   ...,
   [[ 14:
      nbifomContainer [2] NBIFOMContainer OPTIONAL,
      extProtoConfigOpts [3] ExtProtoConfigOptions OPTIONAL
   ]]
}

ActvDedEPSBearerCtxtReq ::= SEQUENCE {
   spare [0] INTEGER (0..15) DEFAULT 0,
   linkedEPSBearerIdent [1] LinkedEPSBearerIdent,
   epsQoS [2] EPSQualityOfService,
   tft [3] TFT,
   --<iei format="tlv">5D</iei>
   transIdent [4] LinkedTI OPTIONAL,
   --<iei format="tlv">30</iei>
   negotiatedQoS [5] QualityOfService OPTIONAL,
   --<iei format="tv" length="2">32</iei>
   negotiatedLLCSAPI [6] LLCSAPIValue OPTIONAL,
   --<iei format="tv" length="1">8</iei>
   radioPriority [7] RadioPriorityValue OPTIONAL,
   --<iei format="tlv">34</iei>
   packetFlowIdentifier [8] PacketFlowIdentValue OPTIONAL,
   --<iei format="tlv">27</iei>
   protocolConfigOptions [9] ProtocolConfigOptions OPTIONAL,
   ...,
   [[ 12:
      wlanOffloadInd [10] WLANOffloadAccept OPTIONAL
   ]],
   [[ 13:
      nbifomContainer [11] NBIFOMContainer OPTIONAL,
      extProtoConfigOpts [12] ExtProtoConfigOptions OPTIONAL
   ]],
   [[ 15:
      extQOS [13] ExtQualityOfService OPTIONAL
   ]]
}

ActvDfltEPSBearerCtxtAcc ::= SEQUENCE {
   --<iei format="tlv">27</iei>
   protocolConfigOptions [0] ProtocolConfigOptions OPTIONAL,
   ...,
   [[ 13:
      extProtoConfigOpts [1] ExtProtoConfigOptions OPTIONAL
   ]]
}

ActvDfltEPSBearerCtxtRej ::= SEQUENCE {
   esmCause [0] ESMCause,
   --<iei format="tlv">27</iei>
   protocolConfigOptions [1] ProtocolConfigOptions OPTIONAL,
   ...,
   [[ 13:
      extProtoConfigOpts [2] ExtProtoConfigOptions OPTIONAL
   ]]
}

ActvDfltEPSBearerCtxtReq ::= SEQUENCE {
   epsQoS [0] EPSQualityOfService,
   accessPointName [1] AccessPointName,
   pdnAddress [2] PDNAddress,
   --<iei format="tlv">5D</iei>
   transIdent [3] LinkedTI OPTIONAL,
   --<iei format="tlv">30</iei>
   negotiatedQoS [4] QualityOfService OPTIONAL,
   --<iei format="tv" length="2">32</iei>
   negotiatedLLCSAPI [5] LLCSAPIValue OPTIONAL,
   --<iei format="tv" length="1">8</iei>
   radioPriority [6] RadioPriorityValue OPTIONAL,
   --<iei format="tlv">34</iei>
   packetFlowIdentifier [7] PacketFlowIdentValue OPTIONAL,
   --<iei format="tlv">5E</iei>
   apn-AMBR [8] APNAggMaxBitRate OPTIONAL,
   --<iei format="tv" length="2">58</iei>
   esmCause [9] ESMCause OPTIONAL,
   --<iei format="tlv">27</iei>
   protocolConfigOptions [10] ProtocolConfigOptions OPTIONAL,
   ...,
   [[ 10:
      connectivityType [11] ConnectivityType OPTIONAL
   ]],
   [[ 12:
      wlanOffloadInd [12] WLANOffloadAccept OPTIONAL
   ]],
   [[ 13:
      nbifomContainer [13] NBIFOMContainer OPTIONAL,
      hdrCompressConfigStat [14] HdrCompressConfigStat OPTIONAL,
      ctrlPlaneOnlyInd [15] CtrlPlaneOnlyInd OPTIONAL,
      extProtoConfigOpts [16] ExtProtoConfigOptions OPTIONAL,
      servPLMNRateCtrl [17] ServPLMNRateCtrl OPTIONAL
   ]],
   [[ 15:
      extAPNAggMaxBitRate [18] ExtAPNAggMaxBitRate OPTIONAL
   ]]
}

BearerResAllocRej ::= SEQUENCE {
   esmCause [0] ESMCause,
   --<iei format="tlv">27</iei>
   protocolConfigOptions [1] ProtocolConfigOptions OPTIONAL,
   ...,
   [[ 10:
      t3396Value [2] GPRSTimer3 OPTIONAL
   ]],
   [[ 12:
      reattemptInd [3] ReattemptInd OPTIONAL
   ]],
   [[ 13:
      nbifomContainer [4] NBIFOMContainer OPTIONAL,
      extProtoConfigOpts [5] ExtProtoConfigOptions OPTIONAL
   ]]
}

BearerResAllocReq ::= SEQUENCE {
   spare [0] INTEGER (0..15) DEFAULT 0,
   linkedEPSBearerIdent [1] LinkedEPSBearerIdent,
   trafficFlowAgg [2] TFT,
   epsQoS [3] EPSQualityOfService,
   --<iei format="tlv">27</iei>
   protocolConfigOptions [4] ProtocolConfigOptions OPTIONAL,
   ...,
   [[ 10:
      deviceProperties [5] DeviceProperties OPTIONAL
   ]],
   [[ 13:
      nbifomContainer [6] NBIFOMContainer OPTIONAL,
      extProtoConfigOpts [7] ExtProtoConfigOptions OPTIONAL
   ]],
   [[ 15:
      extQOS [8] ExtQualityOfService OPTIONAL
   ]]
}

BearerResModRej ::= SEQUENCE {
   esmCause [0] ESMCause,
   --<iei format="tlv">27</iei>
   protocolConfigOptions [1] ProtocolConfigOptions OPTIONAL,
   ...,
   [[ 10:
      t3396Value [2] GPRSTimer3 OPTIONAL
   ]],
   [[ 12:
      reattemptInd [3] ReattemptInd OPTIONAL
   ]],
   [[ 13:
      nbifomContainer [4] NBIFOMContainer OPTIONAL,
      extProtoConfigOpts [5] ExtProtoConfigOptions OPTIONAL
   ]]
}

BearerResModReq ::= SEQUENCE {
   spare [0] INTEGER (0..15) DEFAULT 0,
   linkedEPSBearerIdent [1] LinkedEPSBearerIdent,
   trafficFlowAgg [2] TFT,
   --<iei format="tlv">5B</iei>
   reqTrafficFlowQoS [3] EPSQualityOfService OPTIONAL,
   --<iei format="tv" length="2">58</iei>
   esmCause [4] ESMCause OPTIONAL,
   --<iei format="tlv">27</iei>
   protocolConfigOptions [5] ProtocolConfigOptions OPTIONAL,
   ...,
   [[ 10:
      deviceProperties [6] DeviceProperties OPTIONAL
   ]],
   [[ 13:
      nbifomContainer [7] NBIFOMContainer OPTIONAL,
      hdrCompressConfigStat [8] HdrCompressConfigStat OPTIONAL,
      extProtoConfigOpts [9] ExtProtoConfigOptions OPTIONAL
   ]],
   [[ 15:
      extQOS [10] ExtQualityOfService OPTIONAL
   ]]
}

DeactEPSBearerCtxtAcc ::= SEQUENCE {
   --<iei format="tlv">27</iei>
   protocolConfigOptions [0] ProtocolConfigOptions OPTIONAL,
   ...,
   [[ 13:
      extProtoConfigOpts [1] ExtProtoConfigOptions OPTIONAL
   ]]
}

DeactEPSBearerCtxtReq ::= SEQUENCE {
   esmCause [0] ESMCause,
   --<iei format="tlv">27</iei>
   protocolConfigOptions [1] ProtocolConfigOptions OPTIONAL,
   ...,
   [[ 11:
      t3396Value [2] GPRSTimer3 OPTIONAL
   ]],
   [[ 12:
      wlanOffloadInd [3] WLANOffloadAccept OPTIONAL
   ]],
   [[ 13:
      nbifomContainer [4] NBIFOMContainer OPTIONAL,
      extProtoConfigOpts [5] ExtProtoConfigOptions OPTIONAL
   ]]
}

ESMInfoResp ::= SEQUENCE {
   --<iei format="tlv">28</iei>
   accessPointName [0] AccessPointName OPTIONAL,
   --<iei format="tlv">27</iei>
   protocolConfigOptions [1] ProtocolConfigOptions OPTIONAL,
   ...,
   [[ 13:
      extProtoConfigOpts [2] ExtProtoConfigOptions OPTIONAL
   ]]
}

ModEPSBearerCtxtAcc ::= SEQUENCE {
   --<iei format="tlv">27</iei>
   protocolConfigOptions [0] ProtocolConfigOptions OPTIONAL,
   ...,
   [[ 13:
      nbifomContainer [1] NBIFOMContainer OPTIONAL,
      extProtoConfigOpts [2] ExtProtoConfigOptions OPTIONAL
   ]]
}

ModEPSBearerCtxtRej ::= SEQUENCE {
   esmCause [0] ESMCause,
   --<iei format="tlv">27</iei>
   protocolConfigOptions [1] ProtocolConfigOptions OPTIONAL,
   ...,
   [[ 13:
      nbifomContainer [2] NBIFOMContainer OPTIONAL,
      extProtoConfigOpts [3] ExtProtoConfigOptions OPTIONAL
   ]]
}

ModEPSBearerCtxtReq ::= SEQUENCE {
   --<iei format="tlv">5B</iei>
   newEPSQoS [0] EPSQualityOfService OPTIONAL,
   --<iei format="tlv">36</iei>
   tft [1] TFT OPTIONAL,
   --<iei format="tlv">30</iei>
   newQoS [2] QualityOfService OPTIONAL,
   --<iei format="tv" length="2">32</iei>
   negotiatedLLCSAPI [3] LLCSAPIValue OPTIONAL,
   --<iei format="tv" length="1">8</iei>
   radioPriority [4] RadioPriorityValue OPTIONAL,
   --<iei format="tlv">34</iei>
   packetFlowIdentifier [5] PacketFlowIdentValue OPTIONAL,
   --<iei format="tlv">5E</iei>
   apn-AMBR [6] APNAggMaxBitRate OPTIONAL,
   --<iei format="tlv">27</iei>
   protocolConfigOptions [7] ProtocolConfigOptions OPTIONAL,
   ...,
   [[ 12:
      wlanOffloadInd [8] WLANOffloadAccept OPTIONAL
   ]],
   [[ 13:
      nbifomContainer [9] NBIFOMContainer OPTIONAL,
      hdrCompressConfigStat [10] HdrCompressConfigStat OPTIONAL,
      extProtoConfigOpts [11] ExtProtoConfigOptions OPTIONAL
   ]],
   [[ 15:
      extAPNAggMaxBitRate [12] ExtAPNAggMaxBitRate OPTIONAL,
      extQOS [13] ExtQualityOfService OPTIONAL
   ]]
}

PDNConnectRej ::= SEQUENCE {
   esmCause [0] ESMCause,
   --<iei format="tlv">27</iei>
   protocolConfigOptions [1] ProtocolConfigOptions OPTIONAL,
   ...,
   [[ 10:
      t3396Value [2] GPRSTimer3 OPTIONAL
   ]],
   [[ 12:
      reattemptInd [3] ReattemptInd OPTIONAL
   ]],
   [[ 13:
      nbifomContainer [4] NBIFOMContainer OPTIONAL,
      extProtoConfigOpts [5] ExtProtoConfigOptions OPTIONAL
   ]]
}

PDNConnectReq ::= SEQUENCE {
   pdnType [0] PDNType,
   requestType [1] RequestTypeValue,
   --<iei format="tv" length="1">D</iei>
   esmInfoXferFlag [2] ESMInfoXferFlag OPTIONAL,
   --<iei format="tlv">28</iei>
   accessPointName [3] AccessPointName OPTIONAL,
   --<iei format="tlv">27</iei>
   protocolConfigOptions [4] ProtocolConfigOptions OPTIONAL,
   ...,
   [[ 10:
      deviceProperties [5] DeviceProperties OPTIONAL
   ]],
   [[ 13:
      nbifomContainer [6] NBIFOMContainer OPTIONAL,
      hdrCompressConfig [7] HdrCompressConfig OPTIONAL,
      extProtoConfigOpts [8] ExtProtoConfigOptions OPTIONAL
   ]]
}

PDNDisconnRej ::= SEQUENCE {
   esmCause [0] ESMCause,
   --<iei format="tlv">27</iei>
   protocolConfigOptions [1] ProtocolConfigOptions OPTIONAL,
   ...,
   [[ 13:
      extProtoConfigOpts [2] ExtProtoConfigOptions OPTIONAL
   ]]
}

PDNDisconnReq ::= SEQUENCE {
   spare [0] INTEGER (0..15) DEFAULT 0,
   linkedEPSBearerIdent [1] LinkedEPSBearerIdent,
   --<iei format="tlv">27</iei>
   protocolConfigOptions [2] ProtocolConfigOptions OPTIONAL,
   ...,
   [[ 13:
      extProtoConfigOpts [3] ExtProtoConfigOptions OPTIONAL
   ]]
}

CtrlPlaneSvcReq ::= SEQUENCE {
   ctrlPlaneSvcType [0] CtrlPlaneSvcType,
   nasKeySetId [1] NASKeySetIdentifier,
   --<iei format="tlv-e">78</iei>
   esmMsgCont [2] ESMMessageContainer OPTIONAL,
   --<iei format="tlv">67</iei>
   nasMsgCont [3] NASMessageContainer OPTIONAL,
   --<iei format="tlv">57</iei>
   epsBearerContextStatus [4] EPSBearerContextStatus OPTIONAL,
   --<iei format="tv" length="1">D</iei>
   deviceProperties [5] DeviceProperties OPTIONAL
}

ESMDataTransport ::= SEQUENCE {
   userDataContainer [0] OCTET STRING,
   --<iei format="tv" length="1">F</iei>
   releaseAssistInd [1] ReleaseAssistInd OPTIONAL
}

ServiceAccept ::= SEQUENCE {
   --<iei format="tlv">57</iei>
   epsBearerContextStatus [0] EPSBearerContextStatus OPTIONAL,
   --<iei format="tlv">6B</iei>
   t3448Value [1] GPRSTimer2 OPTIONAL
}

PDU ::= SEQUENCE {
   --<cEncSrcFname>TS24301MsgEnc_PDU_secHdr.c</cEncSrcFname>
   --<cDecSrcFname>TS24301MsgDec_PDU_secHdr.c</cDecSrcFname>
   secHdr [0] SecProtMsgHeader OPTIONAL,
   l3HdrOpts [1] EXPLICIT L3HdrOptions, -- L3 header, octet 1, bits 5 thru 8
   --<cDecSrcFname>PDU_protoDiscr.c</cDecSrcFname>
   protoDiscr [2] NAS-PROTOCOL-CLASS.&protoDiscr ({TS24301-IE-OBJECTSET}),
   --<inline/>
   pti [3] EXPLICIT CHOICE {
      --<selector element="protoDiscr" value="2"/>
      value [0] INTEGER (0..255),
      noValue [1] NULL
   },
   msgType [4] NAS-PROTOCOL-CLASS.&msgType ({TS24301-IE-OBJECTSET}) (0..255),
   data [5] EXPLICIT NAS-PROTOCOL-CLASS.&Value ({TS24301-IE-OBJECTSET}{@
      protoDiscr,@msgType}),
   --<cEncSrcFname>TS24301MsgEnc_PDU_eom.c</cEncSrcFname>   
   --<cDecSrcFname>TS24301MsgDec_PDU_eom.c</cDecSrcFname>   
   eom [6] NULL
}

Notification ::= SEQUENCE {
   --<is3GLength/>
   length [0] INTEGER (1),
   value [1] INTEGER (0..255)
}

RemoteUEReport ::= SEQUENCE {
   --<iei format="tlv-e">79</iei>
   remoteUECtxtConn [0] RemoteUECtxtList OPTIONAL,
   --<iei format="tlv-e">7A</iei>
   remoteUECtxtDisconn [1] RemoteUECtxtList OPTIONAL,
   --<iei format="tlv">6F</iei>
   proSeKeyMgmtFunc [2] PKMFAddress OPTIONAL
}

-- Value assignments

mt-AttachAccept INTEGER ::= 66

mt-AttachComplete INTEGER ::= 67

mt-AttachReject INTEGER ::= 68

mt-AttachRequest INTEGER ::= 65

mt-AuthFailure INTEGER ::= 92

mt-AuthReject INTEGER ::= 84

mt-AuthRequest INTEGER ::= 82

mt-AuthResponse INTEGER ::= 83

mt-CSServiceNotif INTEGER ::= 100

mt-DetachAccept INTEGER ::= 70

mt-DetachRequest INTEGER ::= 69

mt-DLNASTransport INTEGER ::= 98

mt-EMMInformation INTEGER ::= 97

mt-EMMStatus INTEGER ::= 96

mt-ExtServiceReq INTEGER ::= 76

mt-GUTIReallocCmd INTEGER ::= 80

mt-GUTIReallocCmplt INTEGER ::= 81

mt-IdentReq INTEGER ::= 85

mt-IdentResp INTEGER ::= 86

mt-SecModeCmd INTEGER ::= 93

mt-SecModeCmplt INTEGER ::= 94

mt-SecModeReject INTEGER ::= 95

mt-ServiceReject INTEGER ::= 78

mt-ServiceRequest INTEGER ::= 0

mt-TrkAreaUpdAccept INTEGER ::= 73

mt-TrkAreaUpdCmplt INTEGER ::= 74

mt-TrkAreaUpdReject INTEGER ::= 75

mt-TrkAreaUpdRequest INTEGER ::= 72

mt-ULNASTransport INTEGER ::= 99

mt-DLGenNASTransport INTEGER ::= 104

mt-ULGenNASTransport INTEGER ::= 105

mt-CtrlPlaneSvcReq INTEGER ::= 77

mt-ServiceAccept INTEGER ::= 79

mt-ActvDedEPSBearerCtxtAcc INTEGER ::= 198

mt-ActvDedEPSBearerCtxtRej INTEGER ::= 199

mt-ActvDedEPSBearerCtxtReq INTEGER ::= 197

mt-ActvDfltEPSBearerCtxtAcc INTEGER ::= 194

mt-ActvDfltEPSBearerCtxtRej INTEGER ::= 195

mt-ActvDfltEPSBearerCtxtReq INTEGER ::= 193

mt-BearerResAllocRej INTEGER ::= 213

mt-BearerResAllocReq INTEGER ::= 212

mt-BearerResModRej INTEGER ::= 215

mt-BearerResModReq INTEGER ::= 214

mt-DeactEPSBearerCtxtAcc INTEGER ::= 206

mt-DeactEPSBearerCtxtReq INTEGER ::= 205

mt-ESMDummyMsg INTEGER ::= 220

mt-ESMInfoReq INTEGER ::= 217

mt-ESMInfoResp INTEGER ::= 218

mt-ESMStatus INTEGER ::= 232

mt-ModEPSBearerCtxtAcc INTEGER ::= 202

mt-ModEPSBearerCtxtRej INTEGER ::= 203

mt-ModEPSBearerCtxtReq INTEGER ::= 201

mt-Notification INTEGER ::= 219

mt-PDNConnectRej INTEGER ::= 209

mt-PDNConnectReq INTEGER ::= 208

mt-PDNDisconnRej INTEGER ::= 211

mt-PDNDisconnReq INTEGER ::= 210

mt-RemoteUEReport INTEGER ::= 233

mt-RemoteUEReportResp INTEGER ::= 234

mt-ESMDataTransport INTEGER ::= 235


-- Information Object definitions

obj-AttachAccept NAS-PROTOCOL-CLASS ::= {
   &protoDiscr epsMobMgmt, 
   &msgType mt-AttachAccept, 
   &Value AttachAccept
}


obj-AttachComplete NAS-PROTOCOL-CLASS ::= {
   &protoDiscr epsMobMgmt, 
   &msgType mt-AttachComplete, 
   &Value AttachComplete
}


obj-AttachReject NAS-PROTOCOL-CLASS ::= {
   &protoDiscr epsMobMgmt, 
   &msgType mt-AttachReject, 
   &Value AttachReject
}


obj-AttachRequest NAS-PROTOCOL-CLASS ::= {
   &protoDiscr epsMobMgmt, 
   &msgType mt-AttachRequest, 
   &Value AttachRequest
}


obj-AuthFailure NAS-PROTOCOL-CLASS ::= {
   &protoDiscr epsMobMgmt, 
   &msgType mt-AuthFailure, 
   &Value AuthFailure
}


obj-AuthReject NAS-PROTOCOL-CLASS ::= {
   &protoDiscr epsMobMgmt, 
   &msgType mt-AuthReject, 
   &Value NULL
}


obj-AuthRequest NAS-PROTOCOL-CLASS ::= {
   &protoDiscr epsMobMgmt, 
   &msgType mt-AuthRequest, 
   &Value AuthRequest
}


obj-AuthResponse NAS-PROTOCOL-CLASS ::= {
   &protoDiscr epsMobMgmt, 
   &msgType mt-AuthResponse, 
   &Value AuthResponse
}


obj-CSServiceNotif NAS-PROTOCOL-CLASS ::= {
   &protoDiscr epsMobMgmt, 
   &msgType mt-CSServiceNotif, 
   &Value CSServiceNotif
}


obj-DetachAccept NAS-PROTOCOL-CLASS ::= {
   &protoDiscr epsMobMgmt, 
   &msgType mt-DetachAccept, 
   &Value NULL
}


obj-DetachRequest NAS-PROTOCOL-CLASS ::= {
   &protoDiscr epsMobMgmt, 
   &msgType mt-DetachRequest, 
   &Value DetachRequest
}


obj-DLNASTransport NAS-PROTOCOL-CLASS ::= {
   &protoDiscr epsMobMgmt, 
   &msgType mt-DLNASTransport, 
   &Value DLNASTransport
}


obj-EMMInformation NAS-PROTOCOL-CLASS ::= {
   &protoDiscr epsMobMgmt, 
   &msgType mt-EMMInformation, 
   &Value EMMInformation
}


obj-EMMStatus NAS-PROTOCOL-CLASS ::= {
   &protoDiscr epsMobMgmt, 
   &msgType mt-EMMStatus, 
   &Value EMMStatus
}


obj-ExtServiceReq NAS-PROTOCOL-CLASS ::= {
   &protoDiscr epsMobMgmt, 
   &msgType mt-ExtServiceReq, 
   &Value ExtServiceReq
}


obj-GUTIReallocCmd NAS-PROTOCOL-CLASS ::= {
   &protoDiscr epsMobMgmt, 
   &msgType mt-GUTIReallocCmd, 
   &Value GUTIReallocCmd
}


obj-GUTIReallocCmplt NAS-PROTOCOL-CLASS ::= {
   &protoDiscr epsMobMgmt, 
   &msgType mt-GUTIReallocCmplt, 
   &Value NULL
}


obj-IdentReq NAS-PROTOCOL-CLASS ::= {
   &protoDiscr epsMobMgmt, 
   &msgType mt-IdentReq, 
   &Value IdentReq
}


obj-IdentResp NAS-PROTOCOL-CLASS ::= {
   &protoDiscr epsMobMgmt, 
   &msgType mt-IdentResp, 
   &Value IdentResp
}


obj-SecModeCmd NAS-PROTOCOL-CLASS ::= {
   &protoDiscr epsMobMgmt, 
   &msgType mt-SecModeCmd, 
   &Value SecModeCmd
}


obj-SecModeCmplt NAS-PROTOCOL-CLASS ::= {
   &protoDiscr epsMobMgmt, 
   &msgType mt-SecModeCmplt, 
   &Value SecModeCmplt
}


obj-SecModeReject NAS-PROTOCOL-CLASS ::= {
   &protoDiscr epsMobMgmt, 
   &msgType mt-SecModeReject, 
   &Value SecModeReject
}


obj-ServiceReject NAS-PROTOCOL-CLASS ::= {
   &protoDiscr epsMobMgmt, 
   &msgType mt-ServiceReject, 
   &Value ServiceReject
}


obj-ServiceRequest NAS-PROTOCOL-CLASS ::= {
   &protoDiscr epsMobMgmt, 
   &msgType mt-ServiceRequest, 
   &Value ServiceRequest
}


obj-TrkAreaUpdAccept NAS-PROTOCOL-CLASS ::= {
   &protoDiscr epsMobMgmt, 
   &msgType mt-TrkAreaUpdAccept, 
   &Value TrkAreaUpdAccept
}


obj-TrkAreaUpdCmplt NAS-PROTOCOL-CLASS ::= {
   &protoDiscr epsMobMgmt, 
   &msgType mt-TrkAreaUpdCmplt, 
   &Value NULL
}


obj-TrkAreaUpdReject NAS-PROTOCOL-CLASS ::= {
   &protoDiscr epsMobMgmt, 
   &msgType mt-TrkAreaUpdReject, 
   &Value TrkAreaUpdReject
}


obj-TrkAreaUpdRequest NAS-PROTOCOL-CLASS ::= {
   &protoDiscr epsMobMgmt, 
   &msgType mt-TrkAreaUpdRequest, 
   &Value TrkAreaUpdRequest
}


obj-ULNASTransport NAS-PROTOCOL-CLASS ::= {
   &protoDiscr epsMobMgmt, 
   &msgType mt-ULNASTransport, 
   &Value ULNASTransport
}


obj-DLGenNASTransport NAS-PROTOCOL-CLASS ::= {
   &protoDiscr epsMobMgmt, 
   &msgType mt-DLGenNASTransport, 
   &Value DLGenNASTransport
}


obj-ULGenNASTransport NAS-PROTOCOL-CLASS ::= {
   &protoDiscr epsMobMgmt, 
   &msgType mt-ULGenNASTransport, 
   &Value ULGenNASTransport
}


obj-CtrlPlaneSvcReq NAS-PROTOCOL-CLASS ::= {
   &protoDiscr epsMobMgmt, 
   &msgType mt-CtrlPlaneSvcReq, 
   &Value CtrlPlaneSvcReq
}


obj-ServiceAccept NAS-PROTOCOL-CLASS ::= {
   &protoDiscr epsMobMgmt, 
   &msgType mt-ServiceAccept, 
   &Value ServiceAccept
}


obj-ActvDedEPSBearerCtxtAcc NAS-PROTOCOL-CLASS ::= {
   &protoDiscr epsSessMgmt, 
   &msgType mt-ActvDedEPSBearerCtxtAcc, 
   &Value ActvDedEPSBearerCtxtAcc
}


obj-ActvDedEPSBearerCtxtRej NAS-PROTOCOL-CLASS ::= {
   &protoDiscr epsSessMgmt, 
   &msgType mt-ActvDedEPSBearerCtxtRej, 
   &Value ActvDedEPSBearerCtxtRej
}


obj-ActvDedEPSBearerCtxtReq NAS-PROTOCOL-CLASS ::= {
   &protoDiscr epsSessMgmt, 
   &msgType mt-ActvDedEPSBearerCtxtReq, 
   &Value ActvDedEPSBearerCtxtReq
}


obj-ActvDfltEPSBearerCtxtAcc NAS-PROTOCOL-CLASS ::= {
   &protoDiscr epsSessMgmt, 
   &msgType mt-ActvDfltEPSBearerCtxtAcc, 
   &Value ActvDfltEPSBearerCtxtAcc
}


obj-ActvDfltEPSBearerCtxtRej NAS-PROTOCOL-CLASS ::= {
   &protoDiscr epsSessMgmt, 
   &msgType mt-ActvDfltEPSBearerCtxtRej, 
   &Value ActvDfltEPSBearerCtxtRej
}


obj-ActvDfltEPSBearerCtxtReq NAS-PROTOCOL-CLASS ::= {
   &protoDiscr epsSessMgmt, 
   &msgType mt-ActvDfltEPSBearerCtxtReq, 
   &Value ActvDfltEPSBearerCtxtReq
}


obj-BearerResAllocRej NAS-PROTOCOL-CLASS ::= {
   &protoDiscr epsSessMgmt, 
   &msgType mt-BearerResAllocRej, 
   &Value BearerResAllocRej
}


obj-BearerResAllocReq NAS-PROTOCOL-CLASS ::= {
   &protoDiscr epsSessMgmt, 
   &msgType mt-BearerResAllocReq, 
   &Value BearerResAllocReq
}


obj-BearerResModRej NAS-PROTOCOL-CLASS ::= {
   &protoDiscr epsSessMgmt, 
   &msgType mt-BearerResModRej, 
   &Value BearerResModRej
}


obj-BearerResModReq NAS-PROTOCOL-CLASS ::= {
   &protoDiscr epsSessMgmt, 
   &msgType mt-BearerResModReq, 
   &Value BearerResModReq
}


obj-DeactEPSBearerCtxtAcc NAS-PROTOCOL-CLASS ::= {
   &protoDiscr epsSessMgmt, 
   &msgType mt-DeactEPSBearerCtxtAcc, 
   &Value DeactEPSBearerCtxtAcc
}


obj-DeactEPSBearerCtxtReq NAS-PROTOCOL-CLASS ::= {
   &protoDiscr epsSessMgmt, 
   &msgType mt-DeactEPSBearerCtxtReq, 
   &Value DeactEPSBearerCtxtReq
}


obj-ESMDummyMsg NAS-PROTOCOL-CLASS ::= {
   &protoDiscr epsSessMgmt, 
   &msgType mt-ESMDummyMsg, 
   &Value NULL
}


obj-ESMInfoReq NAS-PROTOCOL-CLASS ::= {
   &protoDiscr epsSessMgmt, 
   &msgType mt-ESMInfoReq, 
   &Value NULL
}


obj-ESMInfoResp NAS-PROTOCOL-CLASS ::= {
   &protoDiscr epsSessMgmt, 
   &msgType mt-ESMInfoResp, 
   &Value ESMInfoResp
}


obj-ESMStatus NAS-PROTOCOL-CLASS ::= {
   &protoDiscr epsSessMgmt, 
   &msgType mt-ESMStatus, 
   &Value ESMStatus
}


obj-ModEPSBearerCtxtAcc NAS-PROTOCOL-CLASS ::= {
   &protoDiscr epsSessMgmt, 
   &msgType mt-ModEPSBearerCtxtAcc, 
   &Value ModEPSBearerCtxtAcc
}


obj-ModEPSBearerCtxtRej NAS-PROTOCOL-CLASS ::= {
   &protoDiscr epsSessMgmt, 
   &msgType mt-ModEPSBearerCtxtRej, 
   &Value ModEPSBearerCtxtRej
}


obj-ModEPSBearerCtxtReq NAS-PROTOCOL-CLASS ::= {
   &protoDiscr epsSessMgmt, 
   &msgType mt-ModEPSBearerCtxtReq, 
   &Value ModEPSBearerCtxtReq
}


obj-Notification NAS-PROTOCOL-CLASS ::= {
   &protoDiscr epsSessMgmt, 
   &msgType mt-Notification, 
   &Value Notification
}


obj-PDNConnectRej NAS-PROTOCOL-CLASS ::= {
   &protoDiscr epsSessMgmt, 
   &msgType mt-PDNConnectRej, 
   &Value PDNConnectRej
}


obj-PDNConnectReq NAS-PROTOCOL-CLASS ::= {
   &protoDiscr epsSessMgmt, 
   &msgType mt-PDNConnectReq, 
   &Value PDNConnectReq
}


obj-PDNDisconnRej NAS-PROTOCOL-CLASS ::= {
   &protoDiscr epsSessMgmt, 
   &msgType mt-PDNDisconnRej, 
   &Value PDNDisconnRej
}


obj-PDNDisconnReq NAS-PROTOCOL-CLASS ::= {
   &protoDiscr epsSessMgmt, 
   &msgType mt-PDNDisconnReq, 
   &Value PDNDisconnReq
}


obj-RemoteUEReport NAS-PROTOCOL-CLASS ::= {
   &protoDiscr epsSessMgmt, 
   &msgType mt-RemoteUEReport, 
   &Value RemoteUEReport
}


obj-RemoteUEReportResp NAS-PROTOCOL-CLASS ::= {
   &protoDiscr epsSessMgmt, 
   &msgType mt-RemoteUEReportResp, 
   &Value RemoteUEReportResp
}


obj-ESMDataTransport NAS-PROTOCOL-CLASS ::= {
   &protoDiscr epsSessMgmt, 
   &msgType mt-ESMDataTransport, 
   &Value ESMDataTransport
}


-- Information Object Set definitions

TS24301-IE-OBJECTSET NAS-PROTOCOL-CLASS ::= {obj-AttachAccept | 
   obj-AttachComplete | obj-AttachReject | obj-AttachRequest | obj-AuthFailure
    | obj-AuthReject | obj-AuthRequest | obj-AuthResponse | obj-CSServiceNotif
    | obj-DetachAccept | obj-DetachRequest | obj-DLNASTransport | 
   obj-EMMInformation | obj-EMMStatus | obj-ExtServiceReq | obj-GUTIReallocCmd
    | obj-GUTIReallocCmplt | obj-IdentReq | obj-IdentResp | obj-SecModeCmd | 
   obj-SecModeCmplt | obj-SecModeReject | obj-ServiceRequest | 
   obj-ServiceReject | obj-TrkAreaUpdAccept | obj-TrkAreaUpdCmplt | 
   obj-TrkAreaUpdReject | obj-TrkAreaUpdRequest | obj-ULNASTransport | 
   obj-ULGenNASTransport | obj-DLGenNASTransport | obj-ActvDedEPSBearerCtxtAcc
    | obj-ActvDedEPSBearerCtxtRej | obj-ActvDedEPSBearerCtxtReq | 
   obj-ActvDfltEPSBearerCtxtAcc | obj-ActvDfltEPSBearerCtxtRej | 
   obj-ActvDfltEPSBearerCtxtReq | obj-BearerResAllocRej | obj-BearerResAllocReq
    | obj-BearerResModRej | obj-BearerResModReq | obj-DeactEPSBearerCtxtAcc | 
   obj-DeactEPSBearerCtxtReq | obj-ESMInfoReq | obj-ESMInfoResp | obj-ESMStatus
    | obj-ModEPSBearerCtxtAcc | obj-ModEPSBearerCtxtRej | 
   obj-ModEPSBearerCtxtReq | obj-PDNConnectRej | obj-PDNConnectReq | 
   obj-PDNDisconnRej | obj-PDNDisconnReq | obj-CtrlPlaneSvcReq | 
   obj-ESMDataTransport | obj-ServiceAccept,...}

END
TS24501Msgs DEFINITIONS AUTOMATIC TAGS ::= BEGIN

IMPORTS

AuthParamAUTN, AuthParamRAND, AuthFailureParam, GPRSTimer, GPRSTimer2, 
   GPRSTimer3, ExtProtoConfigOptions, IMEISVRequest, MCCMNCPair, IMEI, IMEISV, 
   NetworkName, TimeZone, TimeZoneAndTime, DaylightSavingTime, PLMNList, 
   EmergencyNumberList, MobileStationClassmark2, SupportedCodecList, 
   ExtDRXParams, Non3GPPNetPolicies, TBCDString
FROM TS24008IES 

AuthRespParam, NASKeySetIdentifier, NASSecurityAlgorithms, UENetworkCapability
   , UEStatus, ExtEmergencyNumberList, EPSBearerContextStatus, UERadioCapId, 
   UERadioCapIdDeletionInd, ReleaseAssistInd, NASMessageContainer
FROM TS24301IES ;

-- Productions

NAS5GProtoDiscr ::= ENUMERATED { sessMgmt5G(46), mobMgmt5G(126), 
   maxProtoDiscr(255) }

NAS5GSecHdrType ::= ENUMERATED { noSec(0), integProt(1), integProtAndCipher(2)
   , integProtAnd5GSecCtxt(3), integProtAndCipherAnd5GSecCtxt(4), secMax(15) }

PDUSessionIdentity ::= ENUMERATED { noPduId(0), pduId1(1), pduId2(2), pduId3(3)
   , pduId4(4), pduId5(5), pduId6(6), pduId7(7), pduId8(8), pduId9(9), 
   pduId10(10), pduId11(11), pduId12(12), pduId13(13), pduId14(14), pduId15(15)
   , pduIdMax(255) }

-- 9.11.2.1 - Additional information 
AdditionalInfo ::= OCTET STRING

-- 9.11.2.1B - DNN 
DNNList ::= OCTET STRING

EAPFormatCode ::= ENUMERATED { request(1), response(2), success(3), failure(4)
   , codeMax(255) }

-- 9.11.2.7 - N1 mode to S1 mode NAS transparent container 
N1ToS1NASContainer ::= INTEGER (1..255)

SST ::= INTEGER (1..255)

SD ::= INTEGER (1..16777215)

-- 9.11.3.2 - MM cause 
MMCause ::= ENUMERATED { illegalUE(3), peiNotAccept(5), illegalME(6), 
   svcNotAllowed(7), idNotDerived(9), implDereg(10), plmnNotAllowed(11), 
   trkAreaNotAllowed(12), roamNotAllowed(13), noCells(15), macFailure(20), 
   synchFailure(21), congestion(22), secCapMismatch(23), secModeRej(24), 
   authUnaccept(26), n1ModeNotAllowed(27), restrictedArea(28), redirToEpc(31), 
   ladnUnavail(43), noNetSlices(62), maxSessions(65), insuffResDNN(67), 
   insuffResSlice(69), ngksiInUse(71), accTo5GNotAllowed(72), netNotAuth(73), 
   noTempAuthSnpn(74), noPermAuthSnpn(75), noAuthCag(76), notForwarded(90), 
   dnnUnsupp(91), insuffRes(92), semIncorrectMsg(95), invMandInfo(96), 
   msgTypeNotExist(97), msgTypeNotCompat(98), infoElemNotExist(99), 
   condIEError(100), msgNotCompat(101), unspecProtoErr(111), mmCauseMAX(255) }

TypeOfIdentity ::= ENUMERATED { none(0), suci(1), guti(2), imei(3), stmsi(4), 
   imeisv(5), macAddr(6), eui64(7) }

RegistrationResultValue ::= ENUMERATED { access(1), nonAccess(2), 
   accessAndNonAccess(3), regResultMAX(7) }

RegistrationTypeValue ::= ENUMERATED { initial(1), mobilityUpdate(2), 
   periodicUpdate(3), emergency(4), regisTypeMAX(7) }

TrackingAreaCode ::= OCTET STRING (SIZE (3))

-- 9.11.3.10 - ABBA 
ABBA ::= OCTET STRING -- (preceeded by 1 octet length)


CIoTDataTypes ::= ENUMERATED { ciotCtrlPlaneUserData(0), ciotSMS(1), 
   ciotLocSvcsMsg(2), ciotMAX(7) }

-- 9.11.3.40 - Payload container type 
PayloadContainerType ::= ENUMERATED { n1SmInfo(1), sms(2), lppMessage(3), 
   transparent(4), uePolicy(5), ueParams(6), locSvcs(7), ciotUserData(8), 
   multPayloads(15) }

-- 9.11.3.41 - PDU session identity 2 
PDUSessionId2 ::= INTEGER (0..255)

-- 9.11.3.42 - PDU session reactivation result 
SessionReactivateRslt ::= SEQUENCE {
   --<is3GLength/>
   length [0] INTEGER (1..255),
   psi [1] SEQUENCE (SIZE (16)) OF BOOLEAN,
   --<length fixed-size="0"/>
   --<noPresentBit/>
   spare [2] OCTET STRING OPTIONAL
}

-- 9.11.3.44 - PDU session status 
PDUSessionStatus ::= SessionReactivateRslt

RequestTypes ::= ENUMERATED { initialReq(1), existPduSession(2), 
   initialEmerReq(3), emerPduSession(4), modifyReq(5), reqTypeMAX(7) }

-- 9.11.3.50 - Service type 
ServiceType ::= ENUMERATED { signaling(0), data(1), mobTermSvc(2), emerSvc(3), 
   emerSvcFallback(4), hiPriAccess(5), elevSignal(6), serviceTypeMAX(15) }

-- 9.11.4.2 - SM cause 
SMCause ::= ENUMERATED { opBarring(8), insuffResources(26), unkOrMissDNN(27), 
   unknownPDUType(28), userAuthFailed(29), reqRejectUnspecified(31), 
   optNotSupported(32), reqSvcOptNotSubscr(33), svcOptTempOutOfOrder(34), 
   ptiAlreadyInUse(35), regularDeactivation(36), networkFailure(38), 
   reactivateRequest(39), semanticErrTft(41), syntaxErrTft(42), invPduId(43), 
   semanticErrInFilter(44), syntaxErrInFilter(45), outOfArea(46), 
   ptiMismatch(47), pdnTypeIPv4OnlyAllow(50), pdnTypeIPv6OnlyAllow(51), 
   pduNotExist(54), pdnTypeIPv4v6OnlyAllow(57), pdnTypeUnstructOnlyAllow(58), 
   pdnTypeEthOnlyAllow(61), insufResForDNN(67), notSuppSSCMode(68), 
   insufResForSlice(69), unkOrMissDNNInSlice(70), invPTIValue(81), 
   maxDRTooLow(82), semanticErrQoS(83), syntaxErrQoS(84), invEpsId(85), 
   semIncorrectMessage(95), invMandatoryInfo(96), msgTypeNonExistOrNotImpl(97)
   , msgTypeNotCompatWithProtoState(98), ieNonExistOrNotImpl(99), 
   condIEError(100), msgNotCompatWithProtoState(101), 
   protocolErrorUnspecified(111), smCauseMAX(255) }

MaxDataRates ::= ENUMERATED { dr64kbps(0), drFull(255) }

FlowOpCodes ::= ENUMERATED { flowCreate(1), flowDelete(2), flowModify(3), 
   ruleOpMax(7) }

RuleOpCodes ::= ENUMERATED { createNew(1), delete(2), modifyAndAdd(3), 
   modifyAndReplace(4), modifyAndDelete(5), modifyNoModify(6), ruleOpMax(7) }

PacketFilterTypeId ::= ENUMERATED { matchAll(1), ipv4Remote(16), ipv4Local(17)
   , ipv6Remote(33), ipv6Local(35), protId(48), singleLocalPort(64), 
   localPortRange(65), singleRemPort(80), remPortRange(81), secParam(96), 
   typeOfSvc(112), flowLabel(128), destMacAddr(129), srcMacAddr(130), 
   ctagVid(131), stagVid(132), ctagPcp(133), stagPcp(134), ethernet(135), 
   typeIdMax(255) }

SessionUnits ::= ENUMERATED { unused(0), mult1kbps(1), mult4kbps(2), 
   mult16kbps(3), mult64kbps(4), mult256kbps(5), mult1mbps(6), mult4mbps(7), 
   mult16mbps(8), mult64mbps(9), mult256mbps(10), mult1gbps(11), mult4gbps(12)
   , mult16gbps(13), mult64gbps(14), mult256gbps(15), mult1tbps(16), 
   unitsMax(255) }

NAS5GSecProtMsgHdr ::= SEQUENCE {
   protoDiscr [0] NAS5GProtoDiscr,
   spare1 [1] INTEGER (0..15) DEFAULT 0,
   secHdrType [2] NAS5GSecHdrType,
   msgAuthCode [3] INTEGER (0..4294967295), -- Message authentication code (MAC)
   seqNumber [4] INTEGER (0..255) -- Sequence number
}

-- 9.11.2.2 - EAP message 
EAPMessage ::= SEQUENCE {
   --<is3GLength bitFieldSize="16"/>
   length [0] INTEGER (1..65535),
   --<asn1typename>EAPPacketFormat</asn1typename>
   packetFormat [1] SEQUENCE {
      code [0] EAPFormatCode,
      id [1] INTEGER (1..255),
      length [2] INTEGER (1..65535),
      --<length expr="@.length"/>
      data [3] OCTET STRING
   }
}

--<is3GMessage/>
AuthRequest ::= SEQUENCE {
   spare [0] INTEGER (0..15) DEFAULT 0,
   nasKeySetIdent [1] NASKeySetIdentifier,
   -- This field was added as optional in 15.1 and made mandatory in 15.3... 
   abba [2] ABBA, -- 9.11.3.10
   --<iei format="tv" length="17">21</iei>
   authParamRAND [3] AuthParamRAND OPTIONAL,
   --<iei format="tlv">20</iei>
   authParamAUTN [4] AuthParamAUTN OPTIONAL,
   --<iei format="tlv-e">78</iei>
   eapMessage [5] EAPMessage OPTIONAL
}

--<is3GMessage/>
AuthResponse ::= SEQUENCE {
   --<iei format="tlv">2D</iei>
   authRespParam [0] AuthRespParam OPTIONAL,
   --<iei format="tlv-e">78</iei>
   eapMessage [1] EAPMessage OPTIONAL
}

--<is3GMessage/>
AuthResult ::= SEQUENCE {
   spare [0] INTEGER (0..15) DEFAULT 0,
   nasKeySetIdent [1] NASKeySetIdentifier,
   eapMessage [2] EAPMessage,
   --<iei format="tlv">38</iei>
   abba [3] ABBA OPTIONAL -- added in v15.2.0
}

--<is3GMessage/>
AuthFailure ::= SEQUENCE {
   cause [0] MMCause,
   --<iei format="tlv">30</iei>
   authFailureParam [1] AuthFailureParam OPTIONAL
}

--<is3GMessage/>
AuthReject ::= SEQUENCE {
   --<iei format="tlv-e">78</iei>
   eapMessage [0] EAPMessage OPTIONAL -- added in v15.2.0
}

-- 9.11.3.7 - Registration type 
RegistrationType ::= SEQUENCE {
   forBit [0] BOOLEAN,
   regisType [1] RegistrationTypeValue
}

MobileIdentity_SUCI_IMSI ::= SEQUENCE {
   mcc-mnc [0] MCCMNCPair,
   routingInd2 [1] INTEGER (0..15),
   routingInd1 [2] INTEGER (0..15),
   routingInd4 [3] INTEGER (0..15),
   routingInd3 [4] INTEGER (0..15),
   spare [5] INTEGER (0..15) DEFAULT 0,
   protSchemeId [6] INTEGER (0..15),
   homeNetId [7] INTEGER (0..255),
   --<length fixed-size="0"/>
   schemeOutput [8] OCTET STRING
}

MobileIdentity_SUCI_NetId ::= SEQUENCE {
   --<length fixed-size="0">
   nai [0] OCTET STRING
}

MobileIdentity_GUTI ::= SEQUENCE {
   mcc-mnc [0] MCCMNCPair,
   amfRegionID [1] INTEGER (0..255),
   amfSetID [2] INTEGER (0..1023),
   amfPointer [3] INTEGER (0..63),
   tmsi [4] OCTET STRING (SIZE (4))
}

MobileIdentity_STMSI ::= SEQUENCE {
   amfSetID [0] INTEGER (0..1023),
   amfPointer [1] INTEGER (0..63),
   tmsi [2] OCTET STRING (SIZE (4))
}

MobileIdentity_MAC ::= SEQUENCE {
   mauri [0] BOOLEAN,
   macaddr [1] OCTET STRING (SIZE (6))
}

-- 9.11.3.4 - 5G mobile identity 
MobileIdentity ::= CHOICE {
   none [0] NULL,
   suci [1] EXPLICIT CHOICE {
      -- The supiFormat bit in the MobileIdentity determines which of these
      -- choices is present in an encoding.
      supiImsi [0] MobileIdentity_SUCI_IMSI,
      supiNetSpecificId [1] MobileIdentity_SUCI_NetId
   },
   guti [2] MobileIdentity_GUTI,
   imei [3] IMEI,
   stmsi [4] MobileIdentity_STMSI,
   imeisv [5] IMEISV,
   mac [6] MobileIdentity_MAC,
   eui-64 [7] OCTET STRING (SIZE (8))
}

-- 9.11.3.1 - MM capability 
MMCapability ::= SEQUENCE {
   --<is3GLength/>
   length [0] INTEGER (1..255) DEFAULT 1,
   -- octet 3 
   sgc [1] BOOLEAN,
   hcCpCIoT [2] BOOLEAN,
   n3Data [3] BOOLEAN,
   cpCIoT [4] BOOLEAN,
   restrictedEC [5] BOOLEAN,
   lppSupported [6] BOOLEAN,
   handoverSupported [7] BOOLEAN,
   s1Supported [8] BOOLEAN,
   --<noPresentBit/>
   octet4 [9] SEQUENCE {
      racs [0] BOOLEAN,
      nssaa [1] BOOLEAN,
      lcs [2] BOOLEAN,
      v2xcnpc5 [3] BOOLEAN,
      v2xcepc5 [4] BOOLEAN,
      v2x [5] BOOLEAN,
      upCIoT [6] BOOLEAN,
      srvcc [7] BOOLEAN
   } OPTIONAL,
   --<noPresentBit/>
   octet5 [10] SEQUENCE {
      spare1 [0] INTEGER (0..127) DEFAULT 0,
      cag [1] BOOLEAN
   } OPTIONAL,
   --<noPresentBit/>
   --<length fixed-size="0"/>
   spare2 [11] OCTET STRING OPTIONAL
}

-- 9.11.3.54 - UE security capability 
UESecurityCapability ::= SEQUENCE {
   --<is3GLength/>
   length [0] INTEGER (0..255),
   -- octet 3 
   ea0 [1] BOOLEAN,
   ea1 [2] BOOLEAN,
   ea2 [3] BOOLEAN,
   ea3 [4] BOOLEAN,
   ea4 [5] BOOLEAN,
   ea5 [6] BOOLEAN,
   ea6 [7] BOOLEAN,
   ea7 [8] BOOLEAN,
   -- octet 4 
   ia0 [9] BOOLEAN,
   ia1 [10] BOOLEAN,
   ia2 [11] BOOLEAN,
   ia3 [12] BOOLEAN,
   ia4 [13] BOOLEAN,
   ia5 [14] BOOLEAN,
   ia6 [15] BOOLEAN,
   ia7 [16] BOOLEAN,
   -- octet 5 
   --<noPresentBit/>
   octet5 [17] SEQUENCE {
      eea0 [0] BOOLEAN,
      eea1 [1] BOOLEAN,
      eea2 [2] BOOLEAN,
      eea3 [3] BOOLEAN,
      eea4 [4] BOOLEAN,
      eea5 [5] BOOLEAN,
      eea6 [6] BOOLEAN,
      eea7 [7] BOOLEAN
   } OPTIONAL,
   -- octet 6 
   --<noPresentBit/>
   octet6 [18] SEQUENCE {
      eia0 [0] BOOLEAN,
      eia1 [1] BOOLEAN,
      eia2 [2] BOOLEAN,
      eia3 [3] BOOLEAN,
      eia4 [4] BOOLEAN,
      eia5 [5] BOOLEAN,
      eia6 [6] BOOLEAN,
      eia7 [7] BOOLEAN
   } OPTIONAL,
   --<noPresentBit/>
   spare [19] OCTET STRING OPTIONAL
}

-- 9.11.2.8 - S-NSSAI 
SNSSAI ::= SEQUENCE {
   --<is3GLength/>
   length [0] INTEGER (1..255),
   sst [1] SST,
   --<noPresentBit/>
   sd [2] SD OPTIONAL,
   --<noPresentBit/>
   mappedSST [3] OCTET STRING (SIZE (1)) OPTIONAL,
   --<noPresentBit/>
   mappedSD [4] OCTET STRING (SIZE (3)) OPTIONAL
}

-- 9.11.3.37 - NSSAI 
NSSAI ::= SEQUENCE {
   --<is3GLength/>
   length [0] INTEGER (1..255),
   --<is3GVarLenList lengthElem="length"/>
   contents [1] SEQUENCE (SIZE (1..16)) OF SNSSAI
}

-- 9.11.3.8 - Tracking area identity 
-- Mostly the same as 24.301 except the TAC is 3 octets instead of 2... 
TrackingAreaIdent ::= SEQUENCE {
   mcc-mnc [0] MCCMNCPair,
   tac [1] TrackingAreaCode
}

-- 9.11.3.57 - Uplink data status 
UplinkDataStatus ::= SEQUENCE {
   --<is3GLength/>
   length [0] INTEGER (2..255),
   spare1 [1] BOOLEAN DEFAULT FALSE,
   psi [2] SEQUENCE (SIZE (15)) OF BOOLEAN,
   --<noPresentBit/>
   spare2 [3] OCTET STRING OPTIONAL
}

-- 9.11.3.31 - MICO indication 
MICOIndication ::= SEQUENCE {
   spare [0] INTEGER (0..3) DEFAULT 0,
   sprti [1] BOOLEAN,
   raai [2] BOOLEAN
}

-- 9.11.3.13 - Allowed PDU session status 
AllowedPDUSessionStatus ::= SEQUENCE {
   --<is3GLength/>
   length [0] INTEGER (1..255),
   psi [1] SEQUENCE (SIZE (16)) OF BOOLEAN,
   --<noPresentBit/>
   spare [2] OCTET STRING OPTIONAL
}

-- 9.11.3.55 - UE usage setting 
UEUsageSetting ::= SEQUENCE {
   --<is3GLength/>
   length [0] INTEGER (0..255) DEFAULT 3,
   spare [1] INTEGER (0..127) DEFAULT 0,
   usage [2] BOOLEAN
}

-- 9.11.3.2A - DRX parameters 
DRXParams ::= SEQUENCE {
   --<is3GLength/>
   length [0] INTEGER (1),
   spare [1] INTEGER (0..15) DEFAULT 0,
   drxValue [2] INTEGER (0..15)
}

-- 9.11.3.24 - EPS NAS message container 
EPSMessageContainer ::= SEQUENCE {
   --<is3GLength bitFieldSize="16"/>
   length [0] INTEGER (1..65535),
   --<is3GVarLenList lengthElem="length"/>
   contents [1] SEQUENCE OF NASMessageContainer
}

-- 9.11.3.29 - LADN Indication 
LADNIndication ::= SEQUENCE {
   --<is3GLength bitFieldSize="16"/>
   length [0] INTEGER (1..65535),
   --<is3GVarLenList lengthElem="length"/>
   --<noPresentBit/>
   contents [1] SEQUENCE (SIZE (0..8)) OF DNNList OPTIONAL
}

-- -- TYPE DEFINITIONS --- 
/* OpaqueData can be used for any case where the specification has
   some number of octets preceded by a 2-octet length. */
OpaqueData ::= SEQUENCE {
   --<is3GLength bitFieldSize="16"/>
   length [0] INTEGER (1..65535),
   --<length fixed-size="0"/>
   contents [1] OCTET STRING
}

-- 9.11.3.36 - Network slicing indication 
NetSliceIndication ::= SEQUENCE {
   spare [0] INTEGER (0..3) DEFAULT 0,
   dcni [1] BOOLEAN,
   nssci [2] BOOLEAN
}

-- 9.11.3.9A - Update type 
UpdateType ::= SEQUENCE {
   --<is3GLength/>
   length [0] INTEGER (1..255),
   spare [1] INTEGER (0..3) DEFAULT 0,
   epsPnbCIoT [2] INTEGER (1..3),
   pnbCIoT [3] INTEGER (1..3),
   ngranUpd [4] BOOLEAN,
   smsReq [5] BOOLEAN
}

-- 9.11.3.33 - NAS message container 
-- Different from NASMessageContainer defined in 24.301... 
NASMessageContainer2 ::= SEQUENCE {
   --<is3GLength bitFieldSize="16"/>
   length [0] INTEGER (1..65535),
   --<length fixed-size="0"/>
   contents [1] OCTET STRING (SIZE (1..65535))
}

MappedSNSSAIContent ::= SEQUENCE {
   length [0] INTEGER (1..255),
   mappedSST [1] OCTET STRING (SIZE (1)),
   mappedSD [2] OCTET STRING (SIZE (3))
}

-- 9.11.3.31B - Mapped NSSAI 
MappedNSSAI ::= SEQUENCE {
   --<is3GLength/>
   length [0] INTEGER (1..255),
   --<is3GVarLenList lengthElem="length"/>
   contents [1] SEQUENCE (SIZE (1..8)) OF MappedSNSSAIContent
}

-- 9.11.3.12A - Additional information requested 
AdditionalInfoRequested ::= SEQUENCE {
   spare [0] INTEGER (0..127) DEFAULT 0,
   cipherKey [1] BOOLEAN
}

--<is3GMessage/>
RegRequest ::= SEQUENCE {
   nasKeySetIdent [0] NASKeySetIdentifier,
   registrationType [1] RegistrationType,
   mobileId [2] EXPLICIT MobileIdentity,
   --<iei format="tv" length="1">0C</iei>
   nativeNasKeySetIdent [3] NASKeySetIdentifier OPTIONAL,
   --<iei format="tlv">10</iei>
   capability [4] MMCapability OPTIONAL,
   --<iei format="tlv">2E</iei>
   securityCapability [5] UESecurityCapability OPTIONAL,
   --<iei format="tlv">2F</iei>
   requestedNSSAI [6] NSSAI OPTIONAL,
   --<iei format="tv" length="7">52</iei>
   lastVisitedTAI [7] TrackingAreaIdent OPTIONAL,
   --<iei format="tlv">17</iei>
   s1NetworkCapability [8] UENetworkCapability OPTIONAL,
   --<iei format="tlv">40</iei>
   uplinkStat [9] UplinkDataStatus OPTIONAL,
   --<iei format="tlv">50</iei>
   sessionStat [10] PDUSessionStatus OPTIONAL,
   --<iei format="tv" length="1">0B</iei>
   micoInd [11] MICOIndication OPTIONAL,
   --<iei format="tlv">2B</iei>
   ueStat [12] UEStatus OPTIONAL,
   --<iei format="tlv-e">77</iei>
   addlGUTI [13] EXPLICIT MobileIdentity OPTIONAL,
   --<iei format="tlv">25</iei>
   allowedSessionStat [14] AllowedPDUSessionStatus OPTIONAL,
   --<iei format="tlv">18</iei>
   ueUsage [15] UEUsageSetting OPTIONAL,
   --<iei format="tlv">51</iei>
   reqDrxParams [16] DRXParams OPTIONAL, -- added in v15.2.0
   --<iei format="tlv-e">70</iei>
   epsContainer [17] EPSMessageContainer OPTIONAL,
   --<iei format="tlv-e">74</iei>
   ladnInd [18] LADNIndication OPTIONAL, -- added in v15.1.0
   --<iei format="tv" length="1">8</iei>
   containerType [19] PayloadContainerType OPTIONAL, -- added in v15.3.0
   --<iei format="tlv-e">7B</iei>
   --<inline/>
   container [20] EXPLICIT CHOICE {
      -- The only option currently allowed is UE Policy.  See 8.2.6.17A. 
      --<selector element="containerType" value="5"/>
      uePolicy [0] OpaqueData
   } OPTIONAL,
   --<iei format="tv" length="1">9</iei>
   netSliceInd [21] NetSliceIndication OPTIONAL, -- added in v15.2.0
   --<iei format="tlv">53</iei>
   updateType [22] UpdateType OPTIONAL, -- added in v15.2.0
   --<iei format="tlv-e">71</iei>
   nasContainer [23] NASMessageContainer2 OPTIONAL, -- added in v15.2.0
   --<iei format="tlv">60</iei>
   epsBearerStat [24] EPSBearerContextStatus OPTIONAL,
   ...,
   [[ 16:
      mobileStationClassmark2 [25] MobileStationClassmark2 OPTIONAL,
      supportedCodecs [26] SupportedCodecList OPTIONAL,
      reqDRXParams [27] ExtDRXParams OPTIONAL,
      t3324 [28] GPRSTimer3 OPTIONAL,
      ueRadioCapabilityId [29] UERadioCapId OPTIONAL,
      reqMappedNSSAI [30] MappedNSSAI OPTIONAL,
      addlInfoRequested [31] AdditionalInfoRequested OPTIONAL
   ]]
}

-- 9.11.3.6 - Registration result 
RegistrationResult ::= SEQUENCE {
   --<is3GLength/>
   length [0] INTEGER (1..255),
   spare [1] INTEGER (0..3) DEFAULT 0,
   emergencyRegistered [2] BOOLEAN,
   nssaa [3] BOOLEAN,
   smsAllowed [4] BOOLEAN,
   regResult [5] RegistrationResultValue
}

TrackingAreaIdentListItem ::= SEQUENCE {
   spare [0] BOOLEAN DEFAULT FALSE,
   typeOfList [1] INTEGER (0..3),
   numElements [2] INTEGER (0..31),
   --<inline/>
   elements [3] EXPLICIT CHOICE {
      --<selector element="typeOfList" value="0"/>
      --<asn1typename>PartialTrkAreaIdent0</asn1typename>
      partTrkIdentList0 [0] SEQUENCE {
         mcc-mnc [0] MCCMNCPair,
         --<inline/>
         --<length expr="@...numElements"/>
         tacs [1] SEQUENCE (SIZE (1..32)) OF TrackingAreaCode
      },
      --<selector element="typeOfList" value="1"/>
      --<asn1typename>PartialTrkAreaIdent1</asn1typename>
      partTrkIdentList1 [1] SEQUENCE {
         mcc-mnc [0] MCCMNCPair,
         tac [1] TrackingAreaCode
      },
      --<selector element="typeOfList" value="2"/>
      --<length expr="@.numElements"/>
      --<asn1typename>PartialTrkAreaIdent2</asn1typename>
      partTrkIdentList2 [2] SEQUENCE (SIZE (1..32)) OF TrackingAreaIdent,
      --<selector element="typeOfList" value="3"/>
      partTrkIdentList3 [3] MCCMNCPair
   }
}

-- 9.11.3.9 - Tracking area identity list 
-- Mostly the same as 24.301 except the TAC is 3 octets instead of 2... 
-- Also used for Service Area List type (9.11.3.49)... 
TrackingAreaIdentList ::= SEQUENCE {
   --<is3GLength/>
   length [0] INTEGER (1..255),
   --<is3GVarLenList lengthElem="length"/>
   idents [1] SEQUENCE (SIZE (1..16)) OF TrackingAreaIdentListItem
}

RejectedNSSAI ::= SEQUENCE {
   length [0] INTEGER (1..15),
   cause [1] ENUMERATED { unavailInCurrPlmn(0), unavailInCurrRegisArea(1), 
      authPending(2), causeMAX(15) },
   sst [2] SST,
   --<noPresentBit/>
   sd [3] SD OPTIONAL
}

-- 9.11.3.46 - Rejected NSSAI 
RejectedNSSAIList ::= SEQUENCE {
   --<is3GLength/>
   length [0] INTEGER (1..255),
   --<is3GVarLenList lengthElem="length"/>
   rejectedNSSAI [1] SEQUENCE (SIZE (1..8)) OF RejectedNSSAI
}

-- 9.11.3.5 - 5GS network feature support 
NetworkFeatureSupport ::= SEQUENCE {
   --<is3GLength/>
   length [0] INTEGER (1..255),
   -- octet 3 
   mpsInd [1] BOOLEAN,
   withoutN26Ind [2] BOOLEAN,
   emfInd [3] INTEGER (0..3),
   emcInd [4] INTEGER (0..3),
   imsVoPSInd [5] BOOLEAN,
   imsVoPS3GInd [6] BOOLEAN,
   --<noPresentBit/>
   -- octet 4 
   octet4 [7] SEQUENCE {
      lcs [0] BOOLEAN,
      upCIoT [1] BOOLEAN,
      hcCpCIoT [2] BOOLEAN,
      n3Data [3] BOOLEAN,
      cpCIoT [4] BOOLEAN,
      restrictedEC [5] BOOLEAN,
      mcsi [6] BOOLEAN,
      emcn3 [7] BOOLEAN
   } OPTIONAL,
   --<noPresentBit/>
   spare [8] OCTET STRING OPTIONAL
}

ReactivateCause ::= SEQUENCE {
   sessionId [0] INTEGER (0..255),
   cause [1] MMCause
}

-- 9.11.3.43 - PDU session reactivation result error cause 
SessionReactivateCause ::= SEQUENCE {
   --<is3GLength bitFieldSize="16"/>
   length [0] INTEGER (1..512),
   --<is3GVarLenList lengthElem="length"/>
   reactivateCause [1] SEQUENCE (SIZE (1..255)) OF ReactivateCause
}

LADN ::= SEQUENCE {
   dnn [0] DNNList,
   tai [1] TrackingAreaIdent
}

-- 9.11.3.30 - LADN 
LADNList ::= SEQUENCE {
   --<is3GLength bitFieldSize="16"/>
   length [0] INTEGER (1..1715),
   --<is3GVarLenList lengthElem="length"/>
   contents [1] SEQUENCE (SIZE (0..8)) OF LADN
}

PLMNTechList ::= SEQUENCE {
   id [0] OCTET STRING (SIZE (3)),
   techId [1] OCTET STRING (SIZE (2))
}

-- SOR for data type = 0 (steering of roaming information) 
SORSteering ::= SEQUENCE {
   spare [0] INTEGER (0..15) DEFAULT 0,
   ack [1] BOOLEAN,
   listType [2] INTEGER (0..1),
   listInd [3] BOOLEAN,
   dataType [4] INTEGER (0..1) DEFAULT 0, -- always 0 
   sorMAC [5] OCTET STRING (SIZE (16)),
   counter [6] OCTET STRING (SIZE (2)),
   --<inline/>
   --<noPresentBit/>
   content [7] EXPLICIT CHOICE {
      --<selector element="listType" value="0"/>      
      --<length fixed-size="0"/>
      securedPacket [0] OCTET STRING,
      --<selector element="listType" value="1"/>    
      --<length fixed-size="0"/>
      plmnAccess [1] SEQUENCE OF PLMNTechList
   } OPTIONAL
}

-- SOR for data type = 1 (ack of steering of roaming information) 
SORAck ::= SEQUENCE {
   spare [0] INTEGER (0..127) DEFAULT 0,
   dataType [1] INTEGER (0..1) DEFAULT 1, -- always 1 
   sorMAC [2] OCTET STRING (SIZE (16))
}

-- 9.11.3.51 - SOR transparent container 
/* This IE requires custom decoding due to the lowest bit in the header octet
   determining whether the IE contains steering or ack of steering information.*/
SORTransparentContainer ::= SEQUENCE {
   --<is3GLength bitFieldSize="16"/>
   length [0] INTEGER (0..65535),
   steeringOrAck [1] EXPLICIT CHOICE {
      steering [0] SORSteering,
      ack [1] SORAck
   }
}

-- 9.11.3.37A - NSSAI inclusion mode 
NSSAIInclusionMode ::= SEQUENCE {
   spare [0] INTEGER (0..3) DEFAULT 0,
   inclusionMode [1] ENUMERATED { modeA(0), modeB(1), modeC(2), modeD(3) }
}

AccessCategoryDefinition ::= SEQUENCE {
   precedence [0] INTEGER (1..255),
   psac [1] BOOLEAN,
   spare [2] INTEGER (0..3) DEFAULT 0,
   categoryNum [3] INTEGER (0..31),
   --<is3GLength/>
   length [4] INTEGER (1..255),
   --<is3GVarLenList lengthElem="length"/>
   criteria [5] SEQUENCE OF OCTET STRING,
   spare2 [6] INTEGER (0..7) DEFAULT 0,
   accessCategory [7] INTEGER (0..31)
}

-- 9.11.3.38 - Operator defined access category definitions 
AccessCategoryDefinitions ::= SEQUENCE {
   --<is3GLength bitFieldSize="16"/>
   length [0] INTEGER (1..65535),
   --<is3GVarLenList lengthElem="length"/>
   --<noPresentBit/>
   contents [1] SEQUENCE OF AccessCategoryDefinition OPTIONAL
}

CipherDataSet ::= SEQUENCE {
   cipherKey [0] OCTET STRING (SIZE (16)),
   spare1 [1] INTEGER (0..7) DEFAULT 0,
   c0Len [2] INTEGER (0..31),
   --<length expr="@c0Len"/>
   c0 [3] OCTET STRING,
   spare2 [4] INTEGER (0..15) DEFAULT 0,
   eutraPosSIBLen [5] INTEGER (0..15),
   eutraPosSIBType [6] SEQUENCE (SIZE (32)) OF BOOLEAN,
   spare3 [7] INTEGER (0..15) DEFAULT 0,
   nrPosSIBLen [8] INTEGER (0..15),
   nrPosSIBType [9] SEQUENCE (SIZE (34)) OF BOOLEAN,
   spare4 [10] INTEGER (0..63) DEFAULT 0,
   validityStartTime [11] TimeZoneAndTime,
   validityDuration [12] INTEGER (0..65535),
   taiList [13] TrackingAreaIdentList
}

-- 9.11.3.18C - Ciphering key data 
CipheringKeyData ::= SEQUENCE {
   --<is3GLength bitFieldSize="16"/>
   length [0] INTEGER (1..65535),
   --<is3GVarLenList lengthElem="length"/>
   --<storage>array</storage>
   dataSet [1] SEQUENCE (SIZE (1..16)) OF CipherDataSet
}

--<is3GMessage/>
RegAccept ::= SEQUENCE {
   regResult [0] RegistrationResult,
   --<iei format="tlv-e">77</iei>
   guti [1] EXPLICIT MobileIdentity OPTIONAL,
   --<iei format="tlv">4A</iei>
   plmnList [2] PLMNList OPTIONAL,
   --<iei format="tlv">54</iei>
   taiList [3] TrackingAreaIdentList OPTIONAL,
   --<iei format="tlv">15</iei>
   allowedNSSAI [4] NSSAI OPTIONAL,
   --<iei format="tlv">11</iei>
   rejectedNSSAI [5] RejectedNSSAIList OPTIONAL,
   --<iei format="tlv">31</iei>
   configuredNSSAI [6] NSSAI OPTIONAL,
   --<iei format="tlv">21</iei>
   netSupport [7] NetworkFeatureSupport OPTIONAL,
   --<iei format="tlv">50</iei>
   sessionStat [8] PDUSessionStatus OPTIONAL,
   --<iei format="tlv">26</iei>
   reactivateRslt [9] SessionReactivateRslt OPTIONAL,
   --<iei format="tlv-e">72</iei>
   reactivateRsltCause [10] SessionReactivateCause OPTIONAL,
   --<iei format="tlv-e">79</iei>
   ladn [11] LADNList OPTIONAL,
   --<iei format="tv" length="1">B</iei>
   micoInd [12] MICOIndication OPTIONAL,
   --<iei format="tv" length="1">9</iei>
   netSliceInd [13] NetSliceIndication OPTIONAL, -- added in v15.1.0
   --<iei format="tlv">27</iei>
   svcAreaList [14] TrackingAreaIdentList OPTIONAL,
   --<iei format="tlv">5E</iei>
   t3512 [15] GPRSTimer3 OPTIONAL,
   --<iei format="tlv">5D</iei>
   non3GPPDeregTimer [16] GPRSTimer2 OPTIONAL,
   --<iei format="tlv">16</iei>
   t3502 [17] GPRSTimer2 OPTIONAL,
   --<iei format="tlv">34</iei>
   emergencyNumList [18] EmergencyNumberList OPTIONAL,
   --<iei format="tlv-e">7A</iei>
   extEmergencyNumList [19] ExtEmergencyNumberList OPTIONAL, -- added in v15.1.0
   --<iei format="tlv-e">73</iei>
   transparentContainer [20] SORTransparentContainer OPTIONAL, -- added in v15.1.0
   --<iei format="tlv-e">78</iei>
   eapMessage [21] EAPMessage OPTIONAL,
   --<iei format="tv" length="1">A</iei>
   inclusionMode [22] NSSAIInclusionMode OPTIONAL, -- added in v15.2.0
   --<iei format="tlv-e">76</iei>
   accessDefs [23] AccessCategoryDefinitions OPTIONAL, -- added in v15.2.0
   --<iei format="tlv">51</iei>
   negotiatedDrxParams [24] DRXParams OPTIONAL, -- added in v15.2.0
   --<iei format="tv" length="1">D</iei>
   non3GPPNWPolicies [25] Non3GPPNetPolicies OPTIONAL, -- added in v15.4.0
   --<iei format="tlv">60</iei>
   epsBearerStat [26] EPSBearerContextStatus OPTIONAL,
   ...,
   [[ 16:
      negotiatedExtDrxParams [27] ExtDRXParams OPTIONAL,
      t3447 [28] GPRSTimer3 OPTIONAL,
      t3448 [29] GPRSTimer3 OPTIONAL,
      t3324 [30] GPRSTimer3 OPTIONAL,
      ueRadioCapabilityId [31] UERadioCapId OPTIONAL,
      ueRadioCapIdDeletionIndication [32] UERadioCapIdDeletionInd OPTIONAL,
      pendingNSSAI [33] NSSAI OPTIONAL,
      cipherKeyData [34] CipheringKeyData OPTIONAL
   ]]
}

--<is3GMessage/>
RegComplete ::= SEQUENCE {
   --<iei format="tlv-e">73</iei>
   transparentContainer [0] SORTransparentContainer OPTIONAL -- added in v15.1.0
}

--<is3GMessage/>
RegReject ::= SEQUENCE {
   cause [0] MMCause,
   --<iei format="tlv">5F</iei>
   t3346 [1] GPRSTimer2 OPTIONAL,
   --<iei format="tlv">16</iei>
   t3502 [2] GPRSTimer2 OPTIONAL,
   --<iei format="tlv-e">78</iei>
   eapMessage [3] EAPMessage OPTIONAL,
   ...,
   [[ 16:
      rejectedNSSAI [4] RejectedNSSAIList OPTIONAL
   ]]
}

OptionalIE ::= SEQUENCE {
   type [0] INTEGER (0..255),
   value [1] OCTET STRING -- (preceeded by 1 octet length)
}

PayloadContainerEntry ::= SEQUENCE {
   entryLength [0] INTEGER (1..255),
   numOptIEs [1] INTEGER (1..15),
   type [2] PayloadContainerType,
   --<inline/>
   --<length expr="@numOptIEs"/>
   optionalIEs [3] SEQUENCE (SIZE (1..15)) OF OptionalIE,
   contents [4] OCTET STRING (SIZE (0..65535))
}

PayloadContainerContents ::= SEQUENCE {
   numEntries [0] INTEGER (0..255),
   --<inline/>
   --<length expr="@numEntries"/>
   entries [1] SEQUENCE (SIZE (0..255)) OF PayloadContainerEntry
}

/* 9.11.3.39 - Payload container
   Warning: this type covers the specific case where the payload container
   type is 15 (Multiple payloads).*/
MultiPayloadContainer ::= SEQUENCE {
   --<is3GLength bitFieldSize="16"/>
   length [0] INTEGER (1..65535),
   contents [1] PayloadContainerContents
}

-- 9.11.3.47 - Request type 
RequestType ::= SEQUENCE {
   spare [0] BOOLEAN DEFAULT FALSE,
   reqType [1] RequestTypes
}

--<is3GMessage/>
ULNASTrans ::= SEQUENCE {
   spare [0] INTEGER (0..15) DEFAULT 0,
   containerType [1] PayloadContainerType,
   --<inline/>
   container [2] EXPLICIT CHOICE {
      --<selector element="containerType" value="1"/>      
      n1sm [0] OpaqueData,
      --<selector element="containerType" value="2"/>
      sms [1] OpaqueData,
      --<selector element="containerType" value="3"/>
      lpp [2] OpaqueData,
      --<selector element="containerType" value="4"/>
      sor [3] SORAck,
      --<selector element="containerType" value="5"/>
      uePolicy [4] OpaqueData,
      --<selector element="containerType" value="6"/>
      ueParamUpdate [5] OpaqueData,
      --<selector element="containerType" value="7"/>
      locSvcs [6] OpaqueData,
      --<selector element="containerType" value="8"/>
      cIOTUserData [7] OpaqueData,
      --<selector element="containerType" value="15"/>
      multiple [8] MultiPayloadContainer
   },
   --<iei format="tv" length="2">12</iei>
   pduSessionId [3] PDUSessionId2 OPTIONAL,
   --<iei format="tv" length="2">59</iei>
   oldPduSessionId [4] PDUSessionId2 OPTIONAL,
   --<iei format="tv" length="1">8</iei>
   requestType [5] RequestType OPTIONAL,
   --<iei format="tlv">22</iei>
   snssai [6] SNSSAI OPTIONAL,
   --<iei format="tlv">25</iei>
   dnn [7] DNNList OPTIONAL,
   --<iei format="tlv">24</iei>
   addlInfo [8] AdditionalInfo OPTIONAL,
   ...,
   [[ 16:
      maPduSessionInfo [9] INTEGER (0..15) OPTIONAL,
      relAssistInd [10] ReleaseAssistInd OPTIONAL
   ]]
}

UEParamUpdateDataSet ::= SEQUENCE {
   spare [0] INTEGER (0..15),
   dataSetType [1] INTEGER (0..15),
   dataSetLen [2] INTEGER (0..65535),
   --<inline/>
   dataSet [3] EXPLICIT CHOICE {
      --<selector element="dataSetType" value="1"/>      
      --<length expr="@dataSetLen"/>
      securedPacket [0] OCTET STRING,
      --<selector element="dataSetType" value="2"/>      
      --<length expr="@dataSetLen"/>
      defCfgNSSAI [1] OCTET STRING
   }
}

-- UE Param Update for data type = 0 (UE parameters update list) 
UEParamUpdate ::= SEQUENCE {
   spare [0] INTEGER (0..31) DEFAULT 0,
   reg [1] BOOLEAN,
   ack [2] BOOLEAN,
   dataType [3] INTEGER (0..1) DEFAULT 0, -- always 0 
   mac [4] OCTET STRING (SIZE (16)),
   counter [5] OCTET STRING (SIZE (2)),
   --<length fixed-size="0"/>
   updateList [6] SEQUENCE OF UEParamUpdateDataSet
}

--<is3GMessage/>
DLNASTrans ::= SEQUENCE {
   spare [0] INTEGER (0..15) DEFAULT 0,
   containerType [1] PayloadContainerType,
   --<inline/>
   container [2] EXPLICIT CHOICE {
      --<selector element="containerType" value="1"/>      
      n1sm [0] OpaqueData,
      --<selector element="containerType" value="2"/>
      sms [1] OpaqueData,
      --<selector element="containerType" value="3"/>
      lpp [2] OpaqueData,
      --<selector element="containerType" value="4"/>
      sor [3] SORSteering,
      --<selector element="containerType" value="5"/>
      uePolicy [4] OpaqueData,
      --<selector element="containerType" value="6"/>
      ueParamUpdate [5] UEParamUpdate,
      --<selector element="containerType" value="7"/>
      locSvcs [6] OpaqueData,
      --<selector element="containerType" value="8"/>
      cIOTUserData [7] OpaqueData,
      --<selector element="containerType" value="15"/>
      multiple [8] MultiPayloadContainer
   },
   --<iei format="tv" length="2">12</iei>
   pduSessionId [3] PDUSessionId2 OPTIONAL,
   --<iei format="tlv">24</iei>
   addlInfo [4] AdditionalInfo OPTIONAL,
   --<iei format="tv" length="2">58</iei>
   cause [5] MMCause OPTIONAL,
   --<iei format="tlv">37</iei>
   backoffTimer [6] GPRSTimer3 OPTIONAL
}

-- 9.11.3.20 - Deregistration type 
DeregistrationType ::= SEQUENCE {
   switchOff [0] BOOLEAN,
   reregReqd [1] BOOLEAN,
   accessType [2] INTEGER (0..3)
}

--<is3GMessage/>
DeregReqUEOrig ::= SEQUENCE {
   nasKeySetIdent [0] NASKeySetIdentifier, -- added in v15.1.0
   deregType [1] DeregistrationType,
   mobileId [2] EXPLICIT MobileIdentity
}

--<is3GMessage/>
DeregReqUETerm ::= SEQUENCE {
   spare [0] INTEGER (0..15) DEFAULT 0,
   deregType [1] DeregistrationType,
   --<iei format="tv" length="2">58</iei>
   cause [2] MMCause OPTIONAL,
   --<iei format="tlv">5F</iei>
   t3346 [3] GPRSTimer2 OPTIONAL,
   ...,
   [[ 16:
      rejectedNSSAI [4] RejectedNSSAIList OPTIONAL
   ]]
}

--<is3GMessage/>
ServRequest ::= SEQUENCE {
   serviceType [0] ServiceType,
   nasKeySetIdent [1] NASKeySetIdentifier,
   stmsi [2] EXPLICIT MobileIdentity,
   --<iei format="tlv">40</iei>
   uplinkStat [3] UplinkDataStatus OPTIONAL,
   --<iei format="tlv">50</iei>
   sessionStat [4] PDUSessionStatus OPTIONAL,
   --<iei format="tlv">25</iei>
   allowedSessionStat [5] AllowedPDUSessionStatus OPTIONAL,
   --<iei format="tlv-e">71</iei>
   nasContainer [6] NASMessageContainer2 OPTIONAL -- added in v15.2.0
}

--<is3GMessage/>
ServAccept ::= SEQUENCE {
   --<iei format="tlv">50</iei>
   sessionStat [0] PDUSessionStatus OPTIONAL,
   --<iei format="tlv">26</iei>
   reactivateRslt [1] SessionReactivateRslt OPTIONAL,
   --<iei format="tlv-e">72</iei>
   reactivateRsltCause [2] SessionReactivateCause OPTIONAL,
   --<iei format="tlv-e">78</iei>
   eapMessage [3] EAPMessage OPTIONAL,
   ...,
   [[ 16:
      t3448 [4] GPRSTimer3 OPTIONAL
   ]]
}

--<is3GMessage/>
ServReject ::= SEQUENCE {
   cause [0] MMCause,
   --<iei format="tlv">50</iei>
   sessionStat [1] PDUSessionStatus OPTIONAL,
   --<iei format="tlv">5F</iei>
   t3346 [2] GPRSTimer2 OPTIONAL,
   --<iei format="tlv-e">78</iei>
   eapMessage [3] EAPMessage OPTIONAL,
   ...,
   [[ 16:
      t3448 [4] GPRSTimer3 OPTIONAL
   ]]
}

-- 9.11.3.18 - Configuration update indication 
ConfigUpdateIndication ::= SEQUENCE {
   spare [0] INTEGER (0..3) DEFAULT 0,
   regRequested [1] BOOLEAN,
   ack [2] BOOLEAN
}

-- 9.11.3.50A - SMS indication 
SMSIndication ::= SEQUENCE {
   spare [0] INTEGER (0..7) DEFAULT 0,
   sai [1] BOOLEAN
}

CAGEntry ::= SEQUENCE {
   length [0] INTEGER (1..255),
   mcc-mnc [1] MCCMNCPair,
   spare [2] INTEGER (0..127) DEFAULT 0,
   cagOnly [3] BOOLEAN,
   cagID [4] SEQUENCE OF OCTET STRING
}

-- 9.11.3.18A - CAG information list 
CAGInfoList ::= SEQUENCE {
   --<is3GLength bitFieldSize="16"/>
   length [0] INTEGER (0..65535),
   --<is3GVarLenList lengthElem="length"/>
   --<noPresentBit/>
   entries [1] SEQUENCE OF CAGEntry OPTIONAL
}

--<is3GMessage/>
CfgUpdateCmd ::= SEQUENCE {
   --<iei format="tv" length="1">0D</iei>
   cfgUpdIndication [0] ConfigUpdateIndication OPTIONAL,
   --<iei format="tlv-e">77</iei>
   guti [1] EXPLICIT MobileIdentity OPTIONAL,
   --<iei format="tlv">54</iei>
   taiList [2] TrackingAreaIdentList OPTIONAL,
   --<iei format="tlv">15</iei>
   allowedNSSAI [3] NSSAI OPTIONAL,
   --<iei format="tlv">27</iei>
   svcAreaList [4] TrackingAreaIdentList OPTIONAL,
   --<iei format="tlv">43</iei>
   fullNetworkName [5] NetworkName OPTIONAL,
   --<iei format="tlv">45</iei>
   shortNetworkName [6] NetworkName OPTIONAL,
   --<iei format="tv" length="2">46</iei>
   localTZ [7] TimeZone OPTIONAL,
   --<iei format="tv" length="8">47</iei>
   univAndLocalTZ [8] TimeZoneAndTime OPTIONAL,
   --<iei format="tlv">49</iei>
   dst [9] DaylightSavingTime OPTIONAL,
   --<iei format="tlv-e">79</iei>
   ladn [10] LADNList OPTIONAL,
   --<iei format="tv" length="1">0B</iei>
   micoInd [11] MICOIndication OPTIONAL,
   --<iei format="tv" length="1">9</iei>
   netSliceInd [12] NetSliceIndication OPTIONAL, -- added in v15.1.0
   --<iei format="tlv">31</iei>
   configuredNSSAI [13] NSSAI OPTIONAL,
   --<iei format="tlv">11</iei>
   rejectedNSSAI [14] RejectedNSSAIList OPTIONAL,
   --<iei format="tlv-e">76</iei>
   accessDefs [15] AccessCategoryDefinitions OPTIONAL, -- added in v15.2.0
   --<iei format="tv" length="1">F</iei>
   smsInd [16] SMSIndication OPTIONAL,
   ...,
   [[ 16:
      t3447 [17] GPRSTimer3 OPTIONAL,
      cagInfoList [18] CAGInfoList OPTIONAL,
      ueRadioCapabilityId [19] UERadioCapId OPTIONAL,
      ueRadioCapIdDeletionIndication [20] UERadioCapIdDeletionInd OPTIONAL,
      regResult [21] RegistrationResult OPTIONAL
   ]]
}

-- 9.11.3.3 - Identity type 
IdentityType ::= SEQUENCE {
   spare [0] BOOLEAN DEFAULT FALSE,
   typeOfIdent [1] TypeOfIdentity
}

--<is3GMessage/>
IdentityRequest ::= SEQUENCE {
   spare [0] INTEGER (0..15) DEFAULT 0,
   identity [1] IdentityType
}

--<is3GMessage/>
IdentityResponse ::= SEQUENCE {
   mobileId [0] EXPLICIT MobileIdentity
}

-- 9.11.2.1A - Access type 
AccessType ::= SEQUENCE {
   spare [0] INTEGER (0..3) DEFAULT 0,
   typeOfAccess [1] ENUMERATED { access3gpp(1), accessNon3gpp(2) }
}

--<is3GMessage/>
Notify ::= SEQUENCE {
   spare [0] INTEGER (0..15) DEFAULT 0,
   access [1] AccessType
}

--<is3GMessage/>
NotifyResponse ::= SEQUENCE {
   --<iei format="tlv">50</iei>
   sessionStat [0] PDUSessionStatus OPTIONAL
}

-- 9.11.3.34 - NAS security algorithms 
NASSecurityAlgorithm ::= SEQUENCE {
   cipherType [0] INTEGER (0..15),
   protectionType [1] INTEGER (0..15)
}

-- 9.11.3.12 - Additional security information 
AddlSecurityInfo ::= SEQUENCE {
   --<is3GLength/>
   length [0] INTEGER (1..255),
   spare [1] INTEGER (0..63) DEFAULT 0,
   rinmr [2] BOOLEAN,
   hdp [3] BOOLEAN
}

--<is3GMessage/>
SecModeCmd ::= SEQUENCE {
   nasSecAlgorithm [0] NASSecurityAlgorithm,
   spare [1] INTEGER (0..15) DEFAULT 0,
   nasKeySetIdent [2] NASKeySetIdentifier,
   replayedUECapabilities [3] UESecurityCapability,
   --<iei format="tv" length="1">0E</iei>
   imeisvReq [4] IMEISVRequest OPTIONAL,
   --<iei format="tv" length="2">57</iei>
   epsSecAlgorithm [5] NASSecurityAlgorithms OPTIONAL,
   --<iei format="tlv">36</iei>
   addlSecInfo [6] AddlSecurityInfo OPTIONAL, -- added in v15.1.0
   --<iei format="tlv-e">78</iei>
   eapMessage [7] EAPMessage OPTIONAL,
   --<iei format="tlv">38</iei>
   abba [8] ABBA OPTIONAL, -- added in v15.2.0
   --<iei format="tlv">19</iei>
   replayedS1UECapabilities [9] UESecurityCapability OPTIONAL -- added in v15.2.0
}

--<is3GMessage/>
SecModeDone ::= SEQUENCE {
   --<iei format="tlv-e">77</iei>
   imeisv [0] EXPLICIT MobileIdentity OPTIONAL,
   --<iei format="tlv-e">71</iei>
   nasMsgContainer [1] NASMessageContainer2 OPTIONAL,
   ...,
   [[ 16:
      nonImeisvPei [2] EXPLICIT MobileIdentity OPTIONAL
   ]]
}

--<is3GMessage/>
SecModeReject ::= SEQUENCE {
   cause [0] MMCause
}

--<is3GMessage/>
MMStatus ::= SEQUENCE {
   cause [0] MMCause
}

-- 9.11.4.7 - Integrity protection maximum data rate 
IntegrityProtMaxDataRate ::= SEQUENCE {
   maxUEDataRateUplink [0] MaxDataRates,
   maxUEDataRateDownlink [1] MaxDataRates
}

-- 9.11.4.11 - PDU session type 
PDUSessionType ::= SEQUENCE {
   spare [0] BOOLEAN DEFAULT FALSE,
   sessionType [1] INTEGER (0..7)
}

-- 9.11.4.16 - SSC mode 
SSCMode ::= SEQUENCE {
   spare [0] BOOLEAN DEFAULT FALSE,
   sscMode [1] INTEGER (0..7)
}

-- 9.11.4.1 - SM capability 
SMCapability ::= SEQUENCE {
   --<is3GLength/>
   length [0] INTEGER (0..255),
   -- octet 3 
   spare [1] INTEGER (0..3) DEFAULT 0,
   tpmic [2] BOOLEAN,
   mptc [3] BOOLEAN,
   atsll [4] BOOLEAN,
   epts1 [5] BOOLEAN,
   mh6Pdu [6] BOOLEAN,
   rqos [7] BOOLEAN,
   --<noPresentBit/>
   spare2 [8] OCTET STRING OPTIONAL
}

-- 9.11.4.9 - Maximum number of supported packet filters 
MaxSupportedPacketFilters ::= SEQUENCE {
   maxFilters [0] INTEGER (1..2047),
   spare [1] INTEGER (0..31) DEFAULT 0
}

-- 9.11.4.4 - Always-on PDU session requested 
AlwaysOnPDUSessionReq ::= SEQUENCE {
   spare [0] INTEGER (0..7) DEFAULT 0,
   apsr [1] BOOLEAN
}

-- 9.11.4.15 - SM PDU DN request container 
SmPduDnReqContainer ::= SEQUENCE {
   --<is3GLength/>
   length [0] INTEGER (3..255),
   --<is3GVarLenList lengthElem="length"/>
   --<noPresentBit/>
   dnSpecificId [1] OCTET STRING OPTIONAL
}

-- 9.11.4.24 - Header compression configuration 
HeaderCompressionConfig ::= SEQUENCE {
   --<is3GLength/>
   length [0] INTEGER (3..255),
   spare [1] BOOLEAN DEFAULT FALSE,
   p0x0104 [2] BOOLEAN,
   p0x0103 [3] BOOLEAN,
   p0x0102 [4] BOOLEAN,
   p0x0006 [5] BOOLEAN,
   p0x0004 [6] BOOLEAN,
   p0x0003 [7] BOOLEAN,
   p0x0002 [8] BOOLEAN,
   maxCID [9] OCTET STRING (SIZE (2)),
   --<noPresentBit/>
   addlCompressParamsType [10] INTEGER (0..255) OPTIONAL,
   --<noPresentBit/>
   addlCompressParamsContainer [11] OCTET STRING OPTIONAL
}

-- 9.11.4.25 - DS-TT Ethernet port MAC address 
DSTTEthMACAddr ::= SEQUENCE {
   --<is3GLength/>
   length [0] INTEGER (1..255),
   contents [1] OCTET STRING (SIZE (6))
}

-- 9.11.4.26 - DS-TT residence time 
DSTTResidenceTime ::= SEQUENCE {
   length [0] INTEGER (1..255),
   contents [1] OCTET STRING (SIZE (8))
}

-- 9.11.4.27 - Port management information container 
PortMgmtInfoContainer ::= SEQUENCE {
   --<is3GLength bitFieldSize="16"/>
   length [0] INTEGER (0..65535),
   --<noPresentBit/>
   container [1] OCTET STRING OPTIONAL
}

--<is3GMessage/>
EstablishRequest ::= SEQUENCE {
   integProtMaxRate [0] IntegrityProtMaxDataRate, -- added in v15.1.0
   --<iei format="tv" length="1">9</iei>
   pduSessionType [1] PDUSessionType OPTIONAL,
   --<iei format="tv" length="1">0A</iei>
   sscMode [2] SSCMode OPTIONAL,
   --<iei format="tlv">28</iei>
   capability [3] SMCapability OPTIONAL,
   --<iei format="tv" length="3">55</iei>
   maxPktFilters [4] MaxSupportedPacketFilters OPTIONAL,
   --<iei format="tv" length="1">B</iei>
   alwaysOnPDUSession [5] AlwaysOnPDUSessionReq OPTIONAL, -- added in v15.1.0
   --<iei format="tlv">39</iei>
   reqContainer [6] SmPduDnReqContainer OPTIONAL, -- added in v15.2.0
   --<iei format="tlv-e">7B</iei>
   extProtoCfgOpts [7] ExtProtoConfigOptions OPTIONAL,
   ...,
   [[ 16:
      headerCompressionCfg [8] HeaderCompressionConfig OPTIONAL,
      dsttPortMacAddr [9] DSTTEthMACAddr OPTIONAL,
      dsttResidenceTime [10] DSTTResidenceTime OPTIONAL,
      portMgmtInfoContainer [11] PortMgmtInfoContainer OPTIONAL
   ]]
}

PFComponent ::= SEQUENCE {
   typeId [0] PacketFilterTypeId,
   --<inline/>
   value [1] EXPLICIT CHOICE {
      --<selector element="typeId" value="1"/>
      matchAll [0] NULL,
      --<selector element="typeId" value="16"/>
      ipv4Remote [1] OCTET STRING (SIZE (8)),
      --<selector element="typeId" value="17"/>
      ipv4Local [2] OCTET STRING (SIZE (8)),
      --<selector element="typeId" value="33"/>
      ipv6Remote [3] OCTET STRING (SIZE (17)),
      --<selector element="typeId" value="35"/>
      ipv6Local [4] OCTET STRING (SIZE (17)),
      --<selector element="typeId" value="48"/>
      protId [5] OCTET STRING (SIZE (1)),
      --<selector element="typeId" value="64"/>
      singleLocalPort [6] OCTET STRING (SIZE (2)),
      --<selector element="typeId" value="65"/>
      localPortRange [7] OCTET STRING (SIZE (4)),
      --<selector element="typeId" value="80"/>
      singleRemPort [8] OCTET STRING (SIZE (2)),
      --<selector element="typeId" value="81"/>
      remPortRange [9] OCTET STRING (SIZE (4)),
      --<selector element="typeId" value="96"/>
      secParam [10] OCTET STRING (SIZE (4)),
      --<selector element="typeId" value="112"/>
      typeOfSvc [11] OCTET STRING (SIZE (2)),
      --<selector element="typeId" value="128"/>
      flowLabel [12] OCTET STRING (SIZE (3)),
      --<selector element="typeId" value="129"/>
      destMacAddr [13] OCTET STRING (SIZE (6)),
      --<selector element="typeId" value="130"/>
      srcMacAddr [14] OCTET STRING (SIZE (6)),
      --<selector element="typeId" value="131"/>
      ctagVid [15] OCTET STRING (SIZE (2)),
      --<selector element="typeId" value="132"/>
      stagVid [16] OCTET STRING (SIZE (2)),
      --<selector element="typeId" value="133"/>
      ctagPcp [17] OCTET STRING (SIZE (1)),
      --<selector element="typeId" value="134"/>
      stagPcp [18] OCTET STRING (SIZE (1)),
      --<selector element="typeId" value="135"/>
      ethernet [19] OCTET STRING (SIZE (2))
   }
}

PFCreateNew ::= SEQUENCE {
   spare [0] INTEGER (0..3) DEFAULT 0,
   filterDirection [1] INTEGER (0..3),
   filterId [2] INTEGER (0..15),
   --<is3GLength/>
   filterContentLen [3] INTEGER (0..255),
   --<is3GVarLenList lengthElem="filterContentLen"/>
   filterContent [4] SEQUENCE OF PFComponent
}

PFModifyAndDelete ::= SEQUENCE {
   spare [0] INTEGER (0..15) DEFAULT 0,
   filterId [1] INTEGER (0..15)
}

QoSRule ::= SEQUENCE {
   ruleId [0] INTEGER (0..255),
   ruleLen [1] INTEGER (0..65535),
   ruleOpCode [2] RuleOpCodes,
   dqr [3] BOOLEAN,
   numPacketFilters [4] INTEGER (0..15),
   --<inline/>
   packetFilterList [5] EXPLICIT CHOICE {
      --<selector element="ruleOpCode" value="1"/>
      --<length expr="@numPacketFilters"/>
      createNew [0] SEQUENCE (SIZE (0..15)) OF PFCreateNew,
      --<selector element="ruleOpCode" value="2"/>
      delete [1] NULL,
      --<selector element="ruleOpCode" value="3"/>
      --<length expr="@numPacketFilters"/>
      modifyAndAdd [2] SEQUENCE (SIZE (1..15)) OF PFCreateNew,
      --<selector element="ruleOpCode" value="4"/>
      --<length expr="@numPacketFilters"/>
      modifyAndReplace [3] SEQUENCE (SIZE (0..15)) OF PFCreateNew,
      --<selector element="ruleOpCode" value="5"/>
      --<length expr="@numPacketFilters"/>
      modifyAndDelete [4] SEQUENCE (SIZE (1..15)) OF PFModifyAndDelete,
      --<selector element="ruleOpCode" value="6"/>
      modifyNoModify [5] NULL
   },
   precedence [6] INTEGER (0..255),
   spare1 [7] BOOLEAN DEFAULT FALSE,
   segregation [8] BOOLEAN,
   flowId [9] INTEGER (0..63)
}

-- 9.11.4.13 - QoS rules 
QoSRules ::= SEQUENCE {
   --<is3GLength bitFieldSize="16"/>
   length [0] INTEGER (0..65535),
   --<is3GVarLenList lengthElem="length"/>
   rules [1] SEQUENCE OF QoSRule
}

-- 9.11.4.14 - Session AMBR 
SessionAMBR ::= SEQUENCE {
   --<is3GLength/>
   length [0] INTEGER (0..255) DEFAULT 8,
   unitAmbrDL [1] SessionUnits,
   sessionAmbrDL [2] INTEGER (0..65535),
   unitAmbrUL [3] SessionUnits,
   sessionAmbrUL [4] INTEGER (0..65535)
}

-- 9.11.4.10 - PDU address 
PDUAddress ::= SEQUENCE {
   --<is3GLength/>
   length [0] INTEGER (1..255),
   spare [1] INTEGER (0..31) DEFAULT 0,
   sessionType [2] INTEGER (0..7),
   addressInfo [3] OCTET STRING (SIZE (4..12))
}

-- 9.11.4.3 - Always-on PDU session indication 
AlwaysOnPDUSessionInd ::= SEQUENCE {
   spare [0] INTEGER (0..7) DEFAULT 0,
   apsi [1] BOOLEAN
}

ParamsList ::= SEQUENCE {
   paramId [0] INTEGER (0..255),
   paramContentLen [1] INTEGER (0..255),
   paramContent [2] OCTET STRING (SIZE (1..17))
}

EPSBearerCtxt ::= SEQUENCE {
   bearerId [0] INTEGER (0..255),
   bearerCtxtLen [1] INTEGER (0..65535),
   opCode [2] INTEGER (0..3),
   spare [3] BOOLEAN DEFAULT FALSE,
   eBit [4] BOOLEAN,
   numParams [5] INTEGER (0..15),
   --<inline/>
   --<length expr="@numParams"/>
   paramsList [6] SEQUENCE (SIZE (0..15)) OF ParamsList
}

-- 9.11.4.8 - Mapped EPS bearer contexts 
EPSBearerCtxts ::= SEQUENCE {
   --<is3GLength bitFieldSize="16"/>
   length [0] INTEGER (7..65535),
   --<is3GVarLenList lengthElem="length"/>
   epsBearerCtxts [1] SEQUENCE OF EPSBearerCtxt
}

Parameter ::= SEQUENCE {
   id [0] INTEGER (0..255),
   contents [1] OCTET STRING -- (preceeded by 1 octet length)
}

QOSFlowDescription ::= SEQUENCE {
   spare [0] INTEGER (0..3) DEFAULT 0,
   qfi [1] INTEGER (0..63),
   opCode [2] FlowOpCodes,
   spare2 [3] INTEGER (0..31) DEFAULT 0,
   spare3 [4] BOOLEAN DEFAULT FALSE,
   eBit [5] BOOLEAN,
   numParams [6] INTEGER (0..63),
   --<inline/>
   --<length expr="@numParams"/>
   --<noPresentBit/>
   paramsList [7] SEQUENCE (SIZE (0..63)) OF Parameter OPTIONAL
}

-- 9.11.4.12 - QoS flow descriptions 
QOSFlowDescriptions ::= SEQUENCE {
   --<is3GLength bitFieldSize="16"/>
   length [0] INTEGER (6..65535),
   --<is3GVarLenList lengthElem="length"/>
   qosFlowDesr [1] SEQUENCE OF QOSFlowDescription
}

--<is3GMessage/>
EstablishAccept ::= SEQUENCE {
   sscMode [0] SSCMode,
   pduSessionType [1] PDUSessionType,
   qosRules [2] QoSRules,
   sessionAMBR [3] SessionAMBR,
   --<iei format="tv" length="2">59</iei>
   cause [4] SMCause OPTIONAL,
   --<iei format="tlv">29</iei>
   pduAddress [5] PDUAddress OPTIONAL,
   --<iei format="tv" length="2">56</iei>
   rqTimer [6] GPRSTimer OPTIONAL,
   --<iei format="tlv">22</iei>
   snssai [7] SNSSAI OPTIONAL,
   --<iei format="tv" length="1">8</iei>
   alwaysOnPDUSession [8] AlwaysOnPDUSessionInd OPTIONAL, -- added in v15.1.0
   --<iei format="tlv-e">75</iei>
   epsBearerCtxts [9] EPSBearerCtxts OPTIONAL,
   --<iei format="tlv-e">78</iei>
   eapMessage [10] EAPMessage OPTIONAL,
   --<iei format="tlv-e">79</iei>
   qosFlowDesr [11] QOSFlowDescriptions OPTIONAL, -- added in v15.1.0
   --<iei format="tlv-e">7B</iei>
   extProtoCfgOpts [12] ExtProtoConfigOptions OPTIONAL,
   --<iei format="tlv">25</iei>
   dnn [13] DNNList OPTIONAL,
   ...,
   [[ 16:
      headerCompressionCfg [14] HeaderCompressionConfig OPTIONAL
   ]]
}

-- 9.11.4.5 - Allowed SSC mode 
AllowedSSCMode ::= SEQUENCE {
   spare [0] BOOLEAN DEFAULT FALSE,
   ssc3 [1] BOOLEAN,
   ssc2 [2] BOOLEAN,
   ssc1 [3] BOOLEAN
}

-- 9.11.4.19 - Session TMBR - removed in 16.3 
--SessionTMBR ::= SEQUENCE {
--   length INTEGER (0..255) DEFAULT 8,
--   unitTmbrDL INTEGER (0..255),
--   sessionTmbrDL INTEGER (0..65535),
--   unitTmbrUL INTEGER (0..255),
--   sessionTmbrUL INTEGER (0..65535)
--}
-- 9.11.4.21 - 5GSM congestion re-attempt indicator 
CongestionReattemptIndicator ::= SEQUENCE {
   --<is3GLength/>
   length [0] INTEGER (1..255),
   spare [1] INTEGER (0..127) DEFAULT 0,
   abo [2] BOOLEAN
}

--<is3GMessage/>
EstablishReject ::= SEQUENCE {
   cause [0] SMCause,
   --<iei format="tlv">37</iei>
   backoffTimer [1] GPRSTimer3 OPTIONAL,
   --<iei format="tv" length="1">0F</iei>
   allowedSSCMode [2] AllowedSSCMode OPTIONAL,
   --<iei format="tlv-e">78</iei>
   eapMessage [3] EAPMessage OPTIONAL,
   --<iei format="tlv-e">7B</iei>
   extProtoCfgOpts [4] ExtProtoConfigOptions OPTIONAL,
   --<iei format="tlv">61</iei>
   congestionReattemptInd [5] CongestionReattemptIndicator OPTIONAL -- Added in v15.4.0
   -- ...,
   -- [[ 16:
   -- format="tlv">TBD<
   -- reattemptInd ReattemptIndicator OPTIONAL  Added in v16.1.0 but no IEI yet
   -- ]]
}

--<is3GMessage/>
SMAuthCmd ::= SEQUENCE {
   eapMessage [0] EAPMessage,
   --<iei format="tlv-e">7B</iei>
   extProtoCfgOpts [1] ExtProtoConfigOptions OPTIONAL
}

--<is3GMessage/>
SMAuthDone ::= SEQUENCE {
   eapMessage [0] EAPMessage,
   --<iei format="tlv-e">7B</iei>
   extProtoCfgOpts [1] ExtProtoConfigOptions OPTIONAL
}

--<is3GMessage/>
SMAuthResult ::= SEQUENCE {
   --<iei format="tlv-e">78</iei>
   eapMessage [0] EAPMessage OPTIONAL,
   --<iei format="tlv-e">7B</iei>
   extProtoCfgOpts [1] ExtProtoConfigOptions OPTIONAL
}

--<is3GMessage/>
ModifyRequest ::= SEQUENCE {
   --<iei format="tlv">28</iei>
   capability [0] SMCapability OPTIONAL,
   --<iei format="tv" length="2">59</iei>
   cause [1] SMCause OPTIONAL, -- added in v15.1.0
   --<iei format="tv" length="3">55</iei>
   maxPktFilters [2] MaxSupportedPacketFilters OPTIONAL,
   --<iei format="tv" length="1">B</iei>
   alwaysOnPDUSession [3] AlwaysOnPDUSessionReq OPTIONAL, -- added in v15.1.0
   --<iei format="tv" length="3">13</iei>
   integProtMaxRate [4] IntegrityProtMaxDataRate OPTIONAL, -- added in v15.1.0
   --<iei format="tlv-e">7A</iei>
   qosRules [5] QoSRules OPTIONAL,
   --<iei format="tlv-e">79</iei>
   qosFlowDesr [6] QOSFlowDescriptions OPTIONAL, -- added in v15.1.0
   --<iei format="tlv-e">75</iei>
   epsBearerCtxts [7] EPSBearerCtxts OPTIONAL, -- added in v15.2.0
   --<iei format="tlv-e">7B</iei>
   extProtoCfgOpts [8] ExtProtoConfigOptions OPTIONAL,
   ...,
   [[ 16:
      portMgmtInfoContainer [9] PortMgmtInfoContainer OPTIONAL
   ]]
}

--<is3GMessage/>
ModifyReject ::= SEQUENCE {
   cause [0] SMCause,
   --<iei format="tlv">37</iei>
   backoffTimer [1] GPRSTimer3 OPTIONAL,
   --<iei format="tlv-e">7B</iei>
   extProtoCfgOpts [2] ExtProtoConfigOptions OPTIONAL,
   --<iei format="tlv">61</iei>
   congestionReattemptInd [3] CongestionReattemptIndicator OPTIONAL -- Added in v15.4.0
   -- ...,
   -- [[ 16:
   -- format="tlv">TBD<
   -- reattemptInd ReattemptIndicator OPTIONAL  Added in v16.1.0 but no IEI yet
   -- ]]
}

--<is3GMessage/>
ModifyCmd ::= SEQUENCE {
   --<iei format="tv" length="2">59</iei>
   cause [0] SMCause OPTIONAL,
   --<iei format="tlv">2A</iei>
   sessionAMBR [1] SessionAMBR OPTIONAL,
   --<iei format="tv" length="2">56</iei>
   rqTimer [2] GPRSTimer OPTIONAL,
   --<iei format="tv" length="1">8</iei>
   alwaysOnPDUSession [3] AlwaysOnPDUSessionReq OPTIONAL, -- added in v15.1.0
   --<iei format="tlv-e">7A</iei>
   qosRules [4] QoSRules OPTIONAL,
   --<iei format="tlv-e">75</iei>
   epsBearerCtxts [5] EPSBearerCtxts OPTIONAL,
   --<iei format="tlv-e">79</iei>
   qosFlowDesr [6] QOSFlowDescriptions OPTIONAL, -- added in v15.1.0
   --<iei format="tlv-e">7B</iei>
   extProtoCfgOpts [7] ExtProtoConfigOptions OPTIONAL,
   ...,
   [[ 16:
      headerCompressionCfg [8] HeaderCompressionConfig OPTIONAL,
      portMgmtInfoContainer [9] PortMgmtInfoContainer OPTIONAL
   ]]
}

--<is3GMessage/>
ModifyDone ::= SEQUENCE {
   --<iei format="tlv-e">7B</iei>
   extProtoCfgOpts [0] ExtProtoConfigOptions OPTIONAL,
   ...,
   [[ 16:
      portMgmtInfoContainer [1] PortMgmtInfoContainer OPTIONAL
   ]]
}

--<is3GMessage/>
ModifyCmdReject ::= SEQUENCE {
   cause [0] SMCause,
   --<iei format="tlv-e">7B</iei>
   extProtoCfgOpts [1] ExtProtoConfigOptions OPTIONAL
}

--<is3GMessage/>
ReleaseRequest ::= SEQUENCE {
   --<iei format="tv" length="2">59</iei>
   cause [0] SMCause OPTIONAL, -- added in v15.1.0
   --<iei format="tlv-e">7B</iei>
   extProtoCfgOpts [1] ExtProtoConfigOptions OPTIONAL
}

--<is3GMessage/>
ReleaseReject ::= SEQUENCE {
   cause [0] SMCause,
   --<iei format="tlv-e">7B</iei>
   extProtoCfgOpts [1] ExtProtoConfigOptions OPTIONAL
}

--<is3GMessage/>
ReleaseCmd ::= SEQUENCE {
   cause [0] SMCause,
   --<iei format="tlv">37</iei>
   backoffTimer [1] GPRSTimer3 OPTIONAL,
   --<iei format="tlv-e">78</iei>
   eapMessage [2] EAPMessage OPTIONAL,
   --<iei format="tlv">61</iei>
   congestionReattemptInd [3] CongestionReattemptIndicator OPTIONAL, -- Added in v15.4.0
   --<iei format="tlv-e">7B</iei>
   extProtoCfgOpts [4] ExtProtoConfigOptions OPTIONAL
   -- ...,
   -- [[ 16:
   -- iei format="tv" length="1">TBD
   -- accessType AccessType OPTIONAL - Added in v16.3 but no IEI yet
   -- ]]
}

--<is3GMessage/>
ReleaseDone ::= SEQUENCE {
   --<iei format="tv" length="2">59</iei>
   cause [0] SMCause OPTIONAL, -- added in v15.1.0
   --<iei format="tlv-e">7B</iei>
   extProtoCfgOpts [1] ExtProtoConfigOptions OPTIONAL
}

--<is3GMessage/>
SMStatus ::= SEQUENCE {
   cause [0] SMCause
}

-- 9.11.3.18D - Control plane service type 
ControlPlaneServiceType ::= SEQUENCE {
   spare [0] BOOLEAN DEFAULT FALSE,
   value [1] INTEGER (0..7)
}

--<is3GMessage/>
ControlPlaneServReq ::= SEQUENCE {
   nasKeySetIdent [0] NASKeySetIdentifier,
   ctrlPlaneServType [1] ControlPlaneServiceType,
   -- format="tlv">xx<
   -- ciotSmallDataContainer CIoTSmallDataContainer OPTIONAL,  No IEI yet
   --<iei format="tv" length="1">08</iei>
   containerType [2] PayloadContainerType OPTIONAL,
   --<iei format="tlv-e">7B</iei>
   --<inline/>
   container [3] EXPLICIT CHOICE {
      --<selector element="containerType" value="1"/>      
      n1sm [0] OpaqueData,
      --<selector element="containerType" value="2"/>
      sms [1] OpaqueData,
      --<selector element="containerType" value="3"/>
      lpp [2] OpaqueData,
      --<selector element="containerType" value="4"/>
      sor [3] OpaqueData,
      --<selector element="containerType" value="5"/>
      uePolicy [4] OpaqueData,
      --<selector element="containerType" value="6"/>
      ueParamUpdate [5] OpaqueData,
      --<selector element="containerType" value="7"/>
      locSvcs [6] OpaqueData,
      --<selector element="containerType" value="8"/>
      cIOTUserData [7] OpaqueData,
      --<selector element="containerType" value="15"/>
      multiple [8] MultiPayloadContainer
   } OPTIONAL,
   --<iei format="tv" length="2">12</iei>
   pduSessionId [4] PDUSessionId2 OPTIONAL,
   --<iei format="tlv">50</iei>
   sessionStat [5] PDUSessionStatus OPTIONAL,
   --<iei format="tv" length="1">0F</iei>
   releaseAssistIndication [6] ReleaseAssistInd OPTIONAL,
   --<iei format="tlv">40</iei>
   uplinkStat [7] UplinkDataStatus OPTIONAL,
   --<iei format="tlv-e">71</iei>
   nasMsgContainer [8] NASMessageContainer2 OPTIONAL,
   ...,
   [[ 16:
      addlInfo [9] AdditionalInfo OPTIONAL
   ]]
}

PDU ::= SEQUENCE {
   --<cEncSrcFname>TS24501MsgEnc_PDU_secHdr.c</cEncSrcFname>
   --<cDecSrcFname>TS24501MsgDec_PDU_secHdr.c</cDecSrcFname>
   secHdr [0] NAS5GSecProtMsgHdr OPTIONAL,
   protoDiscr [1] NAS5G-PROTOCOL-CLASS.&protoDiscr ({TS24501-IE-OBJECTSET}),
   --<inline/>
   hdrData [2] EXPLICIT CHOICE {
      --<selector element="protoDiscr" value="126"/>
      mm [0] SEQUENCE {
         spare1 [0] INTEGER (0..15) DEFAULT 0,
         secHdrType [1] NAS5GSecHdrType
      },
      --<selector element="protoDiscr" value="46"/>
      sm [1] SEQUENCE {
         pduSessIdent [0] PDUSessionIdentity,
         procTransIdent [1] INTEGER (0..255)
      }
   },
   msgType [3] NAS5G-PROTOCOL-CLASS.&msgType ({TS24501-IE-OBJECTSET}) (0..255),
   data [4] EXPLICIT NAS5G-PROTOCOL-CLASS.&Value ({TS24501-IE-OBJECTSET}{@
      protoDiscr,@msgType}),
   --<cEncSrcFname>TS24501MsgEnc_PDU_eom.c</cEncSrcFname>   
   --<cDecSrcFname>TS24301MsgDec_PDU_eom.c</cDecSrcFname>   
   eom [5] NULL
}

-- 9.11.2.6 - Intra N1 mode NAS transparent container 
IntraN1NASContainer ::= SEQUENCE {
   --<is3GLength/>
   length [0] INTEGER (1..255),
   authCode [1] OCTET STRING (SIZE (4)),
   cipherType [2] INTEGER (0..15),
   integrityType [3] INTEGER (0..15),
   spare1 [4] INTEGER (0..7) DEFAULT 0,
   kacf [5] BOOLEAN,
   tsc [6] BOOLEAN,
   keysetId [7] INTEGER (0..7),
   seqNumber [8] INTEGER (1..255)
}

-- 9.11.2.9 - S1 mode to N1 mode NAS transparent container 
S1ToN1NASContainer ::= SEQUENCE {
   --<is3GLength/>
   length [0] INTEGER (1..255),
   authCode [1] OCTET STRING (SIZE (4)),
   cipherType [2] INTEGER (0..15),
   integrityType [3] INTEGER (0..15),
   spare1 [4] BOOLEAN DEFAULT FALSE,
   ncc [5] INTEGER (0..7),
   tsc [6] BOOLEAN,
   keysetId [7] INTEGER (0..7),
   spare2 [8] INTEGER (1..65535) DEFAULT 0
}

-- 9.11.3.18B - CIoT small data container 
CIoTSmallDataContainer ::= SEQUENCE {
   --<is3GLength/>
   length [0] INTEGER (1..255),
   --<is3GVarLenList lengthElem="length"/>
   --<storage>array</storage>
   dataType [1] CIoTDataTypes,
   --<inline/>
   containerContents [2] EXPLICIT CHOICE {
      --<selector element="dataType" value="0"/>
      ctrlPlaneUserData [0] SEQUENCE {
         ddx [0] INTEGER (0..3),
         pduSessionId [1] INTEGER (0..7)
      },
      --<selector element="dataType" value="1"/>
      sms [1] SEQUENCE {
         spare [0] INTEGER (0..31) DEFAULT 0
      },
      --<selector element="dataType" value="2"/>
      locSvcsMsgContainer [2] SEQUENCE {
         ddx [0] INTEGER (0..3),
         spare [1] INTEGER (0..7) DEFAULT 0,
         addlInfoLen [2] INTEGER (0..255),
         --<noPresentBit/>
         --<length expr="@.addlInfoLen"/>
         addlInfo [3] OCTET STRING OPTIONAL
      }
   },
   --<length fixed-size="0"/>
   contents [3] OCTET STRING
}

-- UE Param Update for data type = 1 (UE parameters update list acknowledgement)
UEParamUpdateAck ::= SEQUENCE {
   spare [0] INTEGER (0..127) DEFAULT 0,
   dataType [1] INTEGER (0..1) DEFAULT 1, -- always 1 
   mac [2] OCTET STRING (SIZE (16))
}

-- 9.11.3.53A - UE Parameters Update Transparent Container 
/* This IE requires custom decoding due to the lowest bit in the header octet
   determining whether the IE contains an update list or ack of an update list.*/
UEParamUpdateContainer ::= SEQUENCE {
   --<is3GLength bitFieldSize="16"/>
   length [0] INTEGER (0..65535),
   updateOrAck [1] EXPLICIT CHOICE {
      update [0] UEParamUpdate,
      ack [1] UEParamUpdateAck
   }
}

-- 9.11.4.17 - Re-attempt indicator 
ReattemptIndicator ::= SEQUENCE {
   --<is3GLength/>
   length [0] INTEGER (1),
   spare [1] INTEGER (0..63) DEFAULT 0,
   eplmnc [2] BOOLEAN,
   ratc [3] BOOLEAN
}

-- 9.11.4.18 - 5GSM network feature support 
SMNetworkFeatureSupport ::= SEQUENCE {
   --<is3GLength/>
   length [0] INTEGER (1..255),
   spare [1] INTEGER (0..127) DEFAULT 0,
   eptS1 [2] BOOLEAN,
   --<noPresentBit/>
   spare2 [3] OCTET STRING OPTIONAL
}

-- 9.11.4.22 - ATSSS container 
ATSSSContainer ::= SEQUENCE {
   --<is3GLength bitFieldSize="16"/>
   length [0] INTEGER (3..65535),
   contents [1] OCTET STRING (SIZE (0..65535))
}

-- 9.11.4.23 - Control plane only indication 
ControlPlaneIndication ::= SEQUENCE {
   spare [0] INTEGER (0..7) DEFAULT 0,
   cpoi [1] BOOLEAN
}

-- Value assignments

mt-AuthRequest5G INTEGER ::= 86

mt-AuthResponse5G INTEGER ::= 87

mt-AuthResult5G INTEGER ::= 90

mt-AuthFailure5G INTEGER ::= 89

mt-AuthReject5G INTEGER ::= 88

mt-RegRequest5G INTEGER ::= 65

mt-RegAccept5G INTEGER ::= 66

mt-RegComplete5G INTEGER ::= 67

mt-RegReject5G INTEGER ::= 68

mt-ULNASTrans5G INTEGER ::= 103

mt-DLNASTrans5G INTEGER ::= 104

mt-DeregReqUEOrig5G INTEGER ::= 69

mt-DeregAcceptUEOrig5G INTEGER ::= 70

mt-DeregReqUETerm5G INTEGER ::= 71

mt-DeregAcceptUETerm5G INTEGER ::= 72

mt-ServRequest5G INTEGER ::= 76

mt-ServAccept5G INTEGER ::= 78

mt-ServReject5G INTEGER ::= 77

mt-CfgUpdateCmd5G INTEGER ::= 84

mt-CfgUpdateDone5G INTEGER ::= 85

mt-IdentityRequest5G INTEGER ::= 91

mt-IdentityResponse5G INTEGER ::= 92

mt-Notify5G INTEGER ::= 101

mt-NotifyResponse5G INTEGER ::= 102

mt-SecModeCmd5G INTEGER ::= 93

mt-SecModeDone5G INTEGER ::= 94

mt-SecModeReject5G INTEGER ::= 95

mt-MMStatus5G INTEGER ::= 100

mt-ControlPlaneServReq5G INTEGER ::= 79

st-EstablishRequest5G INTEGER ::= 193

st-EstablishAccept5G INTEGER ::= 194

st-EstablishReject5G INTEGER ::= 195

st-AuthCmd5G INTEGER ::= 197

st-AuthDone5G INTEGER ::= 198

st-AuthResult5G INTEGER ::= 199

st-ModifyRequest5G INTEGER ::= 201

st-ModifyReject5G INTEGER ::= 202

st-ModifyCmd5G INTEGER ::= 203

st-ModifyDone5G INTEGER ::= 204

st-ModifyCmdReject5G INTEGER ::= 205

st-ReleaseRequest5G INTEGER ::= 209

st-ReleaseReject5G INTEGER ::= 210

st-ReleaseCmd5G INTEGER ::= 211

st-ReleaseDone5G INTEGER ::= 212

st-SMStatus5G INTEGER ::= 214


-- Class definitions

NAS5G-PROTOCOL-CLASS ::= CLASS {
   &protoDiscr NAS5GProtoDiscr,
   &msgType INTEGER (0..255),
   &Value
}


-- Information Object definitions

obj-MMAuthRequest5G NAS5G-PROTOCOL-CLASS ::= {
   &protoDiscr mobMgmt5G, 
   &msgType mt-AuthRequest5G, 
   &Value AuthRequest
}


obj-MMAuthResponse5G NAS5G-PROTOCOL-CLASS ::= {
   &protoDiscr mobMgmt5G, 
   &msgType mt-AuthResponse5G, 
   &Value AuthResponse
}


obj-MMAuthResult5G NAS5G-PROTOCOL-CLASS ::= {
   &protoDiscr mobMgmt5G, 
   &msgType mt-AuthResult5G, 
   &Value AuthResult
}


obj-MMAuthFailure5G NAS5G-PROTOCOL-CLASS ::= {
   &protoDiscr mobMgmt5G, 
   &msgType mt-AuthFailure5G, 
   &Value AuthFailure
}


obj-MMAuthReject5G NAS5G-PROTOCOL-CLASS ::= {
   &protoDiscr mobMgmt5G, 
   &msgType mt-AuthReject5G, 
   &Value AuthReject
}


obj-RegRequest5G NAS5G-PROTOCOL-CLASS ::= {
   &protoDiscr mobMgmt5G, 
   &msgType mt-RegRequest5G, 
   &Value RegRequest
}


obj-RegAccept5G NAS5G-PROTOCOL-CLASS ::= {
   &protoDiscr mobMgmt5G, 
   &msgType mt-RegAccept5G, 
   &Value RegAccept
}


obj-RegComplete5G NAS5G-PROTOCOL-CLASS ::= {
   &protoDiscr mobMgmt5G, 
   &msgType mt-RegComplete5G, 
   &Value RegComplete
}


obj-RegReject5G NAS5G-PROTOCOL-CLASS ::= {
   &protoDiscr mobMgmt5G, 
   &msgType mt-RegReject5G, 
   &Value RegReject
}


obj-ULNASTrans5G NAS5G-PROTOCOL-CLASS ::= {
   &protoDiscr mobMgmt5G, 
   &msgType mt-ULNASTrans5G, 
   &Value ULNASTrans
}


obj-DLNASTrans5G NAS5G-PROTOCOL-CLASS ::= {
   &protoDiscr mobMgmt5G, 
   &msgType mt-DLNASTrans5G, 
   &Value DLNASTrans
}


obj-DeregReqUEOrig5G NAS5G-PROTOCOL-CLASS ::= {
   &protoDiscr mobMgmt5G, 
   &msgType mt-DeregReqUEOrig5G, 
   &Value DeregReqUEOrig
}


obj-DeregAcceptUEOrig5G NAS5G-PROTOCOL-CLASS ::= {
   &protoDiscr mobMgmt5G, 
   &msgType mt-DeregAcceptUEOrig5G, 
   &Value NULL
}


obj-DeregReqUETerm5G NAS5G-PROTOCOL-CLASS ::= {
   &protoDiscr mobMgmt5G, 
   &msgType mt-DeregReqUETerm5G, 
   &Value DeregReqUETerm
}


obj-DeregAcceptUETerm5G NAS5G-PROTOCOL-CLASS ::= {
   &protoDiscr mobMgmt5G, 
   &msgType mt-DeregAcceptUETerm5G, 
   &Value NULL
}


obj-ServRequest5G NAS5G-PROTOCOL-CLASS ::= {
   &protoDiscr mobMgmt5G, 
   &msgType mt-ServRequest5G, 
   &Value ServRequest
}


obj-ServAccept5G NAS5G-PROTOCOL-CLASS ::= {
   &protoDiscr mobMgmt5G, 
   &msgType mt-ServAccept5G, 
   &Value ServAccept
}


obj-ServReject5G NAS5G-PROTOCOL-CLASS ::= {
   &protoDiscr mobMgmt5G, 
   &msgType mt-ServReject5G, 
   &Value ServReject
}


obj-CfgUpdateCmd5G NAS5G-PROTOCOL-CLASS ::= {
   &protoDiscr mobMgmt5G, 
   &msgType mt-CfgUpdateCmd5G, 
   &Value CfgUpdateCmd
}


obj-CfgUpdateDone5G NAS5G-PROTOCOL-CLASS ::= {
   &protoDiscr mobMgmt5G, 
   &msgType mt-CfgUpdateDone5G, 
   &Value NULL
}


obj-IdentityRequest5G NAS5G-PROTOCOL-CLASS ::= {
   &protoDiscr mobMgmt5G, 
   &msgType mt-IdentityRequest5G, 
   &Value IdentityRequest
}


obj-IdentityResponse5G NAS5G-PROTOCOL-CLASS ::= {
   &protoDiscr mobMgmt5G, 
   &msgType mt-IdentityResponse5G, 
   &Value IdentityResponse
}


obj-Notify5G NAS5G-PROTOCOL-CLASS ::= {
   &protoDiscr mobMgmt5G, 
   &msgType mt-Notify5G, 
   &Value Notify
}


obj-NotifyResponse5G NAS5G-PROTOCOL-CLASS ::= {
   &protoDiscr mobMgmt5G, 
   &msgType mt-NotifyResponse5G, 
   &Value NotifyResponse
}


obj-SecModeCmd5G NAS5G-PROTOCOL-CLASS ::= {
   &protoDiscr mobMgmt5G, 
   &msgType mt-SecModeCmd5G, 
   &Value SecModeCmd
}


obj-SecModeDone5G NAS5G-PROTOCOL-CLASS ::= {
   &protoDiscr mobMgmt5G, 
   &msgType mt-SecModeDone5G, 
   &Value SecModeDone
}


obj-SecModeReject5G NAS5G-PROTOCOL-CLASS ::= {
   &protoDiscr mobMgmt5G, 
   &msgType mt-SecModeReject5G, 
   &Value SecModeReject
}


obj-MMStatus5G NAS5G-PROTOCOL-CLASS ::= {
   &protoDiscr mobMgmt5G, 
   &msgType mt-MMStatus5G, 
   &Value MMStatus
}


obj-ControlPlaneServReq5G NAS5G-PROTOCOL-CLASS ::= {
   &protoDiscr mobMgmt5G, 
   &msgType mt-ControlPlaneServReq5G, 
   &Value ControlPlaneServReq
}


obj-EstablishRequest5G NAS5G-PROTOCOL-CLASS ::= {
   &protoDiscr sessMgmt5G, 
   &msgType st-EstablishRequest5G, 
   &Value EstablishRequest
}


obj-EstablishAccept5G NAS5G-PROTOCOL-CLASS ::= {
   &protoDiscr sessMgmt5G, 
   &msgType st-EstablishAccept5G, 
   &Value EstablishAccept
}


obj-EstablishReject5G NAS5G-PROTOCOL-CLASS ::= {
   &protoDiscr sessMgmt5G, 
   &msgType st-EstablishReject5G, 
   &Value EstablishReject
}


obj-SMAuthCmd5G NAS5G-PROTOCOL-CLASS ::= {
   &protoDiscr sessMgmt5G, 
   &msgType st-AuthCmd5G, 
   &Value SMAuthCmd
}


obj-SMAuthDone5G NAS5G-PROTOCOL-CLASS ::= {
   &protoDiscr sessMgmt5G, 
   &msgType st-AuthDone5G, 
   &Value SMAuthDone
}


obj-SMAuthResult5G NAS5G-PROTOCOL-CLASS ::= {
   &protoDiscr sessMgmt5G, 
   &msgType st-AuthResult5G, 
   &Value SMAuthResult
}


obj-ModifyRequest5G NAS5G-PROTOCOL-CLASS ::= {
   &protoDiscr sessMgmt5G, 
   &msgType st-ModifyRequest5G, 
   &Value ModifyRequest
}


obj-ModifyReject5G NAS5G-PROTOCOL-CLASS ::= {
   &protoDiscr sessMgmt5G, 
   &msgType st-ModifyReject5G, 
   &Value ModifyReject
}


obj-ModifyCmd5G NAS5G-PROTOCOL-CLASS ::= {
   &protoDiscr sessMgmt5G, 
   &msgType st-ModifyCmd5G, 
   &Value ModifyCmd
}


obj-ModifyDone5G NAS5G-PROTOCOL-CLASS ::= {
   &protoDiscr sessMgmt5G, 
   &msgType st-ModifyDone5G, 
   &Value ModifyDone
}


obj-ModifyCmdReject5G NAS5G-PROTOCOL-CLASS ::= {
   &protoDiscr sessMgmt5G, 
   &msgType st-ModifyCmdReject5G, 
   &Value ModifyCmdReject
}


obj-ReleaseRequest5G NAS5G-PROTOCOL-CLASS ::= {
   &protoDiscr sessMgmt5G, 
   &msgType st-ReleaseRequest5G, 
   &Value ReleaseRequest
}


obj-ReleaseReject5G NAS5G-PROTOCOL-CLASS ::= {
   &protoDiscr sessMgmt5G, 
   &msgType st-ReleaseReject5G, 
   &Value ReleaseReject
}


obj-ReleaseCmd5G NAS5G-PROTOCOL-CLASS ::= {
   &protoDiscr sessMgmt5G, 
   &msgType st-ReleaseCmd5G, 
   &Value ReleaseCmd
}


obj-ReleaseDone5G NAS5G-PROTOCOL-CLASS ::= {
   &protoDiscr sessMgmt5G, 
   &msgType st-ReleaseDone5G, 
   &Value ReleaseDone
}


obj-SMStatus5G NAS5G-PROTOCOL-CLASS ::= {
   &protoDiscr sessMgmt5G, 
   &msgType st-SMStatus5G, 
   &Value SMStatus
}


-- Information Object Set definitions

TS24501-IE-OBJECTSET NAS5G-PROTOCOL-CLASS ::= {obj-MMAuthRequest5G | 
   obj-MMAuthResponse5G | obj-MMAuthResult5G | obj-MMAuthFailure5G | 
   obj-MMAuthReject5G | obj-RegRequest5G | obj-RegAccept5G | obj-RegComplete5G
    | obj-RegReject5G | obj-ULNASTrans5G | obj-DLNASTrans5G | 
   obj-DeregReqUEOrig5G | obj-DeregAcceptUEOrig5G | obj-DeregReqUETerm5G | 
   obj-DeregAcceptUETerm5G | obj-ServRequest5G | obj-ServAccept5G | 
   obj-ServReject5G | obj-CfgUpdateCmd5G | obj-CfgUpdateDone5G | 
   obj-IdentityRequest5G | obj-IdentityResponse5G | obj-Notify5G | 
   obj-NotifyResponse5G | obj-SecModeCmd5G | obj-SecModeDone5G | 
   obj-SecModeReject5G | obj-MMStatus5G | obj-EstablishRequest5G | 
   obj-EstablishAccept5G | obj-EstablishReject5G | obj-SMAuthCmd5G | 
   obj-SMAuthDone5G | obj-SMAuthResult5G | obj-ModifyRequest5G | 
   obj-ModifyReject5G | obj-ModifyCmd5G | obj-ModifyDone5G | 
   obj-ModifyCmdReject5G | obj-ReleaseRequest5G | obj-ReleaseReject5G | 
   obj-ReleaseCmd5G | obj-ReleaseDone5G | obj-SMStatus5G | 
   obj-ControlPlaneServReq5G}

END
