CSTA-start-call-detail-records-transmission
	{ iso( 1) identified-organization( 3) icd-ecma( 12)
		standard( 0) csta3( 285) start-call-detail-records-transmission( 363) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
CDRCrossRefID, CDRTransferMode FROM CSTA-call-detail-record
	{ iso( 1) identified-organization( 3) icd-ecma( 12)
		 standard( 0) csta3( 285) call-detail-record( 132) };

startCDRTransmission OPERATION ::=
{ 	ARGUMENT		StartCDRTransmissionArgument
	RESULT			StartCDRTransmissionResult
	ERRORS			{universalFailure }
	CODE			local: 363 }

StartCDRTransmissionArgument ::= SEQUENCE
{	transferMode			CDRTransferMode,
	extensions			CSTACommonArguments			OPTIONAL }

StartCDRTransmissionResult ::= SEQUENCE
{	cdrCrossRefID			CDRCrossRefID,  	     --corrected 06/2001
	extensions			CSTACommonArguments			OPTIONAL }

END  -- of CSTA-start-call-detail-records-transmission
