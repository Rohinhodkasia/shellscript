-- This file was generated by the Objective Systems ASN1C Compiler
-- (http://www.obj-sys.com).  Version: 7.4.2, Date: 15-Jun-2020.

NR-UE-Variables DEFINITIONS AUTOMATIC TAGS ::= BEGIN

IMPORTS

ARFCN-ValueNR, CellIdentity, EUTRA-PhysCellId, MeasId, MeasIdToAddModList, 
   MeasIdleCarrierEUTRA-r16, MeasIdleCarrierNR-r16, MeasResultIdleEUTRA-r16, 
   MeasResultIdleNR-r16, MeasObjectToAddModList, PhysCellId, RNTI-Value, 
   ReportConfigToAddModList, RSRP-Range, SL-MeasId-r16, SL-MeasIdList-r16, 
   SL-MeasObjectList-r16, SL-ReportConfigList-r16, SL-QuantityConfig-r16, 
   Tx-PoolMeasToAddModListEUTRA-r16, Tx-PoolMeasList-r16, QuantityConfig, 
   maxNrofCellMeas, maxNrofMeasId, maxFreqIdle-r16, PhysCellIdUTRA-FDD-r16, 
   ValidityAreaList-r16, CondConfigToAddModList-r16, ConnEstFailReport-r16, 
   LoggingDuration-r16, LoggingInterval-r16, LogMeasInfoList-r16, 
   LogMeasInfo-r16, RA-Report-r16, RLF-Report-r16, TraceReference-r16, 
   WLAN-Identifiers-r16, WLAN-NameList-r16, BT-NameList-r16, PLMN-Identity, 
   maxPLMN, RA-ReportList-r16, VisitedCellInfoList-r16, AbsoluteTimeInfo-r16, 
   LoggedEventTriggerConfig-r16, LoggedPeriodicalReportConfig-r16, 
   Sensor-NameListConfig-r16, WLAN-NameListConfig-r16, BT-NameListConfig-r16, 
   PLMN-IdentityList3-r16, AreaConfiguration-r16, maxNrofSL-MeasId-r16, 
   maxNrofFreqSL-r16, maxNrofCLI-RSSI-Resources-r16, maxNrofSRS-Resources-r16, 
   RSSI-ResourceId-r16, SRS-ResourceId
FROM NR-RRC-Definitions ;

-- Productions

-- TAG-VARCONDITIONALCONFIG-STOP
-- TAG-VARCONNESTFAILREPORT-START
VarConnEstFailReport-r16 ::= ConnEstFailReport-r16

-- TAG-VARMEASREPORTLISTSL-STOP
-- TAG-VARMOBILITYHISTORYREPORT-START
VarMobilityHistoryReport-r16 ::= VisitedCellInfoList-r16

-- NR-UE-VARIABLES-STOP
-- TAG-VARCONDITIONALCONFIG-START
VarConditionalConfig ::= SEQUENCE {
   condConfigList [0] CondConfigToAddModList-r16 OPTIONAL
}

-- TAG-VARCONNESTFAILREPORT-STOP
-- TAG-VARLOGMEASCONFIG-START
VarLogMeasConfig-r16-IEs ::= SEQUENCE {
   areaConfiguration-r16 [0] AreaConfiguration-r16 OPTIONAL, -- Need R
   plmn-IdentityList-r16 [1] PLMN-IdentityList3-r16 OPTIONAL, -- Need R
   bt-NameList-r16 [2] EXPLICIT BT-NameListConfig-r16 OPTIONAL, -- Need R
   wlan-NameList-r16 [3] EXPLICIT WLAN-NameListConfig-r16 OPTIONAL, -- Need R
   sensor-NameList-r16 [4] EXPLICIT Sensor-NameListConfig-r16 OPTIONAL, -- Need R
   loggingDuration-r16 [5] LoggingDuration-r16,
   reportType [6] EXPLICIT CHOICE {
      periodical [0] LoggedPeriodicalReportConfig-r16,
      eventTriggered [1] LoggedEventTriggerConfig-r16
   }
}

-- TAG-VARLOGMEASCONFIG-STOP
-- TAG-VARLOGMEAREPORT-START
VarLogMeasReport-r16 ::= SEQUENCE {
   absoluteTimeStamp-r16 [0] AbsoluteTimeInfo-r16,
   traceReference-r16 [1] TraceReference-r16,
   traceRecordingSessionRef-r16 [2] OCTET STRING (SIZE (2)),
   tce-Id-r16 [3] OCTET STRING (SIZE (1)),
   logMeasInfoList-r16 [4] LogMeasInfoList-r16,
   plmn-IdentityList-r16 [5] PLMN-IdentityList3-r16
}

-- TAG-VARLOGMEAREPORT-STOP
-- TAG-VARMEASCONFIG-START
VarMeasConfig ::= SEQUENCE {
     -- Measurement identities
   measIdList [0] MeasIdToAddModList OPTIONAL,
     -- Measurement objects
   measObjectList [1] MeasObjectToAddModList OPTIONAL,
     -- Reporting configurations
   reportConfigList [2] ReportConfigToAddModList OPTIONAL,
     -- Other parameters
   quantityConfig [3] QuantityConfig OPTIONAL,
   s-MeasureConfig [4] EXPLICIT CHOICE {
      ssb-RSRP [0] RSRP-Range,
      csi-RSRP [1] RSRP-Range
   } OPTIONAL
}

-- TAG-VARMEASCONFIG-STOP
-- TAG-VARMEASCONFIGSL-START
VarMeasConfigSL-r16 ::= SEQUENCE {
     -- NR sidelink measurement identities
   sl-MeasIdList-r16 [0] SL-MeasIdList-r16 OPTIONAL,
     -- NR sidelink measurement objects
   sl-MeasObjectList-r16 [1] SL-MeasObjectList-r16 OPTIONAL,
     -- NR sidelink reporting configurations
   sl-reportConfigList-r16 [2] SL-ReportConfigList-r16 OPTIONAL,
     -- Other parameters
   sl-QuantityConfig-r16 [3] SL-QuantityConfig-r16 OPTIONAL
}

-- TAG-VARMEASCONFIGSL-STOP
-- TAG-VARMEASIDLECONFIG-START
VarMeasIdleConfig-r16 ::= SEQUENCE {
   measIdleCarrierListNR-r16 [0] SEQUENCE (SIZE (1..maxFreqIdle-r16)) OF MeasIdleCarrierNR-r16
       OPTIONAL,
   measIdleCarrierListEUTRA-r16 [1] SEQUENCE (SIZE (1..maxFreqIdle-r16)) OF 
      MeasIdleCarrierEUTRA-r16 OPTIONAL,
   measIdleDuration-r16 [2] ENUMERATED { sec10(0), sec30(1), sec60(2), 
      sec120(3), sec180(4), sec240(5), sec300(6), spare(7) },
   validityAreaList-r16 [3] ValidityAreaList-r16 OPTIONAL
}

-- TAG-VARMEASIDLECONFIG-STOP
-- TAG-VARMEASIDLEREPORT-START
VarMeasIdleReport-r16 ::= SEQUENCE {
   measReportIdleNR-r16 [0] MeasResultIdleNR-r16,
   measReportIdleEUTRA-r16 [1] MeasResultIdleEUTRA-r16
}

CellsTriggeredList ::= SEQUENCE (SIZE (1..maxNrofCellMeas)) OF CHOICE {
   physCellId [0] PhysCellId,
   physCellIdEUTRA [1] EUTRA-PhysCellId,
   physCellIdUTRA-FDD-r16 [2] PhysCellIdUTRA-FDD-r16
}

SRS-RSRP-TriggeredList-r16 ::= SEQUENCE (SIZE (1..maxNrofSRS-Resources-r16)) OF SRS-ResourceId

CLI-RSSI-TriggeredList-r16 ::= SEQUENCE (SIZE (1..maxNrofCLI-RSSI-Resources-r16)) OF RSSI-ResourceId-r16

CLI-TriggeredList-r16 ::= CHOICE {
   srs-RSRP-TriggeredList-r16 [0] SRS-RSRP-TriggeredList-r16,
   cli-RSSI-TriggeredList-r16 [1] CLI-RSSI-TriggeredList-r16
}

VarMeasReport ::= SEQUENCE {
     -- List of measurement that have been triggered
   measId [0] MeasId,
   cellsTriggeredList [1] CellsTriggeredList OPTIONAL,
   numberOfReportsSent [2] INTEGER,
   cli-TriggeredList-r16 [3] EXPLICIT CLI-TriggeredList-r16 OPTIONAL,
   poolsTriggeredList-r16 [4] EXPLICIT CHOICE {
      tx-PoolMeasToAddModListEUTRA-r16 [0] Tx-PoolMeasToAddModListEUTRA-r16,
      tx-PoolMeasToAddModListNR-r16 [1] Tx-PoolMeasList-r16
   } OPTIONAL
}

-- TAG-VARMEASIDLEREPORT-STOP
-- TAG-VARMEASREPORTLIST-START
VarMeasReportList ::= SEQUENCE (SIZE (1..maxNrofMeasId)) OF VarMeasReport

VarMeasReportSL-r16 ::= SEQUENCE {
     -- List of NR sidelink measurement that have been triggered
   sl-MeasId-r16 [0] SL-MeasId-r16,
   sl-FrequencyTriggeredList-r16 [1] SEQUENCE (SIZE (1..maxNrofFreqSL-r16)) OF ARFCN-ValueNR
       OPTIONAL,
   sl-NumberOfReportsSent-r16 [2] INTEGER
}

-- TAG-VARMEASREPORTLIST-STOP
-- TAG-VARMEASREPORTLISTSL-START
VarMeasReportListSL-r16 ::= SEQUENCE (SIZE (1..maxNrofSL-MeasId-r16)) OF VarMeasReportSL-r16

-- TAG-VARMOBILITYHISTORYREPORT-STOP
-- TAG-VARPENDINGRNA-UPDATE-START
VarPendingRNA-Update ::= SEQUENCE {
   pendingRNA-Update [0] BOOLEAN OPTIONAL
}

PLMN-IdentityList-r16 ::= SEQUENCE (SIZE (1..maxPLMN)) OF PLMN-Identity

-- TAG-VARPENDINGRNA-UPDATE-STOP
-- TAG-VARRA-REPORT-START
VarRA-Report-r16 ::= SEQUENCE {
   ra-ReportList-r16 [0] RA-ReportList-r16,
   plmn-IdentityList-r16 [1] PLMN-IdentityList-r16
}

-- TAG-VARRA-REPORT-STOP
-- TAG-VARRESUMEMAC-INPUT-START
VarResumeMAC-Input ::= SEQUENCE {
   sourcePhysCellId [0] PhysCellId,
   targetCellIdentity [1] CellIdentity,
   source-c-RNTI [2] RNTI-Value
}

-- TAG-VARRESUMEMAC-INPUT-STOP
-- TAG-VARRLF-REPORT-START
VarRLF-Report-r16 ::= SEQUENCE {
   rlf-Report-r16 [0] EXPLICIT RLF-Report-r16,
   plmn-IdentityList-r16 [1] PLMN-IdentityList-r16
}

-- TAG-VARRLF-REPORT-STOP
-- TAG-VARSHORTMAC-INPUT-START
VarShortMAC-Input ::= SEQUENCE {
   sourcePhysCellId [0] PhysCellId,
   targetCellIdentity [1] CellIdentity,
   source-c-RNTI [2] RNTI-Value
}

END
