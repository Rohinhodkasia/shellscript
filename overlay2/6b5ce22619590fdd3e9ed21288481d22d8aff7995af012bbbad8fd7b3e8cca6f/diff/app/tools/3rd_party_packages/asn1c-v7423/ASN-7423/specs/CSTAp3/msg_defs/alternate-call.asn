CSTA-alternate-call
	{ iso( 1) identified-organization( 3) icd-ecma( 12)
		standard( 0) csta3( 285) alternate-call( 1) }

DEFINITIONS ::=
BEGIN

IMPORTS
OPERATION, ERROR FROM Remote-Operations-Information-Objects
	{joint-iso-itu-t remote-operations(4) informationObjects(5) version1(0) }

-- Data Types --
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
CSTACommonArguments FROM CSTA-extension-types
	{ iso( 1) identified-organization( 3) icd-ecma( 12)
		standard( 0) csta3( 285) extension-types( 129) }
ConsultOptions FROM CSTA-call-control
	{ iso( 1) identified-organization( 3) icd-ecma( 12)
		standard( 0) csta3( 285) call-control( 130) };

alternateCall OPERATION ::=
{ 	ARGUMENT 		AlternateCallArgument
	RESULT 			AlternateCallResult
	ERRORS 			{universalFailure }
	CODE 			local: 1 }

AlternateCallArgument ::= SEQUENCE
{ 	heldCall 			ConnectionID,
	activeCall 			ConnectionID,
	connectionReservation 		BOOLEAN 			OPTIONAL,
	consultOptions 			ConsultOptions 			DEFAULT unrestricted,
	extensions 			CSTACommonArguments 		OPTIONAL }

AlternateCallResult ::=CHOICE
{ 	extensions 			CSTACommonArguments,
	noData 				NULL }

END -- of CSTA-alternate-call
