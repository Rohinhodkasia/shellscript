CSTA-registration-info
	{ iso( 1) identified-organization( 3) icd-ecma( 12)
		standard( 0) csta3( 285) registration-info ( 372) }

DEFINITIONS ::=
BEGIN

IMPORTS
OPERATION, ERROR FROM Remote-Operations-Information-Objects
	{joint-iso-itu-t remote-operations(4) informationObjects(5) version1(0) }

-- Data Types –-
RegistrationList FROM CSTA-status-reporting
	{ iso( 1) identified-organization( 3) icd-ecma( 12)
		standard( 0) csta3( 285) status-reporting( 126) }
universalFailure FROM CSTA-error-definition
	{ iso( 1) identified-organization( 3) icd-ecma( 12)
		standard( 0) csta3( 285) error-definition( 120) }
ServiceCrossRefID FROM CSTA-capability-exchange
	{ iso( 1) identified-organization( 3) icd-ecma( 12)
		standard( 0) csta3( 285) capability-exchange( 131) }
CSTACommonArguments FROM CSTA-extension-types
	{ iso( 1) identified-organization( 3) icd-ecma( 12)
		standard( 0) csta3( 285) extension-types( 129) };

registrationInfo OPERATION ::=
{ 	ARGUMENT 		RegistrationInfoArg
	ERRORS 			{universalFailure }
	CODE 			local: 372 }

RegistrationInfoArg ::= SEQUENCE
{ 	serviceCrossRefID		ServiceCrossRefID,
	segmentID			INTEGER				OPTIONAL,
	lastSegment			BOOLEAN,
	registrationList		RegistrationList,
	extensions 			CSTACommonArguments 		OPTIONAL }

END -- of CSTA-registration-info
