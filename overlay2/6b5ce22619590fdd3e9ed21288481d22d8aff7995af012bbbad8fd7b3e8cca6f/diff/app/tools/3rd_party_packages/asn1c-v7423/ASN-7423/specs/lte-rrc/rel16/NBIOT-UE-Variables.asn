-- This file was generated by the Objective Systems ASN1C Compiler
-- (http://www.obj-sys.com).  Version: 7.4.2, Date: 15-Jun-2020.

NBIOT-UE-Variables DEFINITIONS AUTOMATIC TAGS ::= BEGIN

IMPORTS

CellGlobalIdEUTRA, maxFreq, PLMN-IdentityList3-r11
FROM EUTRA-RRC-Definitions 

VarShortMAC-Input, VarShortResumeMAC-Input-r13
FROM EUTRA-UE-Variables 

ANR-CarrierList-NB-r16, ANR-MeasResult-NB-r16, maxFreqANR-NB-r16, 
   NRSRP-Range-NB-r14, NRSRQ-Range-NB-r14, RLF-Report-NB-r16
FROM NBIOT-RRC-Definitions ;

-- Productions

VarShortMAC-Input-NB-r13 ::= VarShortMAC-Input

VarShortResumeMAC-Input-NB-r13 ::= VarShortResumeMAC-Input-r13

VarANR-MeasConfig-NB-r16 ::= SEQUENCE {
   anr-QualityThreshold-r16 [0] NRSRP-Range-NB-r14,
   anr-CarrierList-r16 [1] ANR-CarrierList-NB-r16 OPTIONAL
}

VarANR-MeasReport-NB-r16 ::= SEQUENCE {
   plmn-IdentityList-r16 [0] PLMN-IdentityList3-r11,
   servCellIdentity-r16 [1] CellGlobalIdEUTRA,
   measResultServCell-r16 [2] SEQUENCE {
      nrsrpResult-r16 [0] NRSRP-Range-NB-r14,
      nrsrqResult-r16 [1] NRSRQ-Range-NB-r14
   },
   measResultList-r16 [3] SEQUENCE (SIZE (1..maxFreqANR-NB-r16)) OF ANR-MeasResult-NB-r16
}

VarRLF-Report-NB-r16 ::= SEQUENCE {
   rlf-Report-r16 [0] RLF-Report-NB-r16,
   plmn-IdentityList-r16 [1] PLMN-IdentityList3-r11
}

END
