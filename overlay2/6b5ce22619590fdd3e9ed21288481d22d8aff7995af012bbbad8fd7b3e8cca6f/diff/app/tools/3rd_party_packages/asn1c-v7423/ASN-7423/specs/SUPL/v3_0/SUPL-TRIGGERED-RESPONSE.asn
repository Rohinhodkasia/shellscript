-- This file was generated by the Objective Systems ASN1C Compiler
-- (http://www.obj-sys.com).  Version: 6.8.A, Date: 18-Nov-2014.

SUPL-TRIGGERED-RESPONSE DEFINITIONS AUTOMATIC TAGS ::= BEGIN

IMPORTS

PosMethod, SLPAddress
FROM ULP-Components 

SupportedNetworkInformation, SPCSETKey, SPCTID, SPCSETKeylifetime, 
   GNSSPosTechnology
FROM Ver2-ULP-Components 

TriggerParams
FROM SUPL-TRIGGERED-START 

Ver3-SUPL-TRIGGERED-RESPONSE-extension
FROM ULP-Version-3-message-extensions ;

-- Productions

RepModee ::= ENUMERATED { realtime(1), quasirealtime(2), batch(3), ... }

BatchRepConditions ::= CHOICE {
   num-interval [0] INTEGER (1..1024),
   num-minutes [1] INTEGER (1..2048),
   endofsession [2] NULL,
   ...
}

BatchRepType ::= SEQUENCE {
   reportPosition [0] BOOLEAN,
   reportMeasurements [1] BOOLEAN,
   intermediateReports [2] BOOLEAN,
   discardOldest [3] BOOLEAN OPTIONAL,
   ...
}

ReportingMode ::= SEQUENCE {
   repMode [0] RepModee,
   batchRepConditions [1] BatchRepConditions OPTIONAL,
   batchRepType [2] BatchRepType OPTIONAL,
   ...
}

Ver2-SUPLTRIGGEREDRESPONSE ::= SEQUENCE {
   posMethod [0] PosMethod,
   triggerParams [1] TriggerParams OPTIONAL,
   sLPAddress [2] SLPAddress OPTIONAL,
   supportedNetworkInformation [3] SupportedNetworkInformation OPTIONAL,
   reportingMode [4] ReportingMode OPTIONAL,
   sPCSETKey [5] SPCSETKey OPTIONAL,
   sPCTID [6] SPCTID OPTIONAL,
   sPCSETKeylifetime [7] SPCSETKeylifetime OPTIONAL,
   gnssPosTechnology [8] GNSSPosTechnology OPTIONAL,
   ...,
   ver3-SUPL-TRIGGERED-RESPONSE-extension [9] 
      Ver3-SUPL-TRIGGERED-RESPONSE-extension OPTIONAL
}

END
