-- This file was generated by the Objective Systems ASN1C Compiler
-- (http://www.obj-sys.com).  Version: 7.4.2, Date: 15-Jun-2020.

NBIOT-InterNodeDefinitions DEFINITIONS AUTOMATIC TAGS ::= BEGIN

IMPORTS

C-RNTI, PhysCellId, SecurityAlgorithmConfig, ShortMAC-I
FROM EUTRA-RRC-Definitions 

AdditionalReestabInfoList
FROM EUTRA-InterNodeDefinitions 

CarrierFreq-NB-r13, CarrierFreq-NB-v1550, RadioResourceConfigDedicated-NB-r13, 
   UECapabilityInformation-NB, UE-Capability-NB-r13, 
   UE-Capability-NB-Ext-r14-IEs, UE-RadioPagingInfo-NB-r13
FROM NBIOT-RRC-Definitions ;

-- Productions

AS-Config-NB ::= SEQUENCE {
   sourceRadioResourceConfig-r13 [0] RadioResourceConfigDedicated-NB-r13,
   sourceSecurityAlgorithmConfig-r13 [1] SecurityAlgorithmConfig,
   sourceUE-Identity-r13 [2] C-RNTI,
   sourceDl-CarrierFreq-r13 [3] CarrierFreq-NB-r13,
   ...,
   [[
      sourceDL-CarrierFreq-v1550 [4] CarrierFreq-NB-v1550 OPTIONAL
   ]]
}

RRM-Config-NB ::= SEQUENCE {
   ue-InactiveTime [0] ENUMERATED { s1(0), s2(1), s3(2), s5(3), s7(4), s10(5), 
      s15(6), s20(7), s25(8), s30(9), s40(10), s50(11), min1(12), min1s20(13), 
      min1s40(14), min2(15), min2s30(16), min3(17), min3s30(18), min4(19), 
      min5(20), min6(21), min7(22), min8(23), min9(24), min10(25), min12(26), 
      min14(27), min17(28), min20(29), min24(30), min28(31), min33(32), 
      min38(33), min44(34), min50(35), hr1(36), hr1min30(37), hr2(38), 
      hr2min30(39), hr3(40), hr3min30(41), hr4(42), hr5(43), hr6(44), hr8(45), 
      hr10(46), hr13(47), hr16(48), hr20(49), day1(50), day1hr12(51), day2(52)
      , day2hr12(53), day3(54), day4(55), day5(56), day7(57), day10(58), 
      day14(59), day19(60), day24(61), day30(62), dayMoreThan30(63) } OPTIONAL,
   ...
}

ReestablishmentInfo-NB ::= SEQUENCE {
   sourcePhysCellId-r13 [0] PhysCellId,
   targetCellShortMAC-I-r13 [1] ShortMAC-I,
   additionalReestabInfoList-r13 [2] AdditionalReestabInfoList OPTIONAL,
   ...
}

AS-Context-NB ::= SEQUENCE {
   reestablishmentInfo-r13 [0] ReestablishmentInfo-NB OPTIONAL,
   ...
}

HandoverPreparationInformation-NB-Ext-r14-IEs ::= SEQUENCE {
   ue-RadioAccessCapabilityInfoExt-r14 [0] OCTET STRING (CONTAINING 
      UE-Capability-NB-Ext-r14-IEs) OPTIONAL,
   nonCriticalExtension [1] SEQUENCE {

   } OPTIONAL
}

HandoverPreparationInformation-NB-v1380-IEs ::= SEQUENCE {
   lateNonCriticalExtension [0] OCTET STRING OPTIONAL,
   nonCriticalExtension [1] HandoverPreparationInformation-NB-Ext-r14-IEs
       OPTIONAL
}

HandoverPreparationInformation-NB-IEs ::= SEQUENCE {
   ue-RadioAccessCapabilityInfo-r13 [0] UE-Capability-NB-r13,
   as-Config-r13 [1] AS-Config-NB,
   rrm-Config-r13 [2] RRM-Config-NB OPTIONAL,
   as-Context-r13 [3] AS-Context-NB OPTIONAL,
   nonCriticalExtension [4] HandoverPreparationInformation-NB-v1380-IEs
       OPTIONAL
}

HandoverPreparationInformation-NB ::= SEQUENCE {
   criticalExtensions [0] EXPLICIT CHOICE {
      c1 [0] EXPLICIT CHOICE {
         handoverPreparationInformation-r13 [0] 
            HandoverPreparationInformation-NB-IEs,
         spare3 [1] NULL,
         spare2 [2] NULL,
         spare1 [3] NULL
      },
      criticalExtensionsFuture [1] SEQUENCE {

      }
   }
}

UEPagingCoverageInformation-NB-IEs ::= SEQUENCE {
--the possible value(s) can differ from those sent on Uu
   npdcch-NumRepetitionPaging-r13 [0] INTEGER (1..2048) OPTIONAL,
   nonCriticalExtension [1] SEQUENCE {

   } OPTIONAL
}

UEPagingCoverageInformation-NB ::= SEQUENCE {
   criticalExtensions [0] EXPLICIT CHOICE {
      c1 [0] EXPLICIT CHOICE {
         uePagingCoverageInformation-r13 [0] UEPagingCoverageInformation-NB-IEs
            ,
         spare3 [1] NULL,
         spare2 [2] NULL,
         spare1 [3] NULL
      },
      criticalExtensionsFuture [1] SEQUENCE {

      }
   }
}

UERadioAccessCapabilityInformation-NB-r14-IEs ::= SEQUENCE {
   ue-RadioAccessCapabilityInfo-r14 [0] OCTET STRING (CONTAINING 
      UECapabilityInformation-NB) OPTIONAL,
   nonCriticalExtension [1] SEQUENCE {

   } OPTIONAL
}

UERadioAccessCapabilityInformation-NB-v1380-IEs ::= SEQUENCE {
   lateNonCriticalExtension [0] OCTET STRING OPTIONAL,
   nonCriticalExtension [1] UERadioAccessCapabilityInformation-NB-r14-IEs
       OPTIONAL
}

UERadioAccessCapabilityInformation-NB-IEs ::= SEQUENCE {
   ue-RadioAccessCapabilityInfo-r13 [0] OCTET STRING (CONTAINING 
      UE-Capability-NB-r13),
   nonCriticalExtension [1] UERadioAccessCapabilityInformation-NB-v1380-IEs
       OPTIONAL
}

UERadioAccessCapabilityInformation-NB ::= SEQUENCE {
   criticalExtensions [0] EXPLICIT CHOICE {
      c1 [0] EXPLICIT CHOICE {
         ueRadioAccessCapabilityInformation-r13 [0] 
            UERadioAccessCapabilityInformation-NB-IEs,
         spare3 [1] NULL,
         spare2 [2] NULL,
         spare1 [3] NULL
      },
      criticalExtensionsFuture [1] SEQUENCE {

      }
   }
}

UERadioPagingInformation-NB-IEs ::= SEQUENCE {
   ue-RadioPagingInfo-r13 [0] OCTET STRING (CONTAINING 
      UE-RadioPagingInfo-NB-r13),
   nonCriticalExtension [1] SEQUENCE {

   } OPTIONAL
}

UERadioPagingInformation-NB ::= SEQUENCE {
   criticalExtensions [0] EXPLICIT CHOICE {
      c1 [0] EXPLICIT CHOICE {
         ueRadioPagingInformation-r13 [0] UERadioPagingInformation-NB-IEs,
         spare3 [1] NULL,
         spare2 [2] NULL,
         spare1 [3] NULL
      },
      criticalExtensionsFuture [1] SEQUENCE {

      }
   }
}

END
