-- This file was generated by the Objective Systems ASN1C Compiler
-- (http://www.obj-sys.com).  Version: 6.8.A, Date: 15-Nov-2014.

SUPL-END DEFINITIONS AUTOMATIC TAGS ::= BEGIN

IMPORTS

StatusCode, Position, Ver
FROM ULP-Components 

Ver2-SUPL-END-extension
FROM ULP-Version-2-message-extensions 

Ver3-SUPL-END-extension
FROM ULP-Version-3-message-extensions ;

-- Productions

SUPLEND ::= SEQUENCE {
   position [0] Position OPTIONAL,
   statusCode [1] StatusCode OPTIONAL,
   ver [2] Ver OPTIONAL,
   ...,
   ver2-SUPL-END-extension [3] Ver2-SUPL-END-extension OPTIONAL,
   ver3-SUPL-END-extension [4] Ver3-SUPL-END-extension OPTIONAL
}

END
