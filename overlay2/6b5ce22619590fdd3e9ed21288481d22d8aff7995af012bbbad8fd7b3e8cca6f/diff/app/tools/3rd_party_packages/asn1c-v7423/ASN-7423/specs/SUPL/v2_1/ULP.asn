-- This file was generated by the Objective Systems ASN1C Compiler
-- (http://www.obj-sys.com).  Version: 6.8.A, Date: 15-Nov-2014.

ULP DEFINITIONS AUTOMATIC TAGS ::= BEGIN

IMPORTS

Version, SessionID
FROM ULP-Components 

SUPLINIT
FROM SUPL-INIT 

SUPLSTART
FROM SUPL-START 

SUPLRESPONSE
FROM SUPL-RESPONSE 

SUPLPOSINIT
FROM SUPL-POS-INIT 

SUPLPOS
FROM SUPL-POS 

SUPLEND
FROM SUPL-END 

SUPLAUTHREQ
FROM SUPL-AUTH-REQ 

SUPLAUTHRESP
FROM SUPL-AUTH-RESP 

Ver2-SUPLTRIGGEREDSTART
FROM SUPL-TRIGGERED-START 

Ver2-SUPLTRIGGEREDRESPONSE
FROM SUPL-TRIGGERED-RESPONSE 

Ver2-SUPLREPORT
FROM SUPL-REPORT 

Ver2-SUPLTRIGGEREDSTOP
FROM SUPL-TRIGGERED-STOP 

Ver2-SUPLSETINIT
FROM SUPL-SET-INIT 

Ver2-SUPLNOTIFY
FROM SUPL-NOTIFY 

Ver2-SUPLNOTIFYRESPONSE
FROM SUPL-NOTIFY-RESPONSE ;

-- Productions

UlpMessage ::= CHOICE {
   msSUPLINIT [0] SUPLINIT,
   msSUPLSTART [1] SUPLSTART,
   msSUPLRESPONSE [2] SUPLRESPONSE,
   msSUPLPOSINIT [3] SUPLPOSINIT,
   msSUPLPOS [4] SUPLPOS,
   msSUPLEND [5] SUPLEND,
   msSUPLAUTHREQ [6] SUPLAUTHREQ,
   msSUPLAUTHRESP [7] SUPLAUTHRESP,
   ...,
   msSUPLTRIGGEREDSTART [8] Ver2-SUPLTRIGGEREDSTART,
   msSUPLTRIGGEREDRESPONSE [9] Ver2-SUPLTRIGGEREDRESPONSE,
   msSUPLTRIGGEREDSTOP [10] Ver2-SUPLTRIGGEREDSTOP,
   msSUPLNOTIFY [11] Ver2-SUPLNOTIFY,
   msSUPLNOTIFYRESPONSE [12] Ver2-SUPLNOTIFYRESPONSE,
   msSUPLSETINIT [13] Ver2-SUPLSETINIT,
   msSUPLREPORT [14] Ver2-SUPLREPORT
}

ULP-PDU ::= SEQUENCE {
   length [0] INTEGER (0..65535),
   version [1] Version,
   sessionID [2] SessionID,
   message [3] UlpMessage
}

END
