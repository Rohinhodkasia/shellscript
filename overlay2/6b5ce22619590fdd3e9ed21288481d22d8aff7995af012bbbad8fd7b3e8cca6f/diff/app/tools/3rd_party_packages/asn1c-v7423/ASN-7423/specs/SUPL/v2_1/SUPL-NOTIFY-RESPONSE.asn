-- This file was generated by the Objective Systems ASN1C Compiler
-- (http://www.obj-sys.com).  Version: 6.8.A, Date: 15-Nov-2014.

SUPL-NOTIFY-RESPONSE DEFINITIONS AUTOMATIC TAGS ::= BEGIN

-- Productions

NotificationResponse ::= ENUMERATED { allowed(0), notAllowed(1), ... }

Ver2-SUPLNOTIFYRESPONSE ::= SEQUENCE {
   notificationResponse [0] NotificationResponse OPTIONAL,
   ...
}

END
