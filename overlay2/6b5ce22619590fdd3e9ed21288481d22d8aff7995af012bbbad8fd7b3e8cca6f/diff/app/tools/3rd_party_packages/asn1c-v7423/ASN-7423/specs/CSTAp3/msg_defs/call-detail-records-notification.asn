CSTA-call-detail-records-notification
	{ iso( 1) identified-organization( 3) icd-ecma( 12)
		standard( 0) csta3( 285) call-detail-records-notification( 360) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
CDRCrossRefID, CDRReason FROM CSTA-call-detail-record
	{ iso( 1) identified-organization( 3) icd-ecma( 12)
		standard( 0) csta3( 285) call-detail-record( 132) };

cDRNotification OPERATION ::=
{	ARGUMENT		CDRNotificationArgument
	RESULT			CDRNotificationResult
	ERRORS  		{universalFailure }
	CODE			local: 360
 }

CDRNotificationArgument ::= SEQUENCE
{	cdrCrossRefID			CDRCrossRefID,
	cdrReason			CDRReason				OPTIONAL,
	extensions			CSTACommonArguments			OPTIONAL }

CDRNotificationResult ::= CHOICE
{	extensions			CSTACommonArguments,
	noData				NULL }

END  -- of CSTA-call-detail-records-notification
