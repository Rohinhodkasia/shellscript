-- This file was generated by the Objective Systems ASN1C Compiler
-- (http://www.obj-sys.com).  Version: 7.4.2, Date: 15-Jun-2020.

NR-InterNodeDefinitions DEFINITIONS AUTOMATIC TAGS ::= BEGIN

IMPORTS

ARFCN-ValueNR, ARFCN-ValueEUTRA, CellIdentity, CGI-InfoEUTRA, CGI-InfoNR, 
   CSI-RS-Index, DRX-Config, EUTRA-PhysCellId, FreqBandIndicatorNR, GapConfig, 
   maxBandComb, maxBands, maxCellSFTD, maxFeatureSetsPerBand, maxFreqIDC-MRDC, 
   maxNrofCombIDC, maxNrofSCells, maxNrofServingCells, maxNrofServingCells-1, 
   maxNrofServingCellsEUTRA, maxNrofIndexesToReport, maxSimultaneousBands, 
   MeasQuantityResults, MeasResultCellListSFTD-EUTRA, MeasResultCellListSFTD-NR
   , MeasResultList2NR, MeasResultSCG-Failure, MeasResultServFreqListEUTRA-SCG
   , P-Max, PhysCellId, RadioBearerConfig, RAN-NotificationAreaInfo, 
   RRCReconfiguration, ServCellIndex, SetupRelease, SSB-Index, SSB-MTC, 
   SSB-ToMeasure, SS-RSSI-Measurement, ShortMAC-I, SubcarrierSpacing, 
   UEAssistanceInformation, UE-CapabilityRAT-ContainerList
FROM NR-RRC-Definitions ;

-- Productions

BandCombinationIndex ::= INTEGER (1..maxBandComb)

BandEntryIndex ::= INTEGER (0..maxNrofServingCells)

FeatureSetEntryIndex ::= INTEGER (1..maxFeatureSetsPerBand)

HandoverCommand-IEs ::= SEQUENCE {
   handoverCommandMessage [0] OCTET STRING (CONTAINING RRCReconfiguration),
   nonCriticalExtension [1] SEQUENCE {

   } OPTIONAL
}

-- TAG-NR-INTER-NODE-DEFINITIONS-STOP
-- TAG-HANDOVER-COMMAND-START
HandoverCommand ::= SEQUENCE {
   criticalExtensions [0] EXPLICIT CHOICE {
      c1 [0] EXPLICIT CHOICE {
         handoverCommand [0] HandoverCommand-IEs,
         spare3 [1] NULL,
         spare2 [2] NULL,
         spare1 [3] NULL
      },
      criticalExtensionsFuture [1] SEQUENCE {

      }
   }
}

AS-Config ::= SEQUENCE {
   rrcReconfiguration [0] OCTET STRING (CONTAINING RRCReconfiguration),
   ...,
   [[
      sourceRB-SN-Config [1] OCTET STRING (CONTAINING RadioBearerConfig)
          OPTIONAL,
      sourceSCG-NR-Config [2] OCTET STRING (CONTAINING RRCReconfiguration)
          OPTIONAL,
      sourceSCG-EUTRA-Config [3] OCTET STRING OPTIONAL
   ]],
   [[
      sourceSCG-Configured [4] ENUMERATED { true(0) } OPTIONAL
   ]]
}

RRM-Config ::= SEQUENCE {
   ue-InactiveTime [0] ENUMERATED { s1(0), s2(1), s3(2), s5(3), s7(4), s10(5), 
      s15(6), s20(7), s25(8), s30(9), s40(10), s50(11), min1(12), min1s20(13), 
      min1s40(14), min2(15), min2s30(16), min3(17), min3s30(18), min4(19), 
      min5(20), min6(21), min7(22), min8(23), min9(24), min10(25), min12(26), 
      min14(27), min17(28), min20(29), min24(30), min28(31), min33(32), 
      min38(33), min44(34), min50(35), hr1(36), hr1min30(37), hr2(38), 
      hr2min30(39), hr3(40), hr3min30(41), hr4(42), hr5(43), hr6(44), hr8(45), 
      hr10(46), hr13(47), hr16(48), hr20(49), day1(50), day1hr12(51), day2(52)
      , day2hr12(53), day3(54), day4(55), day5(56), day7(57), day10(58), 
      day14(59), day19(60), day24(61), day30(62), dayMoreThan30(63) } OPTIONAL,
   candidateCellInfoList [1] MeasResultList2NR OPTIONAL,
   ...,
   [[
      candidateCellInfoListSN-EUTRA [2] MeasResultServFreqListEUTRA-SCG
          OPTIONAL
   ]]
}

ReestabNCellInfo ::= SEQUENCE {
   cellIdentity [0] CellIdentity,
   key-gNodeB-Star [1] BIT STRING  (SIZE (256)),
   shortMAC-I [2] ShortMAC-I
}

ReestabNCellInfoList ::= SEQUENCE (SIZE (1..maxCellPrep)) OF ReestabNCellInfo

ReestablishmentInfo ::= SEQUENCE {
   sourcePhysCellId [0] PhysCellId,
   targetCellShortMAC-I [1] ShortMAC-I,
   additionalReestabInfoList [2] ReestabNCellInfoList OPTIONAL
}

BandCombinationInfo ::= SEQUENCE {
   bandCombinationIndex [0] BandCombinationIndex,
   allowedFeatureSetsList [1] SEQUENCE (SIZE (1..maxFeatureSetsPerBand)) OF FeatureSetEntryIndex
}

BandCombinationInfoList ::= SEQUENCE (SIZE (1..maxBandComb)) OF BandCombinationInfo

SelectedBandEntriesMN ::= SEQUENCE (SIZE (1..maxSimultaneousBands)) OF BandEntryIndex

ConfigRestrictInfoSCG ::= SEQUENCE {
   allowedBC-ListMRDC [0] BandCombinationInfoList OPTIONAL,
   powerCoordination-FR1 [1] SEQUENCE {
      p-maxNR-FR1 [0] P-Max OPTIONAL,
      p-maxEUTRA [1] P-Max OPTIONAL,
      p-maxUE-FR1 [2] P-Max OPTIONAL
   } OPTIONAL,
   servCellIndexRangeSCG [2] SEQUENCE {
      lowBound [0] ServCellIndex,
      upBound [1] ServCellIndex
   } OPTIONAL, -- Cond SN-AddMod
   maxMeasFreqsSCG [3] INTEGER (1..maxMeasFreqsMN) OPTIONAL,
   dummy [4] INTEGER (1..maxMeasIdentitiesMN) OPTIONAL,
   ...,
   [[
      selectedBandEntriesMNList [5] SEQUENCE (SIZE (1..maxBandComb)) OF 
         SelectedBandEntriesMN OPTIONAL,
      pdcch-BlindDetectionSCG [6] INTEGER (1..15) OPTIONAL,
      maxNumberROHC-ContextSessionsSN [7] INTEGER (0..16384) OPTIONAL
   ]],
   [[
      maxIntraFreqMeasIdentitiesSCG [8] INTEGER (1..maxMeasIdentitiesMN) OPTIONAL,
      maxInterFreqMeasIdentitiesSCG [9] INTEGER (1..maxMeasIdentitiesMN) OPTIONAL
   ]]
}

BandCombinationInfoSN ::= SEQUENCE {
   bandCombinationIndex [0] BandCombinationIndex,
   requestedFeatureSets [1] FeatureSetEntryIndex
}

AS-Context ::= SEQUENCE {
   reestablishmentInfo [0] ReestablishmentInfo OPTIONAL,
   configRestrictInfo [1] ConfigRestrictInfoSCG OPTIONAL,
   ...,
   [[
      ran-NotificationAreaInfo [2] EXPLICIT RAN-NotificationAreaInfo OPTIONAL
   ]],
   [[
      ueAssistanceInformation [3] OCTET STRING (CONTAINING 
         UEAssistanceInformation) OPTIONAL
   ]],
   [[
      selectedBandCombinationSN [4] BandCombinationInfoSN OPTIONAL
   ]]
}

HandoverPreparationInformation-IEs ::= SEQUENCE {
   ue-CapabilityRAT-List [0] UE-CapabilityRAT-ContainerList,
   sourceConfig [1] AS-Config OPTIONAL, -- Cond HO
   rrm-Config [2] RRM-Config OPTIONAL,
   as-Context [3] AS-Context OPTIONAL,
   nonCriticalExtension [4] SEQUENCE {

   } OPTIONAL
}

-- TAG-HANDOVER-COMMAND-STOP
-- TAG-HANDOVER-PREPARATION-INFORMATION-START
HandoverPreparationInformation ::= SEQUENCE {
   criticalExtensions [0] EXPLICIT CHOICE {
      c1 [0] EXPLICIT CHOICE {
         handoverPreparationInformation [0] HandoverPreparationInformation-IEs,
         spare3 [1] NULL,
         spare2 [2] NULL,
         spare1 [3] NULL
      },
      criticalExtensionsFuture [1] SEQUENCE {

      }
   }
}

ConfigRestrictModReqSCG ::= SEQUENCE {
   requestedBC-MRDC [0] BandCombinationInfoSN OPTIONAL,
   requestedP-MaxFR1 [1] P-Max OPTIONAL,
   ...,
   [[
      requestedPDCCH-BlindDetectionSCG [2] INTEGER (1..15) OPTIONAL,
      requestedP-MaxEUTRA [3] P-Max OPTIONAL
   ]]
}

DRX-Info ::= SEQUENCE {
   drx-LongCycleStartOffset [0] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   shortDRX [1] SEQUENCE {
      drx-ShortCycle [0] ENUMERATED { ms2(0), ms3(1), ms4(2), ms5(3), ms6(4), 
         ms7(5), ms8(6), ms10(7), ms14(8), ms16(9), ms20(10), ms30(11), 
         ms32(12), ms35(13), ms40(14), ms64(15), ms80(16), ms128(17), ms160(18)
         , ms256(19), ms320(20), ms512(21), ms640(22), spare9(23), spare8(24), 
         spare7(25), spare6(26), spare5(27), spare4(28), spare3(29), spare2(30)
         , spare1(31) },
      drx-ShortCycleTimer [1] INTEGER (1..16)
   } OPTIONAL
}

NR-FreqInfo ::= SEQUENCE {
   measuredFrequency [0] ARFCN-ValueNR OPTIONAL,
   ...
}

MeasConfigSN ::= SEQUENCE {
   measuredFrequenciesSN [0] SEQUENCE (SIZE (1..maxMeasFreqsSN)) OF NR-FreqInfo OPTIONAL,
   ...
}

FR-Info ::= SEQUENCE {
   servCellIndex [0] ServCellIndex,
   fr-Type [1] ENUMERATED { fr1(0), fr2(1) }
}

FR-InfoList ::= SEQUENCE (SIZE (1..maxNrofServingCells-1)) OF FR-Info

CandidateServingFreqListNR ::= SEQUENCE (SIZE (1..maxFreqIDC-MRDC)) OF ARFCN-ValueNR

PH-UplinkCarrierSCG ::= SEQUENCE {
   ph-Type1or3 [0] ENUMERATED { type1(0), type3(1) },
   ...
}

PH-InfoSCG ::= SEQUENCE {
   servCellIndex [0] ServCellIndex,
   ph-Uplink [1] PH-UplinkCarrierSCG,
   ph-SupplementaryUplink [2] PH-UplinkCarrierSCG OPTIONAL,
   ...
}

PH-TypeListSCG ::= SEQUENCE (SIZE (1..maxNrofServingCells)) OF PH-InfoSCG

CandidateServingFreqListEUTRA ::= SEQUENCE (SIZE (1..maxFreqIDC-MRDC)) OF ARFCN-ValueEUTRA

CG-Config-v1590-IEs ::= SEQUENCE {
   scellFrequenciesSN-NR [0] SEQUENCE (SIZE (1..maxNrofServingCells-1)) OF ARFCN-ValueNR OPTIONAL,
   scellFrequenciesSN-EUTRA [1] SEQUENCE (SIZE (1..maxNrofServingCells-1)) OF ARFCN-ValueEUTRA
       OPTIONAL,
   nonCriticalExtension [2] SEQUENCE {

   } OPTIONAL
}

CG-Config-v1560-IEs ::= SEQUENCE {
   pSCellFrequencyEUTRA [0] ARFCN-ValueEUTRA OPTIONAL,
   scg-CellGroupConfigEUTRA [1] OCTET STRING OPTIONAL,
   candidateCellInfoListSN-EUTRA [2] OCTET STRING OPTIONAL,
   candidateServingFreqListEUTRA [3] CandidateServingFreqListEUTRA OPTIONAL,
   needForGaps [4] ENUMERATED { true(0) } OPTIONAL,
   drx-ConfigSCG [5] DRX-Config OPTIONAL,
   reportCGI-RequestEUTRA [6] SEQUENCE {
      requestedCellInfoEUTRA [0] SEQUENCE {
         eutraFrequency [0] ARFCN-ValueEUTRA,
         cellForWhichToReportCGI-EUTRA [1] EUTRA-PhysCellId
      } OPTIONAL
   } OPTIONAL,
   nonCriticalExtension [7] CG-Config-v1590-IEs OPTIONAL
}

CG-Config-v1540-IEs ::= SEQUENCE {
   pSCellFrequency [0] ARFCN-ValueNR OPTIONAL,
   reportCGI-RequestNR [1] SEQUENCE {
      requestedCellInfo [0] SEQUENCE {
         ssbFrequency [0] ARFCN-ValueNR,
         cellForWhichToReportCGI [1] PhysCellId
      } OPTIONAL
   } OPTIONAL,
   ph-InfoSCG [2] PH-TypeListSCG OPTIONAL,
   nonCriticalExtension [3] CG-Config-v1560-IEs OPTIONAL
}

CG-Config-IEs ::= SEQUENCE {
   scg-CellGroupConfig [0] OCTET STRING (CONTAINING RRCReconfiguration)
       OPTIONAL,
   scg-RB-Config [1] OCTET STRING (CONTAINING RadioBearerConfig) OPTIONAL,
   configRestrictModReq [2] ConfigRestrictModReqSCG OPTIONAL,
   drx-InfoSCG [3] DRX-Info OPTIONAL,
   candidateCellInfoListSN [4] OCTET STRING (CONTAINING MeasResultList2NR)
       OPTIONAL,
   measConfigSN [5] MeasConfigSN OPTIONAL,
   selectedBandCombination [6] BandCombinationInfoSN OPTIONAL,
   fr-InfoListSCG [7] FR-InfoList OPTIONAL,
   candidateServingFreqListNR [8] CandidateServingFreqListNR OPTIONAL,
   nonCriticalExtension [9] CG-Config-v1540-IEs OPTIONAL
}

-- TAG-HANDOVER-PREPARATION-INFORMATION-STOP
-- TAG-CG-CONFIG-START
CG-Config ::= SEQUENCE {
   criticalExtensions [0] EXPLICIT CHOICE {
      c1 [0] EXPLICIT CHOICE {
         cg-Config [0] CG-Config-IEs,
         spare3 [1] NULL,
         spare2 [2] NULL,
         spare1 [3] NULL
      },
      criticalExtensionsFuture [1] SEQUENCE {

      }
   }
}

MeasConfigMN ::= SEQUENCE {
   measuredFrequenciesMN [0] SEQUENCE (SIZE (1..maxMeasFreqsMN)) OF NR-FreqInfo OPTIONAL,
   measGapConfig [1] EXPLICIT CHOICE {
      release [0] NULL,
      setup [1] EXPLICIT GapConfig
   } OPTIONAL,
   gapPurpose [2] ENUMERATED { perUE(0), perFR1(1) } OPTIONAL,
   ...,
   [[
      measGapConfigFR2 [3] EXPLICIT CHOICE {
         release [0] NULL,
         setup [1] EXPLICIT GapConfig
      } OPTIONAL
   ]]
}

VictimSystemType ::= SEQUENCE {
   gps [0] ENUMERATED { true(0) } OPTIONAL,
   glonass [1] ENUMERATED { true(0) } OPTIONAL,
   bds [2] ENUMERATED { true(0) } OPTIONAL,
   galileo [3] ENUMERATED { true(0) } OPTIONAL,
   wlan [4] ENUMERATED { true(0) } OPTIONAL,
   bluetooth [5] ENUMERATED { true(0) } OPTIONAL
}

AffectedCarrierFreqCombEUTRA ::= SEQUENCE (SIZE (1..maxNrofServingCellsEUTRA)) OF ARFCN-ValueEUTRA

AffectedCarrierFreqCombNR ::= SEQUENCE (SIZE (1..maxNrofServingCells)) OF ARFCN-ValueNR

AffectedCarrierFreqCombInfoMRDC ::= SEQUENCE {
   victimSystemType [0] VictimSystemType,
   interferenceDirectionMRDC [1] ENUMERATED { eutra-nr(0), nr(1), other(2), 
      utra-nr-other(3), nr-other(4), spare3(5), spare2(6), spare1(7) },
   affectedCarrierFreqCombMRDC [2] SEQUENCE {
      affectedCarrierFreqCombEUTRA [0] AffectedCarrierFreqCombEUTRA OPTIONAL,
      affectedCarrierFreqCombNR [1] AffectedCarrierFreqCombNR
   } OPTIONAL
}

MRDC-AssistanceInfo ::= SEQUENCE {
   affectedCarrierFreqCombInfoListMRDC [0] SEQUENCE (SIZE (1..maxNrofCombIDC)) OF 
      AffectedCarrierFreqCombInfoMRDC,
   ...
}

PH-UplinkCarrierMCG ::= SEQUENCE {
   ph-Type1or3 [0] ENUMERATED { type1(0), type3(1) },
   ...
}

PH-InfoMCG ::= SEQUENCE {
   servCellIndex [0] ServCellIndex,
   ph-Uplink [1] PH-UplinkCarrierMCG,
   ph-SupplementaryUplink [2] PH-UplinkCarrierMCG OPTIONAL,
   ...
}

PH-TypeListMCG ::= SEQUENCE (SIZE (1..maxNrofServingCells)) OF PH-InfoMCG

SFTD-FrequencyList-NR ::= SEQUENCE (SIZE (1..maxCellSFTD)) OF ARFCN-ValueNR

SFTD-FrequencyList-EUTRA ::= SEQUENCE (SIZE (1..maxCellSFTD)) OF ARFCN-ValueEUTRA

CG-ConfigInfo-v1590-IEs ::= SEQUENCE {
   servFrequenciesMN-NR [0] SEQUENCE (SIZE (1..maxNrofServingCells-1)) OF ARFCN-ValueNR OPTIONAL,
   nonCriticalExtension [1] SEQUENCE {

   } OPTIONAL
}

CG-ConfigInfo-v1570-IEs ::= SEQUENCE {
   sftdFrequencyList-NR [0] SFTD-FrequencyList-NR OPTIONAL,
   sftdFrequencyList-EUTRA [1] SFTD-FrequencyList-EUTRA OPTIONAL,
   nonCriticalExtension [2] CG-ConfigInfo-v1590-IEs OPTIONAL
}

CG-ConfigInfo-v1560-IEs ::= SEQUENCE {
   candidateCellInfoListMN-EUTRA [0] OCTET STRING OPTIONAL,
   candidateCellInfoListSN-EUTRA [1] OCTET STRING OPTIONAL,
   sourceConfigSCG-EUTRA [2] OCTET STRING OPTIONAL,
   scgFailureInfoEUTRA [3] SEQUENCE {
      failureTypeEUTRA [0] ENUMERATED { t313-Expiry(0), randomAccessProblem(1)
         , rlc-MaxNumRetx(2), scg-ChangeFailure(3) },
      measResultSCG-EUTRA [1] OCTET STRING
   } OPTIONAL,
   drx-ConfigMCG [4] DRX-Config OPTIONAL,
   measResultReportCGI-EUTRA [5] SEQUENCE {
      eutraFrequency [0] ARFCN-ValueEUTRA,
      cellForWhichToReportCGI-EUTRA [1] EUTRA-PhysCellId,
      cgi-InfoEUTRA [2] CGI-InfoEUTRA
   } OPTIONAL,
   measResultCellListSFTD-EUTRA [6] MeasResultCellListSFTD-EUTRA OPTIONAL,
   fr-InfoListMCG [7] FR-InfoList OPTIONAL,
   nonCriticalExtension [8] CG-ConfigInfo-v1570-IEs OPTIONAL
}

CG-ConfigInfo-v1540-IEs ::= SEQUENCE {
   ph-InfoMCG [0] PH-TypeListMCG OPTIONAL,
   measResultReportCGI [1] SEQUENCE {
      ssbFrequency [0] ARFCN-ValueNR,
      cellForWhichToReportCGI [1] PhysCellId,
      cgi-Info [2] CGI-InfoNR
   } OPTIONAL,
   nonCriticalExtension [2] CG-ConfigInfo-v1560-IEs OPTIONAL
}

CG-ConfigInfo-IEs ::= SEQUENCE {
   ue-CapabilityInfo [0] OCTET STRING (CONTAINING 
      UE-CapabilityRAT-ContainerList) OPTIONAL, -- Cond SN-AddMod
   candidateCellInfoListMN [1] MeasResultList2NR OPTIONAL,
   candidateCellInfoListSN [2] OCTET STRING (CONTAINING MeasResultList2NR)
       OPTIONAL,
   measResultCellListSFTD-NR [3] MeasResultCellListSFTD-NR OPTIONAL,
   scgFailureInfo [4] SEQUENCE {
      failureType [0] ENUMERATED { t310-Expiry(0), randomAccessProblem(1), 
         rlc-MaxNumRetx(2), synchReconfigFailure-SCG(3), scg-reconfigFailure(4)
         , srb3-IntegrityFailure(5) },
      measResultSCG [1] OCTET STRING (CONTAINING MeasResultSCG-Failure)
   } OPTIONAL,
   configRestrictInfo [5] ConfigRestrictInfoSCG OPTIONAL,
   drx-InfoMCG [6] DRX-Info OPTIONAL,
   measConfigMN [7] MeasConfigMN OPTIONAL,
   sourceConfigSCG [8] OCTET STRING (CONTAINING RRCReconfiguration) OPTIONAL,
   scg-RB-Config [9] OCTET STRING (CONTAINING RadioBearerConfig) OPTIONAL,
   mcg-RB-Config [10] OCTET STRING (CONTAINING RadioBearerConfig) OPTIONAL,
   mrdc-AssistanceInfo [11] MRDC-AssistanceInfo OPTIONAL,
   nonCriticalExtension [12] CG-ConfigInfo-v1540-IEs OPTIONAL
}

-- TAG-CG-CONFIG-STOP
-- TAG-CG-CONFIG-INFO-START
CG-ConfigInfo ::= SEQUENCE {
   criticalExtensions [0] EXPLICIT CHOICE {
      c1 [0] EXPLICIT CHOICE {
         cg-ConfigInfo [0] CG-ConfigInfo-IEs,
         spare3 [1] NULL,
         spare2 [2] NULL,
         spare1 [3] NULL
      },
      criticalExtensionsFuture [1] SEQUENCE {

      }
   }
}

MeasTiming ::= SEQUENCE {
   frequencyAndTiming [0] SEQUENCE {
      carrierFreq [0] ARFCN-ValueNR,
      ssbSubcarrierSpacing [1] SubcarrierSpacing,
      ssb-MeasurementTimingConfiguration [2] SSB-MTC,
      ss-RSSI-Measurement [3] SS-RSSI-Measurement OPTIONAL
   } OPTIONAL,
   ...,
   [[
      ssb-ToMeasure [1] EXPLICIT SSB-ToMeasure OPTIONAL,
      physCellId [2] PhysCellId OPTIONAL
   ]]
}

MeasTimingList ::= SEQUENCE (SIZE (1..maxMeasFreqsMN)) OF MeasTiming

MeasurementTimingConfiguration-v1550-IEs ::= SEQUENCE {
   campOnFirstSSB [0] BOOLEAN,
   psCellOnlyOnFirstSSB [1] BOOLEAN,
   nonCriticalExtension [2] SEQUENCE {

   } OPTIONAL
}

MeasurementTimingConfiguration-IEs ::= SEQUENCE {
   measTiming [0] MeasTimingList OPTIONAL,
   nonCriticalExtension [1] MeasurementTimingConfiguration-v1550-IEs OPTIONAL
}

-- TAG-CG-CONFIG-INFO-STOP
-- TAG-MEASUREMENT-TIMING-CONFIGURATION-START
MeasurementTimingConfiguration ::= SEQUENCE {
   criticalExtensions [0] EXPLICIT CHOICE {
      c1 [0] EXPLICIT CHOICE {
         measTimingConf [0] MeasurementTimingConfiguration-IEs,
         spare3 [1] NULL,
         spare2 [2] NULL,
         spare1 [3] NULL
      },
      criticalExtensionsFuture [1] SEQUENCE {

      }
   }
}

UERadioPagingInformation-IEs ::= SEQUENCE {
   supportedBandListNRForPaging [0] SEQUENCE (SIZE (1..maxBands)) OF FreqBandIndicatorNR
       OPTIONAL,
   nonCriticalExtension [1] SEQUENCE {

   } OPTIONAL
}

-- TAG-MEASUREMENT-TIMING-CONFIGURATION-STOP
-- TAG-UE-RADIO-PAGING-INFORMATION-START
UERadioPagingInformation ::= SEQUENCE {
   criticalExtensions [0] EXPLICIT CHOICE {
      c1 [0] EXPLICIT CHOICE {
         ueRadioPagingInformation [0] UERadioPagingInformation-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

UERadioAccessCapabilityInformation-IEs ::= SEQUENCE {
   ue-RadioAccessCapabilityInfo [0] OCTET STRING (CONTAINING 
      UE-CapabilityRAT-ContainerList),
   nonCriticalExtension [1] SEQUENCE {

   } OPTIONAL
}

-- TAG-UE-RADIO-PAGING-INFORMATION-STOP
-- TAG-UE-RADIO-ACCESS-CAPABILITY-INFORMATION-START
UERadioAccessCapabilityInformation ::= SEQUENCE {
   criticalExtensions [0] EXPLICIT CHOICE {
      c1 [0] EXPLICIT CHOICE {
         ueRadioAccessCapabilityInformation [0] 
            UERadioAccessCapabilityInformation-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

-- Value assignments

maxMeasFreqsMN INTEGER ::= 32

maxMeasFreqsSN INTEGER ::= 32

maxMeasIdentitiesMN INTEGER ::= 62

maxCellPrep INTEGER ::= 32


END
