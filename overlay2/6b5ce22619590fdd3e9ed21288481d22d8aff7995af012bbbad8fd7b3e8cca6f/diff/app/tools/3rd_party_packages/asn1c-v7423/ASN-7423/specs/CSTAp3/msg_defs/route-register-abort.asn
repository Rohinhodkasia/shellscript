CSTA-route-register-abort
	{ iso( 1) identified-organization( 3) icd-ecma( 12)
		standard( 0) csta3( 285) route-register-abort( 249) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
RouteRegisterReqID FROM CSTA-device-feature-types
	{ iso( 1) identified-organization( 3) icd-ecma( 12)
		standard( 0) csta3( 285) device-feature-types( 127) }
CSTACommonArguments FROM CSTA-extension-types 
	{ iso( 1) identified-organization( 3) icd-ecma( 12)
		standard( 0) csta3( 285) extension-types( 129) };

routeRegisterAbort OPERATION ::=
{	ARGUMENT		RouteRegisterAbortArgument
	ERRORS			{universalFailure }
	ALWAYS RESPONDS		FALSE
	CODE			local: 249 }

RouteRegisterAbortArgument ::= SEQUENCE
{	routeRegisterReqID		RouteRegisterReqID,
	extensions			CSTACommonArguments			OPTIONAL }

END  -- of CSTA-route-register-abort
