CSTA-queued-event
	{ iso( 1) identified-organization( 3) icd-ecma( 12)
		standard( 0) csta3( 285) queued-event( 32) }

DEFINITIONS::=
BEGIN

IMPORTS 

-- Data Types –-
EventCause FROM CSTA-event-causes
	{ iso( 1) identified-organization( 3) icd-ecma( 12)
		standard( 0) csta3( 285) event-causes( 121) }
CalledDeviceID,CallingDeviceID,RedirectionDeviceID,SubjectDeviceID,AssociatedCalledDeviceID, AssociatedCallingDeviceID, NetworkCalledDeviceID,
NetworkCallingDeviceID FROM CSTA-device-identifiers
		{ iso( 1) identified-organization( 3) icd-ecma( 12)
			standard( 0) csta3( 285) device-identifiers( 123) }
ConnectionID FROM CSTA-call-connection-identifiers
	{ iso( 1) identified-organization( 3) icd-ecma( 12)
		standard( 0) csta3( 285) call-connection-identifiers( 124) }
LocalConnectionState FROM CSTA-connection-states
	{ iso( 1) identified-organization( 3) icd-ecma( 12)
		standard( 0) csta3( 285) connection-states( 125) }
CSTACommonArguments FROM CSTA-extension-types
	{ iso( 1) identified-organization( 3) icd-ecma( 12)
		standard( 0) csta3( 285) extension-types( 129) }
LocationInfoList,CallCharacteristics, CallLinkageData, ServicesPermitted FROM CSTA-call-control 
	{ iso( 1) identified-organization( 3) icd-ecma( 12)
		standard( 0) csta3( 285) call-control( 130) }
DeviceHistory,CorrelatorData, UserData,LanguagePreferences,
SubjectOfCall, MessageInfo FROM CSTA-device-feature-types
	{ iso( 1) identified-organization( 3) icd-ecma( 12)
		standard( 0) csta3( 285) device-feature-types( 127) }
ConnectionInformation, MediaCallCharacteristics FROM CSTA-media-services
	{ iso( 1) identified-organization( 3) icd-ecma( 12)
		standard( 0) csta3( 285) media-services( 136) };

QueuedEvent ::= SEQUENCE
{	queuedConnection		ConnectionID,
	queue				SubjectDeviceID,
	callingDevice			CallingDeviceID,
	calledDevice			CalledDeviceID,
	lastRedirectionDevice		RedirectionDeviceID,
	numberQueued			[ 0] IMPLICIT INTEGER				OPTIONAL,
	callsInFront			[ 1] IMPLICIT INTEGER				OPTIONAL,
	localConnectionInfo		LocalConnectionState				OPTIONAL,
	correlatorData			[ 2] IMPLICIT CorrelatorData			OPTIONAL,
	userData			UserData					OPTIONAL,
	cause				EventCause,
	servicesPermitted		[ 3] IMPLICIT ServicesPermitted			OPTIONAL,
	networkCallingDevice		NetworkCallingDeviceID				OPTIONAL,
	networkCalledDevice		NetworkCalledDeviceID				OPTIONAL,
	associatedCallingDevice		AssociatedCallingDeviceID			OPTIONAL,
	associatedCalledDevice		AssociatedCalledDeviceID			OPTIONAL,
	mediaCallCharacteristics	[ 4] IMPLICIT MediaCallCharacteristics 		OPTIONAL,
	callCharacteristics		[ 5] IMPLICIT CallCharacteristics		OPTIONAL,
	queuedConnectionInfo		[ 6] IMPLICIT ConnectionInformation		OPTIONAL,
	callLinkageData			[ 7] IMPLICIT CallLinkageData			OPTIONAL,
	subjectOfCall			[ 8] IMPLICIT SubjectOfCall			OPTIONAL,
	messageInfo			[ 9] IMPLICIT MessageInfo			OPTIONAL,
	languagePreferences		[10] IMPLICIT LanguagePreferences		OPTIONAL,
	deviceHistory			[11] IMPLICIT DeviceHistory			OPTIONAL,
	locationInfo			[12] IMPLICIT LocationInfoList			OPTIONAL,
	extensions			CSTACommonArguments				OPTIONAL }

END  -- of CSTA-queued-event
