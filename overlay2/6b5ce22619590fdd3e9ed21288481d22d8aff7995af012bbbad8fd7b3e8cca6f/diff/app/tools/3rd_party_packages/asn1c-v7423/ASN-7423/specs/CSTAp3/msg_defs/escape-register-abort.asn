CSTA-escape-register-abort
	{ iso( 1) identified-organization( 3) icd-ecma( 12)
		standard( 0) csta3( 285) escape-register-abort( 366) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
EscapeRegisterID FROM CSTA-escape-types
	{ iso( 1) identified-organization( 3) icd-ecma( 12)
		standard( 0) csta3( 285) escape-types( 135) };

escapeRegisterAbort OPERATION ::=
{ 	ARGUMENT		EscapeRegisterAbortArgument
	ERRORS			{universalFailure }
	ALWAYS RESPONDS		FALSE
	CODE			local: 366 }

EscapeRegisterAbortArgument ::= SEQUENCE 
{	escapeRegisterID		EscapeRegisterID,
	extensions			CSTACommonArguments			OPTIONAL }

END -- of CSTA-escape-register-abort
