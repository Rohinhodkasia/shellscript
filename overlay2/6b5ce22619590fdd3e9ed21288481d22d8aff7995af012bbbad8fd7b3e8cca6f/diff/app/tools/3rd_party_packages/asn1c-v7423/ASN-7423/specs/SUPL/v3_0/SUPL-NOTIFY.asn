-- This file was generated by the Objective Systems ASN1C Compiler
-- (http://www.obj-sys.com).  Version: 6.8.A, Date: 18-Nov-2014.

SUPL-NOTIFY DEFINITIONS AUTOMATIC TAGS ::= BEGIN

IMPORTS

Notification
FROM SUPL-INIT 

Ver3-SUPL-NOTIFY-extension
FROM ULP-Version-3-message-extensions ;

-- Productions

Ver2-SUPLNOTIFY ::= SEQUENCE {
   notification [0] Notification,
   ...,
   ver3-SUPL-NOTIFY-extension [1] Ver3-SUPL-NOTIFY-extension OPTIONAL
}

END
