CSTA-set-ringer-status
	{ iso( 1) identified-organization( 3) icd-ecma( 12)
		standard( 0) csta3( 285) set-ringer-status( 280) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
RingerID, RingMode, Volume FROM CSTA-physical-device-feature 
	{ iso( 1) identified-organization( 3) icd-ecma( 12)
		standard( 0) csta3( 285) physical-device-feature( 137) };

setRingerStatus OPERATION ::=
{	ARGUMENT 		SetRingerStatusArgument
	RESULT			SetRingerStatusResult
	ERRORS			{universalFailure }
	CODE			local: 280 }

SetRingerStatusArgument ::= SEQUENCE
{	device 				DeviceID,
	ringer				RingerID,
	ringMode 			RingMode				OPTIONAL,
	ringPattern 			[1] IMPLICIT INTEGER	 		OPTIONAL,
	ringVolume	 		[2] Volume 				OPTIONAL,
	extensions 			CSTACommonArguments 			OPTIONAL }

SetRingerStatusResult ::= CHOICE
{	extensions 			CSTACommonArguments,
	noData 				NULL }

END -- of CSTA-set-ringer-status
