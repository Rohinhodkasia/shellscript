-- This file was generated by the Objective Systems ASN1C Compiler
-- (http://www.obj-sys.com).  Version: 6.3.A, Date: 10-Oct-2009.

Remote-Operations-Generic-ROS-PDUs 
{joint-iso-itu-t remote-operations(4) generic-ROS-PDUs(6) version1(0)}
DEFINITIONS IMPLICIT TAGS ::= BEGIN

IMPORTS

OPERATION, ERROR
FROM Remote-Operations-Information-Objects 
{joint-iso-itu-t remote-operations(4) informationObjects(5) version1(0)};

-- Parameterized type assignments

Invoke {InvokeId:InvokeIdSet, OPERATION:Operations} ::= SEQUENCE {
   invokeId InvokeId,
   linkedId CHOICE {
      present [0] present < InvokeId,
      absent [1] NULL
   } OPTIONAL,
   opcode OPERATION.&operationCode ({Operations}),
   argument OPERATION.&ArgumentType ({Operations}{@opcode}) OPTIONAL
}

ReturnResult {OPERATION:Operations} ::= SEQUENCE {
   invokeId InvokeId,
   result SEQUENCE {
      opcode OPERATION.&operationCode ({Operations}),
      result OPERATION.&ResultType ({Operations}{@.opcode})
   } OPTIONAL
}

ReturnError {ERROR:Errors} ::= SEQUENCE {
   invokeId InvokeId,
   errcode ERROR.&errorCode ({Errors}),
   parameter ERROR.&ParameterType ({Errors}{@errcode}) OPTIONAL
}

ROS {InvokeId:InvokeIdSet, OPERATION:Invokable, OPERATION:Returnable} ::= 
   CHOICE {
   invoke [1] Invoke {{InvokeIdSet}, {Invokable} },
   returnResult [2] ReturnResult {{Returnable} },
   returnError [3] ReturnError {{Errors{{Returnable}}} },
   reject [4] Reject
}

Bind {OPERATION:operation} ::= CHOICE {
   bind-invoke [16] OPERATION.&ArgumentType ({operation}),
   bind-result [17] OPERATION.&ResultType ({operation}),
   bind-error [18] OPERATION.&Errors.&ParameterType ({operation})
}

Unbind {OPERATION:operation} ::= CHOICE {
   unbind-invoke [19] OPERATION.&ArgumentType ({operation}),
   unbind-result [20] OPERATION.&ResultType ({operation}),
   unbind-error [21] OPERATION.&Errors.&ParameterType ({operation})
}

-- Parameterized info object set assignments

Errors {OPERATION:Operations} ERROR ::= {Operations.&Errors}

-- Productions

GeneralProblem ::= INTEGER

InvokeProblem ::= INTEGER

ReturnResultProblem ::= INTEGER

ReturnErrorProblem ::= INTEGER

RejectProblem ::= INTEGER

InvokeId ::= CHOICE {
   present INTEGER,
   absent NULL
}

Reject ::= SEQUENCE {
   invokeId InvokeId,
   problem CHOICE {
      general [0] GeneralProblem,
      invoke [1] InvokeProblem,
      returnResult [2] ReturnResultProblem,
      returnError [3] ReturnErrorProblem
   }
}

-- Value assignments

noInvokeId InvokeId ::= absent : NULL


END
