CSTA-get-auditory-apparatus-information
{ iso( 1) identified-organization( 3) icd-ecma( 12)
	standard( 0) csta3( 285) get-auditory-apparatus-information( 261) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
AuditoryApparatusID, AuditoryApparatusList FROM CSTA-physical-device-feature 
	{ iso( 1) identified-organization( 3) icd-ecma( 12)
		standard( 0) csta3( 285) physical-device-feature( 137) };

getAuditoryApparatusInformation OPERATION ::=
{	ARGUMENT 		GetAuditoryApparatusInformationArgument
	RESULT 			GetAuditoryApparatusInformationResult
	ERRORS 			{universalFailure }
	CODE			local: 261 }

GetAuditoryApparatusInformationArgument ::= SEQUENCE
{	device 				DeviceID,
	auditoryApparatus	 	AuditoryApparatusID			OPTIONAL,
	extensions 			CSTACommonArguments			OPTIONAL }

GetAuditoryApparatusInformationResult ::= SEQUENCE
{	auditoryApparatusList		AuditoryApparatusList,
	extensions 			CSTACommonArguments			OPTIONAL }

END -- of CSTA-get-auditory-apparatus-information
