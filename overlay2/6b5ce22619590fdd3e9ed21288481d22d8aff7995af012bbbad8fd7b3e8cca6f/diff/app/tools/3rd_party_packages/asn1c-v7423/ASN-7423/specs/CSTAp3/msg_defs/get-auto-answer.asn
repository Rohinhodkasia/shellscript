CSTA-get-auto-answer
	{ iso( 1) identified-organization( 3) icd-ecma( 12)
		standard( 0) csta3( 285) get-auto-answer( 305) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

getAutoAnswer OPERATION ::=
{	ARGUMENT 		GetAutoAnswerArgument
	RESULT 			GetAutoAnswerResult
	ERRORS 			{universalFailure }
	CODE			local: 305 }

GetAutoAnswerArgument ::= SEQUENCE
{	device 				DeviceID,
	extensions			CSTACommonArguments 			OPTIONAL }

GetAutoAnswerResult ::= SEQUENCE
{	autoAnswerOn			BOOLEAN,
	numberOfRings			INTEGER					OPTIONAL,
	extensions			CSTACommonArguments			OPTIONAL }

END -- of CSTA-get-auto-answer
