-- This file was generated by the Objective Systems ASN1C Compiler
-- (http://www.obj-sys.com).  Version: 6.8.A, Date: 15-Nov-2014.

SUPL-AUTH-RESP DEFINITIONS AUTOMATIC TAGS ::= BEGIN

IMPORTS

SPCSETKey, SPCTID, SPCSETKeylifetime
FROM Ver2-ULP-Components ;

-- Productions

SUPLAUTHRESP ::= SEQUENCE {
   sPCSETKey [0] SPCSETKey,
   sPCTID [1] SPCTID,
   sPCSETKeylifetime [2] SPCSETKeylifetime OPTIONAL,
   ...
}

END
