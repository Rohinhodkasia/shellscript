CSTA-call-detail-records-report
	{ iso( 1) identified-organization( 3) icd-ecma( 12)
		standard( 0) csta3( 285) call-detail-records-report( 361) }
DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
CDRCrossRefID, CDRInfo FROM CSTA-call-detail-record
	{ iso( 1) identified-organization( 3) icd-ecma( 12)
		standard( 0) csta3( 285) call-detail-record( 132) };

cDRReport OPERATION ::=
{ 	ARGUMENT		CDRReportArgument
	RESULT			CDRReportResult
	ERRORS			{universalFailure }
	CODE			local: 361 }

CDRReportArgument ::= SEQUENCE
{	cdrCrossRefID			CDRCrossRefID,  	     --corrected 06/2001
	numberOfRecordsSent		INTEGER (1..128),
	cdrInfo				CDRInfo,
	lastStoredCDRReportSent		BOOLEAN					OPTIONAL,
	extensions			CSTACommonArguments			OPTIONAL }

CDRReportResult ::= CHOICE
{	extensions			CSTACommonArguments,
	noData				NULL }

END  -- of CSTA-call-detail-records-report
