CSTA-start-location-tracking-session
	{ iso( 1) identified-organization( 3) icd-ecma( 12)
		standard( 0) csta3( 285) start-location-tracking-session( 536) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
DeviceID FROM CSTA-device-identifiers
	{ iso( 1) identified-organization( 3) icd-ecma( 12)
		standard( 0) csta3( 285) device-identifiers( 123) }
LocCrossRefID FROM CSTA-device-feature-types
	{ iso( 1) identified-organization( 3) icd-ecma( 12)
		standard( 0) csta3( 285) device-feature-types( 127) };

startLocationTrackingSession OPERATION ::=
{ 	ARGUMENT		StartLocationTrackingSessionArgument
	RESULT			StartLocationTrackingSessionResult
	ERRORS			{universalFailure }
	CODE			local: 536}

StartLocationTrackingSessionArgument ::= SEQUENCE
{	locDevice			DeviceID,
	collectionType			[0] IMPLICIT CollectionType		OPTIONAL,
	collectionInterval		[1] IMPLICIT INTEGER			OPTIONAL,
	maxCollections			[2] IMPLICIT INTEGER			OPTIONAL,
	collectionFilter		[3] IMPLICIT CollectionFilter		OPTIONAL,
	reportingType			[4] IMPLICIT ReportingType		OPTIONAL,
	reportingInterval		[5] IMPLICIT INTEGER			OPTIONAL,
	reportingCount			[6] IMPLICIT INTEGER			OPTIONAL,
	extensions			CSTACommonArguments			OPTIONAL }

StartLocationTrackingSessionResult ::= SEQUENCE 
{	locCrossRefID			LocCrossRefID,
	pidProfile			PIDProfile				OPTIONAL,
	extensions			CSTACommonArguments			OPTIONAL }

CollectionType ::= ENUMERATED
{	periodic			(0),
	periodicWithUpdates		(1),
	updatesOnly			(2) }

CollectionFilter ::= SEQUENCE
{	horizontalMovement		[0] IMPLICIT INTEGER			OPTIONAL,
	verticalMovement		[1] IMPLICIT INTEGER			OPTIONAL,
	civicAdressChange		[2] IMPLICIT INTEGER			OPTIONAL }

ReportingType ::= ENUMERATED
{	immediate			(0),
	periodic			(1),
	count				(2) }

PIDProfile ::= ENUMERATED
{	pidProfileOption1		(0),
	pidProfileOption2		(1) }

END -- of CSTA-start-location-tracking-session
