-- This file was generated by the Objective Systems ASN1C Compiler
-- (http://www.obj-sys.com).  Version: 7.4.2, Date: 15-Jun-2020.

PC5-RRC-Definitions DEFINITIONS AUTOMATIC TAGS ::= BEGIN

IMPORTS

RRC-TransactionIdentifier, SN-FieldLengthAM, SN-FieldLengthUM, 
   LogicalChannelIdentity, maxNrofSLRB-r16, maxNrofSL-QFIs-r16, 
   maxNrofSL-QFIsPerDest-r16, RSRP-Range, SL-MeasConfig-r16, SL-MeasId-r16
FROM NR-RRC-Definitions ;

-- Productions

SLRB-PC5-ConfigIndex-r16 ::= INTEGER (1..maxNrofSLRB-r16)

SL-PFI-r16 ::= INTEGER (1..64)

-- TAG-SCCH-MESSAGE-STOP
-- TAG-MASTERINFORMATIONBLOCKSIDELINK-START
MasterInformationBlockSidelink ::= SEQUENCE {
   sl-TDD-Config-r16 [0] BIT STRING  (SIZE (12)),
   inCoverage-r16 [1] BOOLEAN,
   directFrameNumber-r16 [2] BIT STRING  (SIZE (10)),
   slotIndex-r16 [3] BIT STRING  (SIZE (7)),
   reservedBits-r16 [4] BIT STRING  (SIZE (2))
}

SBCCH-SL-BCH-MessageType ::= CHOICE {
   c1 [0] EXPLICIT CHOICE {
      masterInformationBlockSidelink [0] MasterInformationBlockSidelink,
      spare3 [1] NULL,
      spare2 [2] NULL,
      spare1 [3] NULL
   },
   messageClassExtension [1] SEQUENCE {

   }
}

-- TAG-PC5-RRC-DEFINITIONS-STOP
-- TAG-SBCCH-SL-BCH-MESSAGE-START
SBCCH-SL-BCH-Message ::= SEQUENCE {
   message [0] EXPLICIT SBCCH-SL-BCH-MessageType
}

SL-MeasQuantityResult-r16 ::= SEQUENCE {
   sl-RSRP-r16 [0] RSRP-Range OPTIONAL,
   ...
}

SL-MeasResult-r16 ::= SEQUENCE {
   sl-ResultDMRS-r16 [0] SL-MeasQuantityResult-r16 OPTIONAL,
   ...
}

SL-MeasResults-r16 ::= SEQUENCE {
   sl-MeasId-r16 [0] SL-MeasId-r16,
   sl-MeasResult-r16 [1] SL-MeasResult-r16,
   ...
}

MeasurementReportSidelink-IEs-r16 ::= SEQUENCE {
   sl-measResults-r16 [0] SL-MeasResults-r16,
   lateNonCriticalExtension [1] OCTET STRING OPTIONAL,
   nonCriticalExtension [2] SEQUENCE {

   } OPTIONAL
}

-- TAG-MASTERINFORMATIONBLOCKSIDELINK-STOP
-- TAG-MEASUREMENTREPORTSIDELINK-START
MeasurementReportSidelink ::= SEQUENCE {
   criticalExtensions [0] EXPLICIT CHOICE {
      measurementReportSidelink-r16 [0] MeasurementReportSidelink-IEs-r16,
      criticalExtensionsFuture [1] SEQUENCE {

      }
   }
}

SL-SDAP-ConfigPC5-r16 ::= SEQUENCE {
   sl-MappedQoS-FlowsToAddList-r16 [0] SEQUENCE (SIZE (1..maxNrofSL-QFIsPerDest-r16)) OF SL-PFI-r16
       OPTIONAL, -- Need N
   sl-MappedQoS-FlowsToReleaseList-16 [1] SEQUENCE (SIZE (1..maxNrofSL-QFIsPerDest-r16)) OF SL-PFI-r16
       OPTIONAL,
   ...
}

SL-PDCP-ConfigPC5-r16 ::= SEQUENCE {
   sl-PDCP-SN-Size-r16 [0] ENUMERATED { len12bits(0), len18bits(1) } OPTIONAL, -- Need N
   sl-HeaderCompression-r16 [1] EXPLICIT CHOICE {
      notUsed-r16 [0] NULL,
      rohc-r16 [1] SEQUENCE {
         maxCID-r16 [0] INTEGER (1..16383) DEFAULT 15
      }
   },
   ...
}

SL-RLC-ConfigPC5-r16 ::= CHOICE {
   sl-AM-RLC-r16 [0] SEQUENCE {
      sl-SN-FieldLengthAM-r16 [0] SN-FieldLengthAM OPTIONAL,
      ...
   },
   sl-UM-Bi-Directional-RLC-r16 [1] SEQUENCE {
      sl-SN-FieldLengthUM-r16 [0] SN-FieldLengthUM OPTIONAL,
      ...
   },
   sl-UM-Uni-Directional-RLC-r16 [2] SEQUENCE {
      sl-SN-FieldLengthUM-r16 [0] SN-FieldLengthUM OPTIONAL,
      ...
   }
}

SL-LogicalChannelConfigPC5-r16 ::= SEQUENCE {
   sl-LogicalChannelIdentity-r16 [0] LogicalChannelIdentity,
   ...
}

SLRB-Config-r16 ::= SEQUENCE {
   slrb-PC5-ConfigIndex-r16 [0] SLRB-PC5-ConfigIndex-r16,
   sl-SDAP-ConfigPC5-r16 [1] SL-SDAP-ConfigPC5-r16 OPTIONAL, -- Need N
   sl-PDCP-ConfigPC5-r16 [2] SL-PDCP-ConfigPC5-r16 OPTIONAL, -- Need N
   sl-RLC-ConfigPC5-r16 [3] EXPLICIT SL-RLC-ConfigPC5-r16 OPTIONAL, -- Need N
   sl-MAC-LogicalChannelConfigPC5-r16 [4] SL-LogicalChannelConfigPC5-r16
       OPTIONAL,
   ...
}

SL-CSI-RS-Config-r16 ::= SEQUENCE {
   sl-CSI-RS-FreqAllocation-r16 [0] EXPLICIT CHOICE {
      sl-OneAntennaPort-r16 [0] BIT STRING  (SIZE (12)),
      sl-TwoAntennaPort-r16 [1] BIT STRING  (SIZE (6))
   } OPTIONAL, -- Need N
   sl-CSI-RS-FirstSymbol-r16 [1] ENUMERATED { ffs(0) } OPTIONAL,
   ...
}

RRCReconfigurationSidelink-IEs-r16 ::= SEQUENCE {
   slrb-ConfigToAddModList-r16 [0] SEQUENCE (SIZE (1..maxNrofSLRB-r16)) OF SLRB-Config-r16
       OPTIONAL,
   slrb-ConfigToReleaseList-r16 [1] SEQUENCE (SIZE (1..maxNrofSLRB-r16)) OF 
      SLRB-PC5-ConfigIndex-r16 OPTIONAL,
   sl-MeasConfig-r16 [2] SL-MeasConfig-r16 OPTIONAL,
   sl-CSI-RS-Config-r16 [3] SL-CSI-RS-Config-r16 OPTIONAL,
   lateNonCriticalExtension [4] OCTET STRING OPTIONAL,
   nonCriticalExtension [5] SEQUENCE {

   } OPTIONAL
}

-- TAG-MEASUREMENTREPORTSIDELINK-STOP
-- TAG-RRCRECONFIGURATIONSIDELINK-START
RRCReconfigurationSidelink ::= SEQUENCE {
   rrc-TransactionIdentifier-r16 [0] RRC-TransactionIdentifier,
   criticalExtensions [1] EXPLICIT CHOICE {
      rrcReconfigurationSidelink-r16 [0] RRCReconfigurationSidelink-IEs-r16,
      criticalExtensionsFuture [1] SEQUENCE {

      }
   }
}

RRCReconfigurationCompleteSidelink-IEs-r16 ::= SEQUENCE {
   lateNonCriticalExtension [0] OCTET STRING OPTIONAL,
   nonCriticalExtension [1] SEQUENCE {

   } OPTIONAL
}

-- TAG-RRCRECONFIGURATIONSIDELINK-STOP
-- TAG-RRCRECONFIGURATIONCOMPLETESIDELINK-START
RRCReconfigurationCompleteSidelink ::= SEQUENCE {
   rrc-TransactionIdentifier-r16 [0] RRC-TransactionIdentifier,
   criticalExtensions [1] EXPLICIT CHOICE {
      rrcReconfigurationCompleteSidelink-r16 [0] 
         RRCReconfigurationCompleteSidelink-IEs-r16,
      criticalExtensionsFuture [1] SEQUENCE {

      }
   }
}

RRCReconfigurationFailureSidelink-IEs-r16 ::= SEQUENCE {
   lateNonCriticalExtension [0] OCTET STRING OPTIONAL,
   nonCriticalExtension [1] SEQUENCE {

   } OPTIONAL
}

-- TAG-RRCRECONFIGURATIONCOMPLETESIDELINK-STOP
-- TAG-RRCRECONFIGURATIONFAILURESIDELINK-START
RRCReconfigurationFailureSidelink ::= SEQUENCE {
   rrc-TransactionIdentifier-r16 [0] RRC-TransactionIdentifier,
   criticalExtensions [1] EXPLICIT CHOICE {
      rrcReconfigurationFailureSidelink-r16 [0] 
         RRCReconfigurationFailureSidelink-IEs-r16,
      criticalExtensionsFuture [1] SEQUENCE {

      }
   }
}

UECapabilityEnquirySidelink-IEs-r16 ::= SEQUENCE {
   ueCapabilityInformationSidelink-r16 [0] OCTET STRING OPTIONAL,
   lateNonCriticalExtension [1] OCTET STRING OPTIONAL,
   nonCriticalExtension [2] SEQUENCE {

   } OPTIONAL
}

-- TAG-RRCRECONFIGURATIONFAILURESIDELINK-STOP
-- TAG-UECAPABILITYENQUIRYSIDELINK-START
UECapabilityEnquirySidelink ::= SEQUENCE {
   rrc-TransactionIdentifier-r16 [0] RRC-TransactionIdentifier,
   criticalExtensions [1] EXPLICIT CHOICE {
      ueCapabilityEnquirySidelink-r16 [0] UECapabilityEnquirySidelink-IEs-r16,
      criticalExtensionsFuture [1] SEQUENCE {

      }
   }
}

UECapabilityInformationSidelink-IEs-r16 ::= SEQUENCE {
 -- FFS on the details
   lateNonCriticalExtension [0] OCTET STRING OPTIONAL,
   nonCriticalExtension [1] SEQUENCE {

   } OPTIONAL
}

-- TAG-UECAPABILITYENQUIRYSIDELINK-STOP
-- TAG-UECAPABILITYINFORMATIONSIDELINK-START
UECapabilityInformationSidelink ::= SEQUENCE {
   rrc-TransactionIdentifier-r16 [0] RRC-TransactionIdentifier,
   criticalExtensions [1] EXPLICIT CHOICE {
      ueCapabilityInformationSidelink-r16 [0] 
         UECapabilityInformationSidelink-IEs-r16,
      criticalExtensionsFuture [1] SEQUENCE {

      }
   }
}

SCCH-MessageType ::= CHOICE {
   c1 [0] EXPLICIT CHOICE {
      measurementReportSidelink [0] MeasurementReportSidelink,
      rrcReconfigurationSidelink [1] RRCReconfigurationSidelink,
      rrcReconfigurationCompleteSidelink [2] RRCReconfigurationCompleteSidelink
         ,
      rrcReconfigurationFailureSidelink [3] RRCReconfigurationFailureSidelink,
      ueCapabilityEnquirySidelink [4] UECapabilityEnquirySidelink,
      ueCapabilityInformationSidelink [5] UECapabilityInformationSidelink,
      spare2 [6] NULL,
      spare1 [7] NULL
   },
   messageClassExtension [1] SEQUENCE {

   }
}

-- TAG-SBCCH-SL-BCH-MESSAGE-STOP
-- TAG-SCCH-MESSAGE-START
SCCH-Message ::= SEQUENCE {
   message [0] EXPLICIT SCCH-MessageType
}

END
