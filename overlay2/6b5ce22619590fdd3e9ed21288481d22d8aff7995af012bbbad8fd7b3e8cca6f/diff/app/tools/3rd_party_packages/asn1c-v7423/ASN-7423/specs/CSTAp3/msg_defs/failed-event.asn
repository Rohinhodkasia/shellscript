CSTA-failed-event
	{ iso( 1) identified-organization( 3) icd-ecma( 12)
		standard( 0) csta3( 285) failed-event( 28) }

DEFINITIONS ::=
BEGIN

IMPORTS 

-- Data Types --
EventCause FROM CSTA-event-causes
	{ iso( 1) identified-organization( 3) icd-ecma( 12)
		standard( 0) csta3( 285) event-causes( 121) }
SubjectDeviceID, CallingDeviceID, CalledDeviceID, RedirectionDeviceID, 
	AssociatedCalledDeviceID, AssociatedCallingDeviceID, 
	NetworkCalledDeviceID, NetworkCallingDeviceID 
	FROM CSTA-device-identifiers
		{ iso( 1) identified-organization( 3) icd-ecma( 12)
			standard( 0) csta3( 285) device-identifiers( 123) }
ConnectionID FROM CSTA-call-connection-identifiers
	{ iso( 1) identified-organization( 3) icd-ecma( 12)
		standard( 0) csta3( 285) call-connection-identifiers( 124) }
LocalConnectionState FROM CSTA-connection-states
	{ iso( 1) identified-organization( 3) icd-ecma( 12)
		standard( 0) csta3( 285) connection-states( 125) }
CorrelatorData, UserData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) }
CallCharacteristics, CallLinkageData, ServicesPermitted FROM CSTA-call-control 
	{ iso( 1) identified-organization( 3) icd-ecma( 12)
		standard( 0) csta3( 285) call-control( 130) }
LocationInfoList FROM CSTA-call-control
	{ iso( 1) identified-organization( 3) icd-ecma( 12)
		standard( 0) csta3( 285) call-control( 130) }
LanguagePreferences, SubjectOfCall, MessageInfo,
DeviceHistory FROM CSTA-device-feature-types
	{ iso( 1) identified-organization( 3) icd-ecma( 12)
		standard( 0) csta3( 285) device-feature-types( 127) }
ConnectionInformation, MediaCallCharacteristics FROM CSTA-media-services
	{ iso( 1) identified-organization( 3) icd-ecma( 12)
		standard( 0) csta3( 285) media-services( 136) };

FailedEvent ::= SEQUENCE
{	failedConnection		ConnectionID,
	failingDevice			SubjectDeviceID,
	callingDevice			CallingDeviceID,
	calledDevice			CalledDeviceID,
	lastRedirectionDevice		RedirectionDeviceID,
	originatingNIDConnection	ConnectionID				OPTIONAL,
	localConnectionInfo		LocalConnectionState			OPTIONAL,
	correlatorData			[ 0] IMPLICIT CorrelatorData		OPTIONAL,
	userData			UserData				OPTIONAL,
	cause				EventCause,
	servicesPermitted		[ 1] IMPLICIT ServicesPermitted		OPTIONAL,
	networkCallingDevice		NetworkCallingDeviceID			OPTIONAL,
	networkCalledDevice		NetworkCalledDeviceID			OPTIONAL,
	associatedCallingDevice		AssociatedCallingDeviceID		OPTIONAL,
	associatedCalledDevice		AssociatedCalledDeviceID		OPTIONAL,
	mediaCallCharacteristics 	[ 2] IMPLICIT MediaCallCharacteristics	OPTIONAL,
	callCharacteristics		[ 3] IMPLICIT CallCharacteristics	OPTIONAL,
	failedConnectionInfo 		[ 4] IMPLICIT ConnectionInformation	OPTIONAL,
					 	                     --corrected 06/2001
	callLinkageData			[ 5] IMPLICIT CallLinkageData		OPTIONAL,
	subjectOfCall			[ 6] IMPLICIT SubjectOfCall		OPTIONAL,
	messageInfo			[ 7] IMPLICIT MessageInfo		OPTIONAL,
	languagePreferences		[ 8] IMPLICIT LanguagePreferences	OPTIONAL,
	deviceHistory			[ 9] IMPLICIT DeviceHistory		OPTIONAL,
	locationInfo			[10] IMPLICIT LocationInfoList		OPTIONAL,
	extensions			CSTACommonArguments			OPTIONAL }

END  -- of CSTA-failed-event
