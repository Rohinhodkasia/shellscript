-- This file was generated by the Objective Systems ASN1C Compiler
-- (http://www.obj-sys.com).  Version: 7.4.2, Date: 15-Jun-2020.

NR-Sidelink-Preconf DEFINITIONS AUTOMATIC TAGS ::= BEGIN

IMPORTS

SL-CBR-CommonTxConfigList-r16, SL-FreqConfigCommon-r16, 
   SL-RadioBearerConfig-r16, SL-RLC-BearerConfig-r16, 
   SL-EUTRA-AnchorCarrierFreqList-r16, SL-NR-AnchorCarrierFreqList-r16, 
   SL-MeasConfigCommon-r16, SL-UE-SelectedConfig-r16, TDD-UL-DL-ConfigCommon, 
   maxNrofFreqSL-r16, maxNrofSLRB-r16, maxSL-LCID-r16
FROM NR-RRC-Definitions ;

-- Productions

SL-PreconfigGeneral-r16 ::= SEQUENCE {
   sl-TDD-Config-r16 [0] TDD-UL-DL-ConfigCommon OPTIONAL, -- Need R
   reservedBits-r16 [1] BIT STRING  (SIZE (2)) OPTIONAL,
   ...
}

SidelinkPreconfigNR-r16 ::= SEQUENCE {
   sl-PreconfigFreqInfoList-r16 [0] SEQUENCE (SIZE (1..maxNrofFreqSL-r16)) OF 
      SL-FreqConfigCommon-r16 OPTIONAL, -- Need R
   sl-PreconfigNR-AnchorCarrierFreqList-r16 [1] SL-NR-AnchorCarrierFreqList-r16
       OPTIONAL, -- Need R
   sl-PreconfigEUTRA-AnchorCarrierFreqList-r16 [2] 
      SL-EUTRA-AnchorCarrierFreqList-r16 OPTIONAL, -- Need R
   sl-RadioBearerPreConfigList-r16 [3] SEQUENCE (SIZE (1..maxNrofSLRB-r16)) OF 
      SL-RadioBearerConfig-r16 OPTIONAL, -- Need R
   sl-RLC-BearerPreConfigList-r16 [4] SEQUENCE (SIZE (1..maxSL-LCID-r16)) OF 
      SL-RLC-BearerConfig-r16 OPTIONAL, -- Need R
   sl-MeasPreConfig-r16 [5] SL-MeasConfigCommon-r16 OPTIONAL, -- Need R
   sl-OffsetDFN-r16 [6] INTEGER (0..1000) OPTIONAL, -- Need R
   t400-r16 [7] ENUMERATED { ms100(0), ms200(1), ms300(2), ms400(3), ms600(4), 
      ms1000(5), ms1500(6), ms2000(7) } OPTIONAL, -- Need R
   sl-SSB-PriorityNR-r16 [8] INTEGER (1..8) OPTIONAL, -- Need R
   sl-PreconfigGeneral-r16 [9] SL-PreconfigGeneral-r16 OPTIONAL, -- Need R
   sl-UE-SelectedPreConfig-r16 [10] SL-UE-SelectedConfig-r16 OPTIONAL,
   ...
}

-- TAG-NR-SIDELINK-PRECONF-DEFINITIONS-STOP
-- TAG-SL-PRECONFIGURATIONNR-START
SL-PreconfigurationNR-r16 ::= SEQUENCE {
   sidelinkPreconfigNR-r16 [0] SidelinkPreconfigNR-r16,
   ...
}

END
