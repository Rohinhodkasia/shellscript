-- This file was generated by the Objective Systems ASN1C Compiler
-- (http://www.obj-sys.com).  Version: 6.8.A, Date: 18-Nov-2014.

SUPL-NOTIFY-RESPONSE DEFINITIONS AUTOMATIC TAGS ::= BEGIN

IMPORTS

Ver3-SUPL-NOTIFY-RESPONSE-extension
FROM ULP-Version-3-message-extensions ;

-- Productions

NotificationResponse ::= ENUMERATED { allowed(0), notAllowed(1), ... }

Ver2-SUPLNOTIFYRESPONSE ::= SEQUENCE {
   notificationResponse [0] NotificationResponse OPTIONAL,
   ...,
   ver3-SUPL-NOTIFY-RESPONSE-extension [1] Ver3-SUPL-NOTIFY-RESPONSE-extension
       OPTIONAL
}

END
