CSTA-switching-function-capabilities-changed
	{ iso( 1) identified-organization( 3) icd-ecma( 12)
		standard( 0) csta3( 285) switching-function-capabilities-changed( 212) }

DEFINITIONS ::=
BEGIN

IMPORTS
OPERATION, ERROR FROM Remote-Operations-Information-Objects
	{joint-iso-itu-t remote-operations(4) informationObjects(5) version1(0) }

-- Data Types --
universalFailure FROM CSTA-error-definition
	{ iso( 1) identified-organization( 3) icd-ecma( 12)
		standard( 0) csta3( 285) error-definition( 120) }
SysStatRegisterID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

swFunctionCapsChanged OPERATION ::=
{ 	ARGUMENT 		SwFunctionCapsChangedArg
	RESULT 			SwFunctionCapsChangedRes
	ERRORS 			{universalFailure }
	CODE 			local: 212 }

SwFunctionCapsChangedArg ::= SEQUENCE
{ 	sysStatRegisterID 		SysStatRegisterID 		OPTIONAL,
	extensions 			CSTACommonArguments 		OPTIONAL }

SwFunctionCapsChangedRes ::= CHOICE
{ 	extensions 			CSTACommonArguments,
	noData 				NULL }

END -- of CSTA-switching-function-capabilities-changed
