--
-- The following ASN.1 specification defines the abstract syntax for 
--
--        Data Record Format Version 03 
--                           Release 10
--
-- The specification is structured as follows:
--   (1) structure of the Tap batch
--   (2) defintition of the individual Tap 'records' 
--   (3) Tap data items and groups of data items used within (2)
--   (4) Common, non-Tap data types
--   (5) Tap data items for content charging
--
-- It is mainly a translation from the logical structure
-- diagrams. Where appropriate, names used within the 
-- logical structure diagrams have been shortened.
-- For repeating data items the name as used within the logical
-- structure have been extended by adding 'list' or 'table'
-- (in some instances).
--


TAP-0310  DEFINITIONS IMPLICIT TAGS  ::= 

BEGIN 

--
-- Structure of a Tap batch 
--

DataInterChange ::= CHOICE 
{
    transferBatch TransferBatch, 
    notification  Notification
}

-- Batch Control Information must always, both logically and physically, be the
-- first group/item within Transfer Batch - this ensures that the TAP release 
-- version can be readily identified.  Any new groups/items required may be 
-- inserted at any point after Batch Control Information

TransferBatch ::= [APPLICATION 1] SEQUENCE
{
    batchControlInfo       BatchControlInfo            OPTIONAL,
    accountingInfo         AccountingInfo              OPTIONAL,
    networkInfo            NetworkInfo                 OPTIONAL,
    vasInfo                VasInfoList                 OPTIONAL,
    messageDescriptionInfo MessageDescriptionInfoList  OPTIONAL,
    callEventDetails       CallEventDetailList         OPTIONAL,
    auditControlInfo       AuditControlInfo            OPTIONAL
}

-- The logical and physical structures must not be changed up to and including the 
-- Release Version Number - this ensures that the TAP release version can be readily 
-- identified.  Any new groups/items required may be inserted at any point after 
-- Release Version Number

Notification ::= [APPLICATION 2] SEQUENCE
{
    sender                      Sender                     OPTIONAL,
    recipient                   Recipient                  OPTIONAL,
    fileSequenceNumber          FileSequenceNumber         OPTIONAL,
    rapFileSequenceNumber       RapFileSequenceNumber      OPTIONAL,
    fileCreationTimeStamp       FileCreationTimeStamp      OPTIONAL,
    fileAvailableTimeStamp      FileAvailableTimeStamp     OPTIONAL,
    transferCutOffTimeStamp     TransferCutOffTimeStamp    OPTIONAL,
    specificationVersionNumber  SpecificationVersionNumber OPTIONAL,
    releaseVersionNumber        ReleaseVersionNumber       OPTIONAL,
    fileTypeIndicator           FileTypeIndicator          OPTIONAL,
    operatorSpecInformation     OperatorSpecInfoList       OPTIONAL
}

CallEventDetailList ::=  [APPLICATION 3] SEQUENCE OF CallEventDetail

CallEventDetail ::= CHOICE
{
    mobileOriginatedCall   MobileOriginatedCall,
    mobileTerminatedCall   MobileTerminatedCall,
    supplServiceEvent      SupplServiceEvent,
    serviceCentreUsage     ServiceCentreUsage,
    valueAddedService      ValueAddedService,
    gprsCall               GprsCall,
    contentTransaction     ContentTransaction,
    locationService        LocationService
}

--
-- Structure of the individual Tap records
--

-- The logical and physical structures must not be changed up to and including the 
-- Release Version Number - this ensures that the TAP release version can be readily 
-- identified.  Any new groups/items required may be inserted at any point after 
-- Release Version Number.
-- Please note that this implies also that the 'SEQUENCE OF' construct in the ASN.1 
-- specification cannot be replaced by 'SET OF' within the Transfer Batch, 
-- Notification and Batch Control Information.

BatchControlInfo ::= [APPLICATION 4] SEQUENCE
{
    sender                      Sender                      OPTIONAL,
    recipient                   Recipient                   OPTIONAL,
    fileSequenceNumber          FileSequenceNumber          OPTIONAL,
    fileCreationTimeStamp       FileCreationTimeStamp       OPTIONAL,
    transferCutOffTimeStamp     TransferCutOffTimeStamp     OPTIONAL,
    fileAvailableTimeStamp      FileAvailableTimeStamp      OPTIONAL,
    specificationVersionNumber  SpecificationVersionNumber  OPTIONAL,
    releaseVersionNumber        ReleaseVersionNumber        OPTIONAL,
    fileTypeIndicator           FileTypeIndicator           OPTIONAL,
    rapFileSequenceNumber       RapFileSequenceNumber       OPTIONAL,
    operatorSpecInformation     OperatorSpecInfoList        OPTIONAL
}

AccountingInfo ::= [APPLICATION 5] SEQUENCE
{
    taxation                    TaxationList       OPTIONAL,
    discounting                 DiscountingList    OPTIONAL,
    localCurrency               LocalCurrency      OPTIONAL,
    tapCurrency                 TapCurrency        OPTIONAL,
    currencyConversionInfo      CurrencyConversionList OPTIONAL,
    tapDecimalPlaces            TapDecimalPlaces   OPTIONAL
}

NetworkInfo ::= [APPLICATION 6] SEQUENCE
{
    utcTimeOffsetInfo           UtcTimeOffsetInfoList OPTIONAL,
    recEntityInfo               RecEntityInfoList     OPTIONAL,
    networkType                 NetworkType           OPTIONAL,
    calledNumAnalysis           CalledNumAnalysisList OPTIONAL
}

VasInfoList ::= [APPLICATION 7]  SEQUENCE OF VasInformation

MessageDescriptionInfoList ::= [APPLICATION 8] 
                           SEQUENCE OF MessageDescriptionInformation

MobileOriginatedCall ::= [APPLICATION 9] SEQUENCE
{
    basicCallInformation        MoBasicCallInformation    OPTIONAL,
    locationInformation         LocationInformation       OPTIONAL,
    equipmentInformation        EquipmentInformation      OPTIONAL,
    basicServiceUsedList        BasicServiceUsedList      OPTIONAL,
    supplServiceUsedList        SupplServiceUsedList      OPTIONAL,
    camelServiceUsed            CamelServiceUsed          OPTIONAL,
    valueAddedServiceUsedList   ValueAddedServiceUsedList OPTIONAL,
    dualServiceRequested        DualServiceCode           OPTIONAL,
    operatorSpecInformation     OperatorSpecInfoList      OPTIONAL
}    


MobileTerminatedCall ::= [APPLICATION 10] SEQUENCE
{
    basicCallInformation        MtBasicCallInformation    OPTIONAL,
    locationInformation         LocationInformation       OPTIONAL,
    equipmentInformation        EquipmentInformation      OPTIONAL,
    basicServiceUsedList        BasicServiceUsedList      OPTIONAL,
    supplServiceUsedList        SupplServiceUsedList      OPTIONAL,
    camelServiceUsed            CamelServiceUsed          OPTIONAL,
    valueAddedServiceUsedList   ValueAddedServiceUsedList OPTIONAL,
    dualServiceRequested        DualServiceCode           OPTIONAL,
    operatorSpecInformation     OperatorSpecInfoList      OPTIONAL
}    


SupplServiceEvent ::= [APPLICATION 11] SEQUENCE
{
    fraudMonitorIndicator       FraudMonitorIndicator   OPTIONAL,
    chargeableSubscriber        ChargeableSubscriber    OPTIONAL,
    rapFileSequenceNumber       RapFileSequenceNumber   OPTIONAL,
    networkType                 NetworkType             OPTIONAL,
    locationInformation         LocationInformation     OPTIONAL,
    equipmentInformation        EquipmentInformation    OPTIONAL,
    supplServiceUsed            SupplServiceUsed        OPTIONAL,
    simToolkitIndicator         SimToolkitIndicator     OPTIONAL,
    operatorSpecInformation     OperatorSpecInfoList    OPTIONAL
}


ServiceCentreUsage ::= [APPLICATION 12] SEQUENCE
{
    fraudMonitorIndicator       FraudMonitorIndicator   OPTIONAL,
    basicInformation            ScuBasicInformation     OPTIONAL,
    rapFileSequenceNumber       RapFileSequenceNumber   OPTIONAL,
    networkType                 NetworkType             OPTIONAL,
    servingNetwork              ServingNetwork          OPTIONAL,
    recEntityCode               RecEntityCode           OPTIONAL,
    chargeInformation           ChargeInformation       OPTIONAL,
    scuChargeType               ScuChargeType           OPTIONAL,
    scuTimeStamps               ScuTimeStamps           OPTIONAL,
    operatorSpecInformation     OperatorSpecInfoList    OPTIONAL
}

ValueAddedService ::= [APPLICATION 13] SEQUENCE
{
    fraudMonitorIndicator       FraudMonitorIndicator      OPTIONAL,
    chargeableSubscriber        ScuVasChargeableSubscriber OPTIONAL,
    rapFileSequenceNumber       RapFileSequenceNumber      OPTIONAL,
    networkType                 NetworkType                OPTIONAL,
    servingNetwork              ServingNetwork             OPTIONAL,
    valueAddedServiceUsed       ValueAddedServiceUsed      OPTIONAL,
    operatorSpecInformation     OperatorSpecInfoList       OPTIONAL
}

GprsCall ::= [APPLICATION 14] SEQUENCE
{
    typeOfControllingNode       TypeOfControllingNode     OPTIONAL,
    gprsBasicCallInformation    GprsBasicCallInformation  OPTIONAL,
    gprsLocationInformation     GprsLocationInformation   OPTIONAL,
    equipmentInformation        EquipmentInformation      OPTIONAL,
    gprsServiceUsed             GprsServiceUsed           OPTIONAL,
    camelServiceUsed            CamelServiceUsed          OPTIONAL,
    valueAddedServiceUsedList   ValueAddedServiceUsedList OPTIONAL,
    operatorSpecInformation     OperatorSpecInfoList      OPTIONAL
}

ContentTransaction ::= [APPLICATION 17] SEQUENCE
{
    contentTransactionBasicInfo ContentTransactionBasicInfo OPTIONAL,
    chargedPartyInformation     ChargedPartyInformation     OPTIONAL,
    servingPartiesInformation   ServingPartiesInformation   OPTIONAL,
    contentServiceUsed          ContentServiceUsedList      OPTIONAL,
    operatorSpecInformation     OperatorSpecInfoList        OPTIONAL
}

LocationService ::= [APPLICATION 297] SEQUENCE
{
    fraudMonitorIndicator         FraudMonitorIndicator OPTIONAL,
    rapFileSequenceNumber         RapFileSequenceNumber OPTIONAL,
    recEntityCode                 RecEntityCode OPTIONAL,
    callReference                 CallReference OPTIONAL,
    trackingCustomerInformation   TrackingCustomerInformation OPTIONAL,
    lCSSPInformation              LCSSPInformation OPTIONAL,
    trackedCustomerInformation    TrackedCustomerInformation OPTIONAL,
    locationServiceUsage          LocationServiceUsage OPTIONAL,
    operatorSpecInformation       OperatorSpecInfoList        OPTIONAL
}

AuditControlInfo ::= [APPLICATION 15] SEQUENCE
{
    earliestCallTimeStamp       EarliestCallTimeStamp       OPTIONAL,
    latestCallTimeStamp         LatestCallTimeStamp         OPTIONAL,
    totalChargeValueList        TotalChargeValueList        OPTIONAL,
    totalTaxRefund              TotalTaxRefund              OPTIONAL,
    totalTaxValue               TotalTaxValue               OPTIONAL,
    totalDiscountValue          TotalDiscountValue          OPTIONAL,
    totalDiscountRefund         TotalDiscountRefund         OPTIONAL,
    totalAdvisedChargeValueList TotalAdvisedChargeValueList OPTIONAL,
    callEventDetailsCount       CallEventDetailsCount       OPTIONAL,
    operatorSpecInformation     OperatorSpecInfoList        OPTIONAL
}


-- 
-- Tap data items and groups of data items
--

ThreeGcamelDestination ::= CHOICE
{
    camelDestinationNumber    AddressStringDigits,
    gprsDestination           GprsDestination
}

AccessPointNameNI ::= [APPLICATION 261] AsciiString --(SIZE(1..63))

AccessPointNameOI ::= [APPLICATION 262] AsciiString --(SIZE(1..37))

AddressStringDigits ::= [APPLICATION 33] BCDString

AgeOfLocation ::= [APPLICATION 396] INTEGER

AiurRequested ::= [APPLICATION 34] INTEGER

BasicHSCSDParameters ::= [APPLICATION 35] SEQUENCE
{
    maxNumberOfChannels         NumberOfChannels         OPTIONAL,
    channelCodingAcceptableList ChannelCodingAcceptableList OPTIONAL,
    channelCodingUsed           ChannelCoding            OPTIONAL,
    numberOfChannelsUsed        NumberOfChannelsUsed     OPTIONAL
}

BasicService ::= [APPLICATION 36] SEQUENCE
{
    serviceCode                 BasicServiceCode       OPTIONAL,
    radioChannelRequested       RadioChannelRequested  OPTIONAL,
    radioChannelUsed            RadioChannelUsed       OPTIONAL,
    speechVersionRequested      SpeechVersionRequested OPTIONAL,
    speechVersionUsed           SpeechVersionUsed      OPTIONAL,
    transparencyIndicator       TransparencyIndicator  OPTIONAL,
    fnur                        Fnur                   OPTIONAL,
    aiurRequested               AiurRequested          OPTIONAL,
    userProtocolIndicator       UserProtocolIndicator  OPTIONAL
}

BasicServiceCode ::= CHOICE 
{
    teleServiceCode      TeleServiceCode,
    bearerServiceCode    BearerServiceCode
}

BasicServiceCodeList ::= [APPLICATION 37] SEQUENCE OF BasicServiceCode

BasicServiceUsedList ::= [APPLICATION 38] SEQUENCE OF BasicServiceUsed

BasicServiceUsed ::= [APPLICATION 39] SEQUENCE
{
    basicService                BasicService          OPTIONAL,
    chargingTimeStamp           ChargingTimeStamp     OPTIONAL,
    chargeInformationList       ChargeInformationList OPTIONAL,
    dataVolumeReference         DataVolumeReference   OPTIONAL,
    hSCSDInformation             HSCSDInformation     OPTIONAL
}

BearerServiceCode ::= [APPLICATION 40] HexString --(SIZE(2))

CalledNumAnalysis ::= [APPLICATION 246] SEQUENCE
{
    calledNumAnalysisCode       CalledNumAnalysisCode OPTIONAL,
    countryCodeTable            CountryCodeList       OPTIONAL,
    iacTable                    IacList               OPTIONAL
}

CalledNumAnalysisCode ::= [APPLICATION 247] Code

CalledNumAnalysisList ::= [APPLICATION 249] SEQUENCE OF
CalledNumAnalysis

CalledPlace ::= [APPLICATION 42] AsciiString

CallOriginator ::= [APPLICATION 41]  SEQUENCE
{
    callingNumber               AddressStringDigits   OPTIONAL,
    clirIndicator               ClirIndicator         OPTIONAL
}

CallEventDetailsCount ::= [APPLICATION 43] INTEGER 

CallEventStartTimeStamp ::= [APPLICATION 44] DateTime

CallReference ::= [APPLICATION 45] OCTET STRING --(SIZE(1..8))

CalledRegion ::= [APPLICATION 46] AsciiString

CallTypeGroup ::= [APPLICATION 258] SEQUENCE
{
    callTypeLevel1      CallTypeLevel1           OPTIONAL,
    callTypeLevel2      CallTypeLevel2           OPTIONAL,
    callTypeLevel3      CallTypeLevel3           OPTIONAL,
    calledCountryCode   CalledCountryCode        OPTIONAL
}

CallTypeLevel1 ::= [APPLICATION 259] INTEGER

CallTypeLevel2 ::= [APPLICATION 255] INTEGER

CallTypeLevel3 ::= [APPLICATION 256] INTEGER

CalledCountryCode ::= [APPLICATION 257] AsciiString


CamelCallReference ::= [APPLICATION 49] SEQUENCE
{
    mscAddress          AddressStringDigits      OPTIONAL,
    callReferenceNumber CamelCallReferenceNumber OPTIONAL
}

CamelCallReferenceNumber ::= [APPLICATION 50] HexString --(SIZE(2..16))

CamelInitiatedCFIndicator ::= [APPLICATION 52]  INTEGER

CamelModification ::= [APPLICATION 53] INTEGER

CamelModificationList ::= [APPLICATION 54] SEQUENCE OF CamelModification

CamelServerAddress ::= [APPLICATION 399] AddressStringDigits

CamelServiceKey ::= [APPLICATION 55] INTEGER

CamelServiceLevel ::= [APPLICATION 56] INTEGER

CamelServiceUsed ::= [APPLICATION 57] SEQUENCE
{
    camelServerAddress          CamelServerAddress           OPTIONAL,
    camelServiceLevel           CamelServiceLevel            OPTIONAL,
    camelServiceKey             CamelServiceKey              OPTIONAL,
    defaultCallHandling         DefaultCallHandlingIndicator OPTIONAL,
    camelCallReference          CamelCallReference           OPTIONAL,
    camelChargeInformation      ChargeInformation            OPTIONAL,
    camelInitiatedCFIndicator   CamelInitiatedCFIndicator    OPTIONAL,
    camelModificationList       CamelModificationList        OPTIONAL,
    threeGcamelDestination      ThreeGcamelDestination       OPTIONAL,
    cseInformation              CseInformation               OPTIONAL
}

CauseForTerm ::= [APPLICATION 58] INTEGER

CellId ::= [APPLICATION 59] INTEGER 

ChannelCoding ::= [APPLICATION 60] INTEGER

ChannelCodingAcceptableList ::= [APPLICATION 61]
                                   SEQUENCE OF ChannelCoding

Charge ::= [APPLICATION 62] AbsoluteAmount

ChargeDetail ::= [APPLICATION 63] SEQUENCE
{

    chargeType              ChargeType         OPTIONAL,
    charge                  Charge             OPTIONAL,
    chargeableUnits         ChargeableUnits    OPTIONAL,
    chargedUnits            ChargedUnits       OPTIONAL,
    chargeDetailTimeStamp   ChargingTimeStamp  OPTIONAL,
    dayCategory             DayCategory        OPTIONAL,
    dayCategorySubtype      DayCategorySubtype OPTIONAL,
    timeBand                TimeBand           OPTIONAL,
    timeBandSubtype         TimeBandSubtype    OPTIONAL,
    multiRateIndicator      MultiRateIndicator OPTIONAL
}

ChargeDetailList ::= [APPLICATION 64] SEQUENCE OF ChargeDetail

ChargeableSubscriber ::= CHOICE 
{
    simChargeableSubscriber SimChargeableSubscriber,
    minChargeableSubscriber MinChargeableSubscriber
}

ChargeableUnits ::= [APPLICATION 65]  INTEGER

ChargedItem ::= [APPLICATION 66]  AsciiString --(SIZE(1))

ChargedPartyStatus ::= [APPLICATION 67] INTEGER 

ChargedUnits ::= [APPLICATION 68]  INTEGER 

ChargeInformation ::= [APPLICATION 69] SEQUENCE
{
    chargedItem         ChargedItem         OPTIONAL,
    exchangeRateCode    ExchangeRateCode    OPTIONAL,
    callTypeGroup       CallTypeGroup       OPTIONAL,
     chargeDetailList    ChargeDetailList    OPTIONAL,
    taxInformation      TaxInformationList  OPTIONAL,
    discountInformation DiscountInformation OPTIONAL
}

ChargeInformationList ::= [APPLICATION 70] SEQUENCE OF ChargeInformation

ChargeType ::= [APPLICATION 71] NumberString --(SIZE(2..3))

ChargingCharacteristics ::= [APPLICATION 263] OCTET STRING --(SIZE(1))

ChargingId ::= [APPLICATION 72] INTEGER

ChargingPoint ::= [APPLICATION 73]  AsciiString --(SIZE(1))

ChargingTimeStamp ::= [APPLICATION 74]  DateTime

ClirIndicator ::= [APPLICATION 75] INTEGER

CompletionTimeStamp ::= [APPLICATION 76] DateTime

CountryCode ::= [APPLICATION 77] NumberString

CountryCodeList ::= [APPLICATION 78] SEQUENCE OF CountryCode

CseInformation ::= [APPLICATION 79] OCTET STRING --(SIZE(1..40))

CurrencyConversionList ::= [APPLICATION 80] 
                            SEQUENCE OF CurrencyConversion

CustomerIdType ::= [APPLICATION 363] INTEGER

CustomerIdentifier ::= [APPLICATION 364] AsciiString

DataVolume ::= [APPLICATION 81] INTEGER 

DataVolumeIncoming ::= [APPLICATION 250] DataVolume

DataVolumeOutgoing ::= [APPLICATION 251] DataVolume

DataVolumeReference ::= [APPLICATION 82] INTEGER 

--
--  The following datatypes are used to denote timestamps.
--  Each timestamp consists of a local timestamp and a
--  corresponding UTC time offset. 
--  Except for the timestamps used within the Batch Control 
--  Information and the Audit Control Information 
--  the UTC time offset is identified by a code referencing
--  the UtcTimeOffsetInfo.
--  
 
--
-- We start with the "short" datatype referencing the 
-- UtcTimeOffsetInfo.
-- 


DateTime ::= [APPLICATION 83] SEQUENCE 
{
     -- 
     -- Local timestamps are noted in the format
     --
     --     CCYYMMDDhhmmss
     --
     -- where CC  =  century  ('19', '20',...)
     --       YY  =  year     ('00' - '99')
     --       MM  =  month    ('01', '02', ... , '12')
     --       DD  =  day      ('01', '02', ... , '31')
     --       hh  =  hour     ('00', '01', ... , '24')
     --       mm  =  minutes  ('00', '01', ... , '59')
     --       ss  =  seconds  ('00', '01', ... , '59')
     -- 
    localTimeStamp     LocalTimeStamp    OPTIONAL ,
    utcTimeOffsetCode  UtcTimeOffsetCode OPTIONAL
}

--
-- The following version is the "long" datatype
-- containing the UTC time offset directly. 
--

DateTimeLong ::= [APPLICATION 84] SEQUENCE 
{
    localTimeStamp     LocalTimeStamp OPTIONAL ,
    utcTimeOffset      UtcTimeOffset  OPTIONAL
}

DayCategory ::= [APPLICATION 85] AsciiString --(SIZE(1))

DayCategorySubtype ::= [APPLICATION 86] AsciiString --(SIZE(1))

DefaultCallHandlingIndicator ::= [APPLICATION 87] INTEGER

DepositTimeStamp ::= [APPLICATION 88] DateTime

Destination ::= [APPLICATION 89] SEQUENCE
{
    calledNumber                AddressStringDigits   OPTIONAL,
    dialledDigits               DialledDigits         OPTIONAL,
    calledPlace                 CalledPlace           OPTIONAL,
    calledRegion                CalledRegion          OPTIONAL,
    calledNumAnalysisCode       CalledNumAnalysisCode OPTIONAL
}

DestinationNetwork ::= [APPLICATION 90] NetworkId 

DialledDigits ::= [APPLICATION 279] AsciiString

DiscountApplied ::= CHOICE 
{
    fixedDiscountValue    DiscountValue, 
    discountRate          DiscountRate
}

DiscountCode ::= [APPLICATION 91] INTEGER

Discounting ::= [APPLICATION 94] SEQUENCE
{
    discountCode    DiscountCode    OPTIONAL,
    discountApplied DiscountApplied OPTIONAL
}

DiscountInformation ::= [APPLICATION 96] SEQUENCE
{
    discountCode DiscountCode  OPTIONAL,
    discount     DiscountValue OPTIONAL
}

DiscountingList ::= [APPLICATION 95]  SEQUENCE OF Discounting

DiscountRate ::= [APPLICATION 92] PercentageRate

DiscountValue ::= [APPLICATION 93] AbsoluteAmount

DistanceChargeBandCode ::= [APPLICATION 98] AsciiString --(SIZE(1))

DualServiceCode ::= CHOICE
{
    dualTeleServiceCode     DualTeleServiceCode,
    dualBearerServiceCode   DualBearerServiceCode
}

DualBearerServiceCode ::= [APPLICATION 99] HexString --(SIZE(2))

DualTeleServiceCode ::= [APPLICATION 100] HexString --(SIZE(2))

EarliestCallTimeStamp ::= [APPLICATION 101] DateTimeLong

EquipmentInformation ::= [APPLICATION 102]  SEQUENCE
{ 
    mobileStationClassMark    MobileStationClassMark OPTIONAL,
    imeiOrEsn                 ImeiOrEsn              OPTIONAL
}

Esn ::= [APPLICATION 103] NumberString

ExchangeRate ::= [APPLICATION 104] INTEGER

ExchangeRateCode ::= [APPLICATION 105] Code

CurrencyConversion ::= [APPLICATION 106] SEQUENCE
{
    exchangeRateCode      ExchangeRateCode      OPTIONAL,
    numberOfDecimalPlaces NumberOfDecimalPlaces OPTIONAL,
    exchangeRate          ExchangeRate          OPTIONAL
}

FileAvailableTimeStamp ::= [APPLICATION 107] DateTimeLong

FileCreationTimeStamp ::= [APPLICATION 108] DateTimeLong

FileSequenceNumber ::= [APPLICATION 109] NumberString --(SIZE(5))

FileTypeIndicator ::= [APPLICATION 110] AsciiString --(SIZE(1))

Fnur ::= [APPLICATION 111] INTEGER

FraudMonitorIndicator ::= [APPLICATION 112] AsciiString --(SIZE(1))

GeographicalLocation ::= [APPLICATION 113]  SEQUENCE
{
    servingNetwork              ServingNetwork       OPTIONAL,
    servingBid                  ServingBid           OPTIONAL,
    servingLocationDescription  LocationDescription  OPTIONAL,
    longitude                   Longitude            OPTIONAL,
    latitude                    Latitude             OPTIONAL
}

GmlcAddress ::= [APPLICATION 296] AsciiString

GprsBasicCallInformation ::= [APPLICATION 114] SEQUENCE
{
    fraudMonitorIndicator       FraudMonitorIndicator    OPTIONAL,
    gprsChargeableSubscriber    GprsChargeableSubscriber OPTIONAL,
    rapFileSequenceNumber       RapFileSequenceNumber    OPTIONAL,
    networkType                 NetworkType              OPTIONAL,
    gprsDestination             GprsDestination          OPTIONAL,
    callEventStartTimeStamp     CallEventStartTimeStamp  OPTIONAL,
    totalCallEventDuration      TotalCallEventDuration   OPTIONAL,
    causeForTerm                CauseForTerm             OPTIONAL,
    partialTypeIndicator        PartialTypeIndicator     OPTIONAL,
    pDPContextStartTimestamp    PDPContextStartTimestamp OPTIONAL,
    networkInitPDPContext       NetworkInitPDPContext    OPTIONAL,
    chargingId                  ChargingId               OPTIONAL
}

GprsChargeableSubscriber ::= [APPLICATION 115] SEQUENCE
{
    chargeableSubscriber        ChargeableSubscriber    OPTIONAL,
    pdpType                     PdpType                 OPTIONAL,
    pdpAddress                  PdpAddress              OPTIONAL,
    chargingCharacteristics     ChargingCharacteristics OPTIONAL
}

GprsDestination ::= [APPLICATION 116] SEQUENCE
{
    accessPointNameNI           AccessPointNameNI      OPTIONAL,
    accessPointNameOI           AccessPointNameOI      OPTIONAL,
    remotePdpAddressList        RemotePdpAddressList OPTIONAL
}

GprsLocationInformation ::= [APPLICATION 117] SEQUENCE
{
    gprsNetworkLocation         GprsNetworkLocation     OPTIONAL,
    homeLocationInformation     HomeLocationInformation OPTIONAL,
    geographicalLocation        GeographicalLocation    OPTIONAL 
} 

GprsNetworkLocation ::= [APPLICATION 118] SEQUENCE
{
    recEntity                   RecEntityCodeList OPTIONAL,
    locationArea                LocationArea      OPTIONAL,
    cellId                      CellId            OPTIONAL
}

GprsServiceUsage ::= [APPLICATION 119]  SEQUENCE
{
    gprsUsageTimeStamp          ChargingTimeStamp  OPTIONAL,
    qosRequested                QoSRequested       OPTIONAL,
    qosUsed                     QoSUsed            OPTIONAL,
    dataVolumeIncoming          DataVolumeIncoming OPTIONAL,
    dataVolumeOutgoing          DataVolumeOutgoing OPTIONAL
}

GprsServiceUsageList ::= [APPLICATION 120]  SEQUENCE OF GprsServiceUsage

GprsServiceUsed ::= [APPLICATION 121]  SEQUENCE
{
    gprsServiceUsageList        GprsServiceUsageList  OPTIONAL,
    chargingTimeStamp           ChargingTimeStamp     OPTIONAL,
    chargeInformationList       ChargeInformationList OPTIONAL
}

GsmChargeableSubscriber ::= [APPLICATION 286] SEQUENCE
{
    imsi     Imsi   OPTIONAL,
    msisdn   Msisdn OPTIONAL
}

GSMQoSInformation ::= SEQUENCE
{
    delay          QoSDelay          OPTIONAL,
    meanThroughput QoSMeanThroughput OPTIONAL,
    peakThroughput QoSPeakThroughput OPTIONAL,
    precedence     QoSPrecedence     OPTIONAL,
    reliability    QoSReliability    OPTIONAL
}

GSMQoSRequested ::= [APPLICATION 272]  GSMQoSInformation

GSMQoSUsed ::= [APPLICATION 273] GSMQoSInformation

GsnAddress ::= IpAddress

HomeBid ::= [APPLICATION 122]  Bid

HomeLocationInformation ::= [APPLICATION 123] SEQUENCE
{
    homeBid                     HomeBid             OPTIONAL,
    homeLocationDescription     LocationDescription OPTIONAL
}

HorizontalAccuracyDelivered ::= [APPLICATION 392] INTEGER

HorizontalAccuracyRequested ::= [APPLICATION 385] INTEGER

HSCSDInformation ::= [APPLICATION 124] SEQUENCE
{
    basicHSCSDParameters            BasicHSCSDParameters           OPTIONAL,
    hSCSDParameterModificationList  HSCSDParameterModificationList OPTIONAL
}


HSCSDParameterModification ::= [APPLICATION 125] SEQUENCE
{
    aiur                        AiurRequested         OPTIONAL,
    maxNumberOfChannels         NumberOfChannels      OPTIONAL,
    channelCodingUsed           ChannelCoding         OPTIONAL,
    numberOfChannelsUsed        NumberOfChannelsUsed  OPTIONAL,
    initiatingParty             InitiatingParty       OPTIONAL,
    modificationTimestamp       ModificationTimestamp OPTIONAL
}

HSCSDParameterModificationList ::= [APPLICATION 140] 
                               SEQUENCE OF HSCSDParameterModification

Iac ::= [APPLICATION 126] NumberString

IacList ::= [APPLICATION 127]  SEQUENCE OF Iac

Imei ::= [APPLICATION 128] BCDString --(SIZE(7..8))

ImeiOrEsn ::= CHOICE 
{
    imei  Imei,
    esn   Esn
} 

Imsi ::= [APPLICATION 129] BCDString --(SIZE(3..8))

InitiatingParty ::= [APPLICATION 130] INTEGER

ISPList ::= [APPLICATION 378] SEQUENCE OF
    InternetServiceProvider

IpAddress ::= CHOICE
{
    -- IP4 address as x.x.x.x, where 'x's represent the decimal values
    -- of the four 8-bit segment
    -- IP6 address as x:x:x:x:x:x:x:x, where 'x's represent the
    -- hexadecimal values of the eight 16-bit segments
    iPTextV4Address	IPTextV4Address,
    iPTextV6Address	IPTextV6Address
}

IPTextV4Address	::= [APPLICATION 131] AsciiString --(SIZE(7..15))

IPTextV6Address	::= [APPLICATION 132] AsciiString --(SIZE(15..39))

LatestCallTimeStamp ::= [APPLICATION 133] DateTimeLong

Latitude ::= [APPLICATION 134] INTEGER 

LCSQosDelivered ::= [APPLICATION 390] SEQUENCE
{
    lCSTransactionStatus          LCSTransactionStatus OPTIONAL,
    horizontalAccuracyDelivered   HorizontalAccuracyDelivered OPTIONAL,
    verticalAccuracyDelivered     VerticalAccuracyDelivered OPTIONAL,
    responseTime                  ResponseTime OPTIONAL,
    positioningMethod             PositioningMethod OPTIONAL,
    trackingPeriod                TrackingPeriod OPTIONAL,
    trackingFrequency             TrackingFrequency OPTIONAL,
    ageOfLocation                 AgeOfLocation OPTIONAL
}

LCSQosRequested ::= [APPLICATION 383] SEQUENCE
{
    lCSRequestTimestamp           LCSRequestTimestamp OPTIONAL,
    horizontalAccuracyRequested   HorizontalAccuracyRequested OPTIONAL,
    verticalAccuracyRequested     VerticalAccuracyRequested OPTIONAL,
    responseTimeCategory          ResponseTimeCategory OPTIONAL,
    trackingPeriod                TrackingPeriod OPTIONAL,
    trackingFrequency             TrackingFrequency OPTIONAL
}

LCSRequestTimestamp ::= [APPLICATION 384] DateTime

LCSSPInformation ::= [APPLICATION 373] SEQUENCE
{
    lCSSPIdentificationList       LCSSPIdentificationList OPTIONAL,
    iSPList                       ISPList OPTIONAL,
    networkList                   NetworkList OPTIONAL
}

LCSSPIdentificationList ::= [APPLICATION 374] SEQUENCE OF
    LCSSPIdentification

LCSSPIdentification ::= [APPLICATION 375] SEQUENCE
{
    contentProviderIdType         ContentProviderIdType OPTIONAL,
    contentProviderIdentifier     ContentProviderIdentifier OPTIONAL
}

LCSTransactionStatus ::= [APPLICATION 391] INTEGER

LocalCurrency ::= [APPLICATION 135] Currency

LocalTimeStamp ::= [APPLICATION 16] NumberString --(SIZE(14))

LocationArea ::= [APPLICATION 136] INTEGER 

LocationDescription ::= [APPLICATION 137] AsciiString

LocationInformation ::= [APPLICATION 138]  SEQUENCE
{
    networkLocation             NetworkLocation         OPTIONAL,
    homeLocationInformation     HomeLocationInformation OPTIONAL,
    geographicalLocation        GeographicalLocation    OPTIONAL
} 

LocationServiceUsage ::= [APPLICATION 382] SEQUENCE
{
    lCSQosRequested               LCSQosRequested OPTIONAL,
    lCSQosDelivered               LCSQosDelivered OPTIONAL,
    chargingTimeStamp             ChargingTimeStamp OPTIONAL,
    chargeInformationList         ChargeInformationList OPTIONAL
}

Longitude ::= [APPLICATION 139] INTEGER 

Mdn ::= [APPLICATION 253] NumberString

MessageDescriptionCode ::= [APPLICATION 141] Code

MessageDescription ::= [APPLICATION 142] AsciiString

MessageDescriptionInformation ::= [APPLICATION 143] SEQUENCE
{
    messageDescriptionCode MessageDescriptionCode OPTIONAL,
    messageDescription     MessageDescription     OPTIONAL
}

MessageStatus ::= [APPLICATION 144] INTEGER

MessageType ::= [APPLICATION 145] INTEGER

Min ::= [APPLICATION 146] NumberString --(SIZE(2..15)) 

MinChargeableSubscriber ::= [APPLICATION 254] SEQUENCE
{
    min     Min    OPTIONAL,
    mdn     Mdn    OPTIONAL
}

MoBasicCallInformation ::= [APPLICATION 147] SEQUENCE
{
    fraudMonitorIndicator       FraudMonitorIndicator   OPTIONAL,
    chargeableSubscriber        ChargeableSubscriber    OPTIONAL,
    rapFileSequenceNumber       RapFileSequenceNumber   OPTIONAL,
    networkType                 NetworkType             OPTIONAL,
    destination                 Destination             OPTIONAL,
    destinationNetwork          DestinationNetwork      OPTIONAL,
    callEventStartTimeStamp     CallEventStartTimeStamp OPTIONAL,
    totalCallEventDuration      TotalCallEventDuration  OPTIONAL,
    simToolkitIndicator         SimToolkitIndicator     OPTIONAL,
    causeForTerm                CauseForTerm            OPTIONAL
}

MobileStationClassMark ::= [APPLICATION 148] INTEGER

ModificationTimestamp ::= [APPLICATION 150] DateTime

MscId ::= [APPLICATION 151] AsciiString --(SIZE(1..15))

Msisdn ::= [APPLICATION 152] BCDString --(SIZE(1..8))

MtBasicCallInformation ::= [APPLICATION 153] SEQUENCE
{
    fraudMonitorIndicator       FraudMonitorIndicator   OPTIONAL,
    chargeableSubscriber        ChargeableSubscriber    OPTIONAL,
    rapFileSequenceNumber       RapFileSequenceNumber   OPTIONAL,
    networkType                 NetworkType             OPTIONAL,
    callOriginator              CallOriginator          OPTIONAL,
    originatingNetwork          OriginatingNetwork      OPTIONAL,
    callEventStartTimeStamp     CallEventStartTimeStamp OPTIONAL,
    totalCallEventDuration      TotalCallEventDuration  OPTIONAL,
    simToolkitIndicator         SimToolkitIndicator     OPTIONAL,
    causeForTerm                CauseForTerm            OPTIONAL
}

MultiRateIndicator ::= [APPLICATION 154] INTEGER
  
NetworkId ::= [APPLICATION 155] AsciiString --(SIZE(1..6))

NetworkInitPDPContext ::= [APPLICATION 245] INTEGER

NetworkLocation ::= [APPLICATION 156]  SEQUENCE
{
    recEntityCode               RecEntityCode OPTIONAL,
    callReference               CallReference OPTIONAL,
    locationArea                LocationArea  OPTIONAL,
    cellId                      CellId        OPTIONAL
}

NetworkType ::= [APPLICATION 157] INTEGER 

NonChargedParty ::= [APPLICATION 158]  SEQUENCE
{ 
    nonChargedNumber            AddressStringDigits   OPTIONAL,
    calledNumAnalysisCode       CalledNumAnalysisCode OPTIONAL
}

NumberOfDecimalPlaces ::= [APPLICATION 159] INTEGER

NumberOfChannels ::= [APPLICATION 161] INTEGER

NumberOfChannelsUsed ::= [APPLICATION 252] INTEGER

ObjectType ::= [APPLICATION 281] INTEGER

OperatorSpecInformation ::= [APPLICATION 163] AsciiString

OperatorSpecInfoList ::= [APPLICATION 162] SEQUENCE OF OperatorSpecInformation

OriginatingNetwork ::= [APPLICATION 164] NetworkId 

PacketDataProtocolAddress ::= [APPLICATION 165] AsciiString 

PartialTypeIndicator ::=  [APPLICATION 166] AsciiString --(SIZE(1))

PdpAddress ::= [APPLICATION 167] PacketDataProtocolAddress

PDPContextStartTimestamp ::= [APPLICATION 260] DateTime

PdpType ::= [APPLICATION 168] INTEGER

PlmnId ::= [APPLICATION 169] AsciiString --(SIZE(5))

PositioningMethod ::= [APPLICATION 395] INTEGER

PriorityCode ::= [APPLICATION 170] INTEGER

QoSAllocRetenPriority  ::= [APPLICATION 275] INTEGER

QoSDelay ::= [APPLICATION 171] INTEGER

QoSGuaranteedBitRateDownlink ::= [APPLICATION 283] OCTET STRING --(SIZE(1))

QoSGuaranteedBitRateUplink ::= [APPLICATION 284] OCTET STRING --(SIZE(1))

QoSMaxBitRateUplink ::= [APPLICATION 264] OCTET STRING --(SIZE(1))

QoSMaxBitRateDownlink ::= [APPLICATION 274] OCTET STRING --(SIZE(1))

QoSMeanThroughput   ::= [APPLICATION 173] INTEGER

QoSPeakThroughput ::= [APPLICATION 174] INTEGER

QoSPrecedence   ::= [APPLICATION 175] INTEGER

QoSReliability  ::= [APPLICATION 176] INTEGER

QoSRequested ::= CHOICE
{
    gsmQoSRequested     GSMQoSRequested,
    umtsQoSRequested    UMTSQoSRequested
}

QoSTrafficClass		::= [APPLICATION 268] INTEGER

QoSUsed ::= CHOICE
{
    gsmQoSUsed     GSMQoSUsed,
    umtsQoSUsed    UMTSQoSUsed
}

RadioChannelRequested ::= [APPLICATION 179] INTEGER

RadioChannelUsed ::= [APPLICATION 180] INTEGER

RapFileSequenceNumber ::= [APPLICATION 181]  FileSequenceNumber

Recipient ::= [APPLICATION 182]  PlmnId

RecEntityInformation ::= [APPLICATION 183] SEQUENCE
{
    recEntityCode  RecEntityCode OPTIONAL,
    recEntityType  RecEntityType OPTIONAL,
    recEntityId    RecEntityId   OPTIONAL
}
 
RecEntityCode ::= [APPLICATION 184] Code

RecEntityCodeList ::= [APPLICATION 185] SEQUENCE OF RecEntityCode

RecEntityType ::= [APPLICATION 186] INTEGER

RecEntityId ::= CHOICE 
{
    gmlcAddress  GmlcAddress,
    mscId        MscId,
    msisdn       Msisdn,
    gsnaddress   GsnAddress
}

RecEntityInfoList ::= [APPLICATION 188] 
                            SEQUENCE OF RecEntityInformation

ReleaseVersionNumber ::= [APPLICATION 189] INTEGER

RemotePdpAddressList ::= [APPLICATION 190] SEQUENCE OF PacketDataProtocolAddress

ResponseTime ::= [APPLICATION 394] INTEGER

ResponseTimeCategory ::= [APPLICATION 387] INTEGER

ScuBasicInformation ::= [APPLICATION 191] SEQUENCE
{
    chargeableSubscriber        ScuVasChargeableSubscriber OPTIONAL,
    chargedPartyStatus          ChargedPartyStatus         OPTIONAL,
    nonChargedParty             NonChargedParty            OPTIONAL,
    clirIndicator               ClirIndicator              OPTIONAL,
    originatingNetwork          OriginatingNetwork         OPTIONAL,
    destinationNetwork          DestinationNetwork         OPTIONAL
}

ScuChargeType ::= [APPLICATION 192]  SEQUENCE
{
    messageStatus               MessageStatus          OPTIONAL,
    priorityCode                PriorityCode           OPTIONAL,
    distanceChargeBandCode      DistanceChargeBandCode OPTIONAL,
    messageType                 MessageType            OPTIONAL,
    messageDescriptionCode      MessageDescriptionCode OPTIONAL
}

ScuTimeStamps ::= [APPLICATION 193]  SEQUENCE
{
    depositTimeStamp            DepositTimeStamp    OPTIONAL,
    completionTimeStamp         CompletionTimeStamp OPTIONAL,
    chargingPoint               ChargingPoint       OPTIONAL
}

ScuVasChargeableSubscriber ::= CHOICE 
{
    gsmChargeableSubscriber GsmChargeableSubscriber,
    minChargeableSubscriber    MinChargeableSubscriber
}

Sender ::= [APPLICATION 196]  PlmnId

ServingBid ::= [APPLICATION 198]  Bid

ServingNetwork ::= [APPLICATION 195]  AsciiString

SimChargeableSubscriber ::= [APPLICATION 199] SEQUENCE
{
    imsi     Imsi   OPTIONAL,
    msisdn   Msisdn OPTIONAL
}

SimToolkitIndicator ::= [APPLICATION 200] AsciiString --(SIZE(1)) 

SpecificationVersionNumber  ::= [APPLICATION 201] INTEGER

SpeechVersionRequested ::= [APPLICATION 202] SpeechVersion

SpeechVersionUsed ::= [APPLICATION 203] SpeechVersion

SpeechVersion ::= INTEGER

SsParameters ::= [APPLICATION 204] AsciiString --(SIZE(1..40))

SupplServiceUsed ::= [APPLICATION 206] SEQUENCE
{
    supplServiceCode       SupplServiceCode       OPTIONAL,
    supplServiceActionCode SupplServiceActionCode OPTIONAL,
    ssParameters           SsParameters           OPTIONAL,
    thirdPartyInformation  ThirdPartyInformation  OPTIONAL,
    chargingTimeStamp      ChargingTimeStamp      OPTIONAL,
    chargeInformation      ChargeInformation      OPTIONAL,
    basicServiceCodeList   BasicServiceCodeList   OPTIONAL
}

SupplServiceUsedList ::= [APPLICATION 207] SEQUENCE OF SupplServiceUsed

SupplServiceActionCode ::= [APPLICATION 208] INTEGER

SupplServiceCode ::= [APPLICATION 209] HexString --(SIZE(2))

TapCurrency ::= [APPLICATION 210] Currency

TaxationList ::= [APPLICATION 211]  SEQUENCE OF Taxation

TaxCode ::= [APPLICATION 212] INTEGER

TapDecimalPlaces ::= [APPLICATION 244] INTEGER

TaxInformation ::= [APPLICATION 213] SEQUENCE
{
    taxCode          TaxCode       OPTIONAL,
    taxValue         TaxValue      OPTIONAL,
    chargeType       ChargeType    OPTIONAL,
    taxableAmount    TaxableAmount OPTIONAL
}

TaxInformationList ::= [APPLICATION 214]  SEQUENCE OF TaxInformation

TaxRate ::= [APPLICATION 215] NumberString (SIZE(7))

TaxableAmount ::= [APPLICATION 398] AbsoluteAmount

Taxation ::= [APPLICATION 216] SEQUENCE
{
    taxCode TaxCode OPTIONAL,
    taxType TaxType OPTIONAL,
    taxRate TaxRate OPTIONAL
}

TaxType ::= [APPLICATION 217] AsciiString --(SIZE(2))

TaxValue ::= [APPLICATION 397] AbsoluteAmount

TeleServiceCode ::= [APPLICATION 218] HexString --(SIZE(2))

ThirdPartyInformation ::= [APPLICATION 219]  SEQUENCE
{
    thirdPartyNumber            AddressStringDigits   OPTIONAL,
    clirIndicator               ClirIndicator         OPTIONAL
}

TimeBand ::= [APPLICATION 220] AsciiString --(SIZE(1))

TimeBandSubtype ::= [APPLICATION 221] AsciiString --(SIZE(1))

TotalChargeValue ::= [APPLICATION 222] SEQUENCE
{
    chargeType         ChargeType        OPTIONAL,
    totalCharge        AbsoluteAmount    OPTIONAL,
    totalChargeRefund  TotalChargeRefund OPTIONAL
} 

TotalCallEventDuration ::= [APPLICATION 223] INTEGER 

TotalChargeValueList ::= [APPLICATION 224] SEQUENCE OF TotalChargeValue

TotalDiscountValue ::= [APPLICATION 225] AbsoluteAmount

TotalTaxValue ::= [APPLICATION 226] AbsoluteAmount

TrackedCustomerInformation ::= [APPLICATION 367] SEQUENCE
{
    trackedCustomerIdList         TrackedCustomerIdList OPTIONAL,
    trackedCustomerHomeIdList     TrackedCustomerHomeIdList OPTIONAL,
    trackedCustomerLocList        TrackedCustomerLocList OPTIONAL,
    trackedCustomerEquipment      TrackedCustomerEquipment OPTIONAL
}

TrackedCustomerIdList ::= [APPLICATION 370] SEQUENCE OF
    TrackedCustomerIdentification

TrackedCustomerIdentification ::= [APPLICATION 372] SEQUENCE
{
    customerIdType                CustomerIdType OPTIONAL,
    customerIdentifier            CustomerIdentifier OPTIONAL
}

TrackedCustomerHomeIdList ::= [APPLICATION 376] SEQUENCE OF
    TrackedCustomerHomeId

TrackedCustomerHomeId ::= [APPLICATION 377] SEQUENCE
{
    homeIdType                    HomeIdType OPTIONAL,
    homeIdentifier                HomeIdentifier OPTIONAL
}

TrackedCustomerLocList ::= [APPLICATION 379] SEQUENCE OF
    TrackedCustomerLocation

TrackedCustomerLocation ::= [APPLICATION 380] SEQUENCE
{
    locationIdType                LocationIdType OPTIONAL,
    locationIdentifier            LocationIdentifier OPTIONAL
}

TrackedCustomerEquipment ::= [APPLICATION 381] SEQUENCE
{
    equipmentIdType               EquipmentIdType OPTIONAL,
    equipmentId                   EquipmentId OPTIONAL
}

TrackingCustomerInformation ::= [APPLICATION 298] SEQUENCE
{
    trackingCustomerIdList        TrackingCustomerIdList OPTIONAL,
    trackingCustomerHomeIdList    TrackingCustomerHomeIdList OPTIONAL,
    trackingCustomerLocList       TrackingCustomerLocList OPTIONAL,
    trackingCustomerEquipment     TrackingCustomerEquipment OPTIONAL
}

TrackingCustomerIdList ::= [APPLICATION 299] SEQUENCE OF
    TrackingCustomerIdentification

TrackingCustomerIdentification ::= [APPLICATION 362] SEQUENCE
{
    customerIdType                CustomerIdType OPTIONAL,
    customerIdentifier            CustomerIdentifier OPTIONAL
}

TrackingCustomerHomeIdList ::= [APPLICATION 365] SEQUENCE OF
    TrackingCustomerHomeId

TrackingCustomerHomeId ::= [APPLICATION 366] SEQUENCE
{
    homeIdType                    HomeIdType OPTIONAL,
    homeIdentifier                HomeIdentifier OPTIONAL
}

TrackingCustomerLocList ::= [APPLICATION 368] SEQUENCE OF
    TrackingCustomerLocation

TrackingCustomerLocation ::= [APPLICATION 369] SEQUENCE
{
    locationIdType                LocationIdType OPTIONAL,
    locationIdentifier            LocationIdentifier OPTIONAL
}

TrackingCustomerEquipment ::= [APPLICATION 371] SEQUENCE
{
    equipmentIdType               EquipmentIdType OPTIONAL,
    equipmentId                   EquipmentId OPTIONAL
}

TrackingFrequency ::= [APPLICATION 389] INTEGER

TrackingPeriod ::= [APPLICATION 388] INTEGER

TransferCutOffTimeStamp ::= [APPLICATION 227] DateTimeLong

TransparencyIndicator ::= [APPLICATION 228] INTEGER

TypeOfControllingNode ::= [APPLICATION 229] INTEGER

UMTSQoSInformation	::= SEQUENCE
{
    trafficClass             QoSTrafficClass       OPTIONAL,
    maxBitRateUplink         QoSMaxBitRateUplink   OPTIONAL,
    maxBitRateDownlink       QoSMaxBitRateDownlink OPTIONAL,
    qoSGuaranteedBitRateDownlink  QoSGuaranteedBitRateDownlink  OPTIONAL,
    qoSGuaranteedBitRateUplink    QoSGuaranteedBitRateUplink    OPTIONAL,
    allocRetenPriority            QoSAllocRetenPriority         OPTIONAL
}

UMTSQoSRequested	::= [APPLICATION 270] UMTSQoSInformation

UMTSQoSUsed	::= [APPLICATION 271] UMTSQoSInformation

UserProtocolIndicator ::= [APPLICATION 280] INTEGER

UtcTimeOffset ::= [APPLICATION 231] AsciiString --(SIZE(5))

UtcTimeOffsetCode ::= [APPLICATION 232] Code

UtcTimeOffsetInfo ::= [APPLICATION 233] SEQUENCE
{
    utcTimeOffsetCode   UtcTimeOffsetCode OPTIONAL,
    utcTimeOffset       UtcTimeOffset     OPTIONAL
}

UtcTimeOffsetInfoList ::= [APPLICATION 234]  SEQUENCE OF UtcTimeOffsetInfo

ValueAddedServiceUsedList ::= [APPLICATION 235] SEQUENCE OF ValueAddedServiceUsed 

ValueAddedServiceUsed ::= [APPLICATION 236] SEQUENCE
{
    vasCode                     VasCode           OPTIONAL,
    chargingTimeStamp           ChargingTimeStamp OPTIONAL,
    chargeInformation           ChargeInformation OPTIONAL
}

VasCode ::= [APPLICATION 237] Code

VasInformation ::= [APPLICATION 238] SEQUENCE
{
    vasCode      VasCode             OPTIONAL,
    vasShortDesc VasShortDescription OPTIONAL,
    vasDesc      VasDescription      OPTIONAL
}

VasDescription ::= [APPLICATION 239] Description

VasShortDescription ::= [APPLICATION 240] Description

VerticalAccuracyDelivered ::= [APPLICATION 393] INTEGER

VerticalAccuracyRequested ::= [APPLICATION 386] INTEGER


--
-- Tagged common data types
--

--
-- The AbsoluteAmount data type is used to 
-- encode absolute revenue amounts.
-- The accuracy of all absolute amount values is defined
-- by the value of TapDecimalPlaces within the group
-- AccountingInfo for the entire TAP batch.
-- Note, that only amounts greater than or equal to zero are allowed.
-- The decimal number representing the amount is 
-- derived from the encoded integer 
-- value by division by 10^TapDecimalPlaces.
-- e.g. for TapDecimalPlaces = 3 the following values
-- will be derived:
--       0   represents    0.000
--      12   represents    0.012
--    1234   represents    1.234
-- for TapDecimalPlaces = 5 the following values will be
-- derived:
--       0   represents    0.00000
--    1234   represents    0.01234
--  123456   represents    1.23456
-- This data type is used to encode (total) 
-- charges, (total) discount values and 
-- (total) tax values. 
-- 
AbsoluteAmount ::= [APPLICATION 241] INTEGER 

Bid ::= [APPLICATION 242] AsciiString --(SIZE(5))

Code ::= [APPLICATION 243] INTEGER

--
-- Non-tagged common data types
--
--
-- Recommended common data types to be used for file encoding:
--
-- The following definitions should be used for TAP file creation instead of
-- the default specifications (OCTET STRING)
--
AsciiString ::= VisibleString

Currency ::= VisibleString

Description ::= VisibleString

HexString ::= VisibleString

NumberString ::= NumericString
--

--
-- The PercentageRate data type is used to
-- encode percentage rates with an accuracy of 2 decimal places. 
-- This data type is used to encode discount rates.
-- The decimal number representing the percentage
-- rate is obtained by dividing the integer value by 100
-- Examples:
--
--     1500  represents  15.00 percent
--     1     represents   0.01 percent
--
PercentageRate ::= INTEGER 


--
-- The BCDString data type (Binary Coded Decimal String) is used to
-- represent several digits from 0 through 9, a, b, c, d, e
-- two digits per octet, f as filler when there is an odd number 
-- of digits.
--
BCDString ::= OCTET STRING



--
-- TAP data elements necessary for Content Transaction
--

OrderPlacedTimeStamp ::= [APPLICATION 300] DateTime

RequestedDeliveryTimeStamp ::= [APPLICATION 301] DateTime

ActualDeliveryTimeStamp ::= [APPLICATION 302] DateTime

TransactionStatus ::= [APPLICATION 303] INTEGER

ContentTransactionBasicInfo ::= [APPLICATION 304] SEQUENCE
{
    fraudMonitorIndicator      FraudMonitorIndicator      OPTIONAL,
    rapFileSequenceNumber      RapFileSequenceNumber      OPTIONAL,
    orderPlacedTimeStamp    OrderPlacedTimeStamp    OPTIONAL,
    requestedDeliveryTimeStamp RequestedDeliveryTimeStamp OPTIONAL,
    actualDeliveryTimeStamp    ActualDeliveryTimeStamp    OPTIONAL,
    totalTransactionDuration   TotalCallEventDuration     OPTIONAL,
    transactionStatus          TransactionStatus          OPTIONAL
}

ChargedPartyIdType ::= [APPLICATION 305] INTEGER

ChargedPartyIdentifier ::= [APPLICATION 287] AsciiString

ChargedPartyIdentification ::= [APPLICATION 309] SEQUENCE
{
    chargedPartyIdType         ChargedPartyIdType         OPTIONAL,
    chargedPartyIdentifier     ChargedPartyIdentifier     OPTIONAL
}

ChargedPartyIdList ::= [APPLICATION 310] SEQUENCE OF 
                                         ChargedPartyIdentification

HomeIdType ::= [APPLICATION 311] INTEGER

HomeIdentifier ::= [APPLICATION 288] AsciiString

ChargedPartyHomeIdentification ::= [APPLICATION 313] SEQUENCE
{
    homeIdType     HomeIdType     OPTIONAL,
    homeIdentifier HomeIdentifier OPTIONAL
}

ChargedPartyHomeIdList ::= [APPLICATION 314] SEQUENCE OF
                                             ChargedPartyHomeIdentification

LocationIdType ::= [APPLICATION 315] INTEGER

LocationIdentifier ::= [APPLICATION 289] AsciiString

ChargedPartyLocation ::= [APPLICATION 320] SEQUENCE
{
    locationIdType     LocationIdType     OPTIONAL,
    locationIdentifier LocationIdentifier OPTIONAL
}
 
ChargedPartyLocationList ::= [APPLICATION 321] SEQUENCE OF ChargedPartyLocation
 
EquipmentIdType ::= [APPLICATION 322] INTEGER
EquipmentId ::= [APPLICATION 290] AsciiString

ChargedPartyEquipment ::= [APPLICATION 323] SEQUENCE
{
    equipmentIdType EquipmentIdType OPTIONAL,
    equipmentId     EquipmentId     OPTIONAL
}
 
ChargedPartyInformation ::= [APPLICATION 324] SEQUENCE
{
    chargedPartyIdList       ChargedPartyIdList        OPTIONAL,
    chargedPartyHomeIdList   ChargedPartyHomeIdList    OPTIONAL,
    chargedPartyLocationList ChargedPartyLocationList  OPTIONAL,
    chargedPartyEquipment    ChargedPartyEquipment     OPTIONAL
}
 
ContentProviderIdType ::= [APPLICATION 291] INTEGER

ContentProviderIdentifier ::= [APPLICATION 292] AsciiString

ContentProvider ::= [APPLICATION 327] SEQUENCE
{
    contentProviderIdType ContentProviderIdType OPTIONAL,
    contentProviderIdentifier  ContentProviderIdentifier OPTIONAL
}
 
ContentProviderIdList ::= [APPLICATION 328] SEQUENCE OF ContentProvider

IspIdType ::= [APPLICATION 293] INTEGER

IspIdentifier ::= [APPLICATION 294] AsciiString
 
InternetServiceProvider ::= [APPLICATION 329] SEQUENCE
{
    ispIdType        IspIdType        OPTIONAL,
    ispIdentifier    IspIdentifier    OPTIONAL
}
 
InternetServiceProviderIdList ::= [APPLICATION 330] SEQUENCE OF 
                                                    InternetServiceProvider
 
NetworkIdType ::= [APPLICATION 331] INTEGER

NetworkIdentifier ::= [APPLICATION 295] AsciiString

Network ::= [APPLICATION 332] SEQUENCE
{
    networkIdType NetworkIdType OPTIONAL,
    networkIdentifier    NetworkIdentifier    OPTIONAL
}
 
NetworkList ::= [APPLICATION 333] SEQUENCE OF Network
 
ContentProviderName ::= [APPLICATION 334] AsciiString
 
ServingPartiesInformation ::= [APPLICATION 335] SEQUENCE
{
    contentProviderName           ContentProviderName           OPTIONAL,
    contentProviderIdList         ContentProviderIdList         OPTIONAL,
    internetServiceProviderIdList InternetServiceProviderIdList OPTIONAL,
    networkList                 NetworkList                 OPTIONAL
}
 
ContentTransactionCode ::= [APPLICATION 336] INTEGER
 
ContentTransactionType ::= [APPLICATION 337] INTEGER
 
TransactionDescriptionSupp ::= [APPLICATION 338] INTEGER
 
TransactionDetailDescription ::= [APPLICATION 339] AsciiString

TransactionShortDescription ::= [APPLICATION 340] AsciiString
 
TransactionIdentifier ::= [APPLICATION 341] AsciiString
 
TransactionAuthCode ::= [APPLICATION 342] AsciiString
 
TotalDataVolume ::= [APPLICATION 343] DataVolume
 
ChargeRefundIndicator ::= [APPLICATION 344] INTEGER
 
ContentChargingPoint ::= [APPLICATION 345] INTEGER
 
PaidIndicator ::= [APPLICATION 346] INTEGER
 
PaymentMethod ::= [APPLICATION 347] INTEGER
 
AdvisedChargeCurrency ::= [APPLICATION 348] Currency
 
AdvisedCharge ::= [APPLICATION 349] Charge
 
Commission ::= [APPLICATION 350] Charge
 
AdvisedChargeInformation ::= [APPLICATION 351] SEQUENCE
{
    paidIndicator         PaidIndicator         OPTIONAL,
    paymentMethod         PaymentMethod         OPTIONAL,
    advisedChargeCurrency AdvisedChargeCurrency OPTIONAL,
    advisedCharge         AdvisedCharge         OPTIONAL,
    commission            Commission            OPTIONAL
}
 
ContentServiceUsed ::= [APPLICATION 352] SEQUENCE
{
    contentTransactionCode       ContentTransactionCode       OPTIONAL,
    contentTransactionType       ContentTransactionType       OPTIONAL,
    objectType                   ObjectType                   OPTIONAL,
    transactionDescriptionSupp   TransactionDescriptionSupp   OPTIONAL,
    transactionShortDescription  TransactionShortDescription  OPTIONAL, 
    transactionDetailDescription TransactionDetailDescription OPTIONAL,
    transactionIdentifier        TransactionIdentifier        OPTIONAL,
    transactionAuthCode          TransactionAuthCode          OPTIONAL,
    dataVolumeIncoming           DataVolumeIncoming           OPTIONAL,
    dataVolumeOutgoing           DataVolumeOutgoing           OPTIONAL,
    totalDataVolume              TotalDataVolume              OPTIONAL,
    chargeRefundIndicator        ChargeRefundIndicator        OPTIONAL,
    contentChargingPoint         ContentChargingPoint         OPTIONAL,
    chargeInformationList        ChargeInformationList        OPTIONAL,
    advisedChargeInformation     AdvisedChargeInformation     OPTIONAL
}

ContentServiceUsedList ::= [APPLICATION 285] SEQUENCE OF ContentServiceUsed
 
TotalTaxRefund ::= [APPLICATION 353] AbsoluteAmount
 
TotalDiscountRefund ::= [APPLICATION 354] AbsoluteAmount
 
TotalChargeRefund ::= [APPLICATION 355] AbsoluteAmount
 
TotalAdvisedCharge ::= [APPLICATION 356] AbsoluteAmount
 
TotalAdvisedChargeRefund ::= [APPLICATION 357] AbsoluteAmount
 
TotalCommission ::= [APPLICATION 358] AbsoluteAmount
 
TotalCommissionRefund ::= [APPLICATION 359] AbsoluteAmount
 
TotalAdvisedChargeValue ::= [APPLICATION 360] SEQUENCE
{
    advisedChargeCurrency    AdvisedChargeCurrency    OPTIONAL,
    totalAdvisedCharge       TotalAdvisedCharge       OPTIONAL,
    totalAdvisedChargeRefund TotalAdvisedChargeRefund OPTIONAL,
    totalCommission          TotalCommission          OPTIONAL,
    totalCommissionRefund    TotalCommissionRefund    OPTIONAL
}
 
TotalAdvisedChargeValueList ::= [APPLICATION 361] SEQUENCE OF TotalAdvisedChargeValue


END
