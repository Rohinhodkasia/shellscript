-- This file was generated by the Objective Systems ASN1C Compiler
-- (http://www.obj-sys.com).  Version: 6.8.A, Date: 15-Nov-2014.

SET-TOKEN-SLP-CERTIFICATE DEFINITIONS AUTOMATIC TAGS ::= BEGIN

IMPORTS

Name, UniqueIdentifier, Certificate
FROM PKIX1Explicit-2009 ;

-- Productions

ServiceDuration ::= INTEGER (1..1024)

FQDN ::= VisibleString (FROM ("a".."z" | "A".."Z" | "0".."9" | ". -") ^ SIZE (1..255))

IPAddress ::= CHOICE {
   ipv4Address [0] OCTET STRING (SIZE (4)),
   ipv6Address [1] OCTET STRING (SIZE (16))
}

SET-Id ::= CHOICE {
   msisdn [0] OCTET STRING (SIZE (8)),
   mdn [1] OCTET STRING (SIZE (8)),
   min [2] BIT STRING  (SIZE (34)),
   imsi [3] OCTET STRING (SIZE (8)),
   nai [4] IA5String (SIZE (1..1000)),
   iPAddress [5] IPAddress,
   ...
}

SLP-Id ::= CHOICE {
   iPAddress [0] IPAddress,
   fQDN [1] FQDN,
   ...
}

AltitudeInfo ::= SEQUENCE {
   altitudeDirection [0] ENUMERATED { height(0), depth(1) },
   altitude [1] INTEGER (0..32767),
   altUncertainty [2] INTEGER (0..127),
   ...
}

PositionEstimate ::= SEQUENCE {
   latitudeSign [0] ENUMERATED { north(0), south(1) },
   latitude [1] INTEGER (0..8388607),
   longitude [2] INTEGER (-8388608..8388607),
   uncertainty [3] SEQUENCE {
      uncertaintySemiMajor [0] INTEGER (0..127),
      uncertaintySemiMinor [1] INTEGER (0..127),
      orientationMajorAxis [2] INTEGER (0..180)
   } OPTIONAL,
   confidence [4] INTEGER (0..100) OPTIONAL,
   altitudeInfo [5] AltitudeInfo OPTIONAL,
   ...
}

Horvel ::= SEQUENCE {
   bearing [0] BIT STRING  (SIZE (9)),
   horspeed [1] BIT STRING  (SIZE (16)),
   ...
}

Horandvervel ::= SEQUENCE {
   verdirect [0] BIT STRING  (SIZE (1)),
   bearing [1] BIT STRING  (SIZE (9)),
   horspeed [2] BIT STRING  (SIZE (16)),
   verspeed [3] BIT STRING  (SIZE (8)),
   ...
}

Horveluncert ::= SEQUENCE {
   bearing [0] BIT STRING  (SIZE (9)),
   horspeed [1] BIT STRING  (SIZE (16)),
   uncertspeed [2] BIT STRING  (SIZE (8)),
   ...
}

Horandveruncert ::= SEQUENCE {
   verdirect [0] BIT STRING  (SIZE (1)),
   bearing [1] BIT STRING  (SIZE (9)),
   horspeed [2] BIT STRING  (SIZE (16)),
   verspeed [3] BIT STRING  (SIZE (8)),
   horuncertspeed [4] BIT STRING  (SIZE (8)),
   veruncertspeed [5] BIT STRING  (SIZE (8)),
   ...
}

Velocity ::= CHOICE {
   horvel [0] Horvel,
   horandvervel [1] Horandvervel,
   horveluncert [2] Horveluncert,
   horandveruncert [3] Horandveruncert,
   ...
}

Position ::= SEQUENCE {
   timestamp [0] UTCTime,
   positionEstimate [1] PositionEstimate,
   velocity [2] Velocity OPTIONAL,
   ...
}

SET-Token-Body ::= SEQUENCE {
   sET-Id SET-Id,
   sLP-Id SLP-Id,
   dSLP-ID SLP-Id,
   sET-Position Position OPTIONAL,
   time UTCTime,
   duration ServiceDuration,
   sLP-Name Name OPTIONAL,
   sLP-Unique-ID [1] UniqueIdentifier OPTIONAL,
   publicKey BIT STRING  OPTIONAL,
   ...
}

AlgorithmIdentifier ::= SEQUENCE {
   algorithm [0] OBJECT IDENTIFIER,
   parameters [1] ANY OPTIONAL
}

SET-Token-Content ::= SEQUENCE {
   sET-Token-Body [0] SET-Token-Body,
   signatureAlgorithm [1] AlgorithmIdentifier,
   sLPSignature [2] BIT STRING 
}

SLP-Certificate-Content ::= SEQUENCE (SIZE (1..maxCert)) OF Certificate

-- Value assignments

maxCert INTEGER ::= 5


END
