CSTA-escape-register-cancel
	{ iso( 1) identified-organization( 3) icd-ecma( 12)
		standard( 0) csta3( 285) escape-register-cancel( 367) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
EscapeRegisterID FROM CSTA-escape-types
	{ iso( 1) identified-organization( 3) icd-ecma( 12)
		standard( 0) csta3( 285) escape-types( 135) };

escapeRegisterCancel OPERATION ::=
{	ARGUMENT		EscapeRegisterCancelArgument
	RESULT			EscapeRegisterCancelResult
	ERRORS			{universalFailure }
	CODE			local: 367 }

EscapeRegisterCancelArgument ::= SEQUENCE 
{	escapeRegisterID		EscapeRegisterID,
	extensions			CSTACommonArguments			OPTIONAL }

EscapeRegisterCancelResult  ::= CHOICE
{	extensions			CSTACommonArguments,
	noData				NULL }

END -- of CSTA-escape-register-cancel
