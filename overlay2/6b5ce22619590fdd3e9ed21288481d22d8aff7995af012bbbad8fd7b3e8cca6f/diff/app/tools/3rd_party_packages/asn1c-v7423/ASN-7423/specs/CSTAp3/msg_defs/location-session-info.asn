CSTA-location-session-info
{ iso( 1) identified-organization( 3) icd-ecma( 12)
standard( 0) csta3( 285) location-session-info( 541) }

DEFINITIONS ::=
BEGIN

IMPORTS
OPERATION, ERROR FROM Remote-Operations-Information-Objects 
	{joint-iso-itu-t remote-operations(4) informationObjects(5) version1(0) }

-- Data Types --
universalFailure FROM CSTA-error-definition
{ iso( 1) identified-organization( 3) icd-ecma( 12)
standard( 0) csta3( 285) error-definition( 120) }
CSTACommonArguments FROM CSTA-extension-types
{ iso( 1) identified-organization( 3) icd-ecma( 12)
standard( 0) csta3( 285) extension-types( 129) }
DeviceID FROM CSTA-device-identifiers
{ iso( 1) identified-organization( 3) icd-ecma( 12)
standard( 0) csta3( 285) device-identifiers( 123) }
LocationSessionInfoList FROM CSTA-status-reporting
{ iso( 1) identified-organization( 3) icd-ecma( 12)
standard( 0) csta3( 285) status-reporting( 126) }
ServiceCrossRefID FROM CSTA-capability-exchange
	{ iso( 1) identified-organization( 3) icd-ecma( 12)
		standard( 0) csta3( 285) capability-exchange( 131) };

locationSessionInfoReport OPERATION ::=
{ 	ARGUMENT		LocationSessionInfoArgument
	ERRORS			{universalFailure }
	CODE 			local: 541}

LocationSessionInfoArgument ::= SEQUENCE
{	serviceCrossRefID		ServiceCrossRefID			OPTIONAL,
	segmentID			INTEGER					OPTIONAL,
	lastSegment			BOOLEAN,
	locationSessionInfoList		LocationSessionInfoList,
	extensions			CSTACommonArguments			OPTIONAL }

END -- of CSTA-location-session-info
