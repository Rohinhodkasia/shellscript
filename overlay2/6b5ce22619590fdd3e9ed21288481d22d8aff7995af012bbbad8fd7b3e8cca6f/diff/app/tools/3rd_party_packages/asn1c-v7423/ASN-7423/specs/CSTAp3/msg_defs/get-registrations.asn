CSTA-get-registrations
	{ iso( 1) identified-organization( 3) icd-ecma( 12)
		standard( 0) csta3( 285) get-registrations( 371) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
RegistrationTypeList FROM CSTA-status-reporting
	{ iso( 1) identified-organization( 3) icd-ecma( 12)
		standard( 0) csta3( 285) status-reporting( 126) }
ServiceCrossRefID FROM CSTA-capability-exchange
	{ iso( 1) identified-organization( 3) icd-ecma( 12)
		standard( 0) csta3( 285) capability-exchange( 131) }
RegistrationList FROM CSTA-status-reporting
	{ iso( 1) identified-organization( 3) icd-ecma( 12)
		standard( 0) csta3( 285) status-reporting( 126) }
CSTACommonArguments FROM CSTA-extension-types
	{ iso( 1) identified-organization( 3) icd-ecma( 12)
		standard( 0) csta3( 285) extension-types( 129) };

getRegistrations OPERATION ::=
{ 	ARGUMENT 		GetRegistrationsArg
	RESULT 			GetRegistrationsRes
	ERRORS 			{universalFailure }
	CODE 			local: 371 }

GetRegistrationsArg ::= SEQUENCE
{ 	requestedRegTypes 		RegistrationTypeList		OPTIONAL,
	extensions 			CSTACommonArguments 		OPTIONAL }

GetRegistrationsRes ::= SEQUENCE
{ 	crossRefIDorRegistrationData	CHOICE
	{	serviceCrossRefID	ServiceCrossRefID,
		registrationList	RegistrationList },
	extensions 			CSTACommonArguments 		OPTIONAL }

END -- of CSTA-get-registrations
