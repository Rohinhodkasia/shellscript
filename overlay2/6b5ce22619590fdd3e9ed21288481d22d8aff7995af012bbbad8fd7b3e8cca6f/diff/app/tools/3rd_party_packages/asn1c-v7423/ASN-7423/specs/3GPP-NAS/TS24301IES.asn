TS24301IES DEFINITIONS AUTOMATIC TAGS ::= BEGIN

IMPORTS IMEI, IMSI, MCCMNCPair, TBCDString, TimeZoneAndTime FROM TS24008IES ;

-- Common types

/* 9.9.2.1 - EPS bearer context status */

EPSBearerContextStatus ::= SEQUENCE {
   --<is3GLength/>
   length INTEGER (2), 

   -- first octet
   ebi7  BOOLEAN, 
   ebi6  BOOLEAN, 
   ebi5  BOOLEAN, 
   ebi4  BOOLEAN, 
   ebi3  BOOLEAN, 
   ebi2  BOOLEAN, 
   ebi1  BOOLEAN, 
   ebi0  BOOLEAN DEFAULT FALSE, 

   -- 2nd octet
   ebi15 BOOLEAN, 
   ebi14 BOOLEAN, 
   ebi13 BOOLEAN, 
   ebi12 BOOLEAN, 
   ebi11 BOOLEAN, 
   ebi10 BOOLEAN, 
   ebi9  BOOLEAN, 
   ebi8  BOOLEAN 
}

/* 9.9.2.6 - NAS security parameters from E-UTRA */

NASSecParamsFromEUTRA ::= SEQUENCE {
   spare INTEGER (0..15) DEFAULT 0, 
   dlNASCount INTEGER (0..15)
}

/* 9.9.2.7 - NAS security parameters to E-UTRA */

NASSecParamsToEUTRA ::= SEQUENCE {
   nonceMMEValue OCTET STRING (SIZE (4)),
   spare1 BOOLEAN DEFAULT FALSE, 
   typeOfCiphAlg INTEGER (0..7), 
   spare2 BOOLEAN DEFAULT FALSE, 
   typeOfProtAlg INTEGER (0..7), 
   spare3 INTEGER (0..15) DEFAULT 0, 
   tsc BOOLEAN, 
   nasKeySetIdent INTEGER (0..7)
}

/* 9.9.3 - EPS Mobility Management (EMM) information elements */

/* 9.9.3.0A - Additional update result */

AddnUpdateResult ::= SEQUENCE {
   spare INTEGER (0..3) DEFAULT 0,
   value ENUMERATED { noInfo(0), csFbNotPref(1), smsOnly(2), reserved(3) }
}

/* 9.9.3.0B - Additional update type */

AddnUpdateType ::= SEQUENCE {
   pnb_CIoT ENUMERATED { 
      noAddInfo(0), cpCIotEpsPref(1), upCIotEpsPref(2), reserved(3) 
   },
   saf  BOOLEAN,
   autv BOOLEAN
}

/* 9.9.3.4 - Authentication response parameter */

AuthRespParam ::= OCTET STRING (SIZE (4..16))

/* 9.9.3.4B - SMS services status */

SMSServicesStatus ::= SEQUENCE {
   spare BOOLEAN DEFAULT FALSE, 
   value INTEGER (0..7) 
}

/* 9.9.3.5 - CSFB response */

CSFBResponse ::= SEQUENCE {
   spare BOOLEAN DEFAULT FALSE, 
   value INTEGER (0..7) 
}

/* 9.9.3.7 - Detach type */

DetachType ::= SEQUENCE {
   switchOff BOOLEAN, 
   typeOfDetach INTEGER (0..7)
}

/* 9.9.3.9 - EMM cause */

EMMCause ::= ENUMERATED { 
   imsiUnkInHSS(2), illegalUE(3), imeiNotAccept(5), illegalME(6), 
   epsSvcNotAllowed(7), epsAndNonEPSSvcNotAllowed(8), ueIdentNotDeriv(9), 
   implDetach(10), plmnNotAllowed(11), trkAreaNotAllowed(12), 
   roamNotAllowed(13), epsSvcNotAllowInPLMN(14), noCellsInTrkArea(15), 
   mscTempNotReach(16), networkFailure(17), csDomainNotAvail(18), 
   esmFailure(19), macFailure(20), synchFailure(21), congestion(22), 
   ueSecCapMismat(23), secModeReject(24), notAuthForCSG(25), 
   nonEPSAuthUnaccept(26), redirTo5GRequired(31), reqSvcOptNotAuth(35),
   csSvcTempUnavail(39), noEPSBearerCtxtAct(40), severeNetFailure(42),
   semIncorrectMsg(95), invMandInfo(96), msgTypeNotExist(97),
   msgTypeNotCompat(98), infoElemNotExist(99), condIEError(100),
   msgNotCompat(101), unspecProtoErr(111), eMMCauseMAX(255)
}

/* 9.9.3.10 - EPS attach result */

EPSAttachResult ::= SEQUENCE {
   spare BOOLEAN DEFAULT FALSE, 
   result INTEGER (0..7)
}

/* 9.9.3.11 - EPS attach type */

EPSAttachType ::= SEQUENCE {
   spare BOOLEAN DEFAULT FALSE, 
   value INTEGER (0..7)
}

/* 9.9.3.12 - EPS mobile identity */

EPSMobileIdentity-GUTI ::= SEQUENCE {
   mcc-mnc MCCMNCPair, 
   mmeGroupID OCTET STRING (SIZE (2)),
   mmeCode INTEGER (0..255),
   tmsi OCTET STRING (SIZE (4))
}

EPSMobileIdentity ::= SEQUENCE {
   --<is3GLength/>
   length INTEGER (0..255), 
   filler INTEGER (0..15) DEFAULT 15, 
   oddEvenInd BOOLEAN, 
   typeOfIdent ENUMERATED { imsi(1), imei(3), guti(6) }, 
   --<inline/>
   content CHOICE {
      --<selector element="typeOfIdent" value="6"/>
      guti EPSMobileIdentity-GUTI, 
      --<selector element="typeOfIdent" value="1"/>
      imsi IMSI, 
      --<selector element="typeOfIdent" value="3"/>
      imei IMEI
   }
}

/* 9.9.3.12A - EPS network feature support */

EPSNetworkFeatureSupport ::= SEQUENCE {
   --<is3GLength/>
   length   INTEGER (1..2) DEFAULT 1,
   cpCIoT   BOOLEAN,
   erNoPDN  BOOLEAN,
   esr      BOOLEAN,
   csLCS    INTEGER (0..3),
   epcLCS   BOOLEAN,
   emcBS    BOOLEAN,
   imsVoPS  BOOLEAN,

   --<noPresentBit/>
   --<inline/>
   octet4 SEQUENCE {
      sigEPSBC BOOLEAN,
      iwkN26   BOOLEAN,
      rDCNR    BOOLEAN,
      rEC      BOOLEAN,
      ePCO     BOOLEAN,
      hcCpCIoT BOOLEAN,
      s1DT     BOOLEAN,
      upCIot   BOOLEAN
   } OPTIONAL
}

/* 9.9.3.13 - EPS update result */

EPSUpdateResult ::= SEQUENCE {
   spare BOOLEAN DEFAULT FALSE,
   result INTEGER (0..7)
}

/* 9.9.3.14 - EPS update type */

EPSUpdateType ::= SEQUENCE {
   active BOOLEAN, 
   value  INTEGER (0..7)
}

/* 9.9.3.15 - ESM message container */

--<length fixed-size="2"/>
ESMMessageContainer ::= OCTET STRING (SIZE (0..65535))

/* 9.9.3.19 - KSI and sequence number */

KSIAndSequenceNumber ::= SEQUENCE {
   ksi   INTEGER (0..7), 
   seqNo INTEGER (0..31)
}

/* 9.9.3.21 - NAS key set identifier */

NASKeySetIdentifier ::= SEQUENCE {
   tsc   BOOLEAN, 
   ident INTEGER (0..7)
}

/* 9.9.3.22 - NAS message container */

NASMessageContainer ::= OCTET STRING (SIZE (2..251))

/* 9.9.3.23 - NAS security algorithms */

NASSecurityAlgorithms ::= SEQUENCE {
   spare1 BOOLEAN DEFAULT FALSE, 
   typeOfCiph ENUMERATED {
      eea0(0), x128-eea1(1), x128-eea2(2), eea3(3), eea4(4), 
      eea5(5), eea6(6), eea7(7)
   },
   spare2 BOOLEAN DEFAULT FALSE, 
   typeOfProt ENUMERATED {
      eia0(0), x128-eia1(1), x128-eia2(2), eia3(3), eia4(4), 
      eia5(5), eia6(6), eia7(7)
   }
}

/* 9.9.3.25 - Nonce */

Nonce ::= OCTET STRING (SIZE (4))

/* 9.9.3.25A - Paging identity */

PagingIdentity ::= SEQUENCE {
   spare INTEGER (0..127) DEFAULT 0, 
   ident ENUMERATED { imsi(0), tmsi(1) }
}

/* 9.9.3.26A - Extended EMM cause */

ExtEMMCause ::= SEQUENCE {
   spare BOOLEAN DEFAULT FALSE,
   nbiotAllowed BOOLEAN,
   epsOptInfo BOOLEAN,
   e-UTRAN-NotAllowed BOOLEAN
}

/* 9.9.3.27 - Service type */

ServiceType ::= INTEGER { 
   moCSFallback(0), mtCSFallBack(1), moCSFBEmergCall(2), pktSvcsViaS1(8)
} (0..15)

/* 9.9.3.28 - Short MAC */

ShortMAC ::= OCTET STRING (SIZE (2))

/* 9.9.3.32 - Tracking area identity */

TrackingAreaIdent ::= SEQUENCE {
   mcc-mnc MCCMNCPair, 
   tac TrackingAreaCode
}

TrackingAreaCode ::= OCTET STRING (SIZE (2))

/* 9.9.3.33 - Tracking area identity list */

TrackingAreaIdentList ::= SEQUENCE {
   --<is3GLength/>
   length INTEGER (6..96), 
   --<is3GVarLenList lengthElem="length"/>
   --<storage>array</storage>
   idents SEQUENCE (SIZE (1..16)) OF TrackingAreaIdentListItem
}

TrackingAreaIdentListItem ::= SEQUENCE {
   spare BOOLEAN DEFAULT FALSE, 
   typeOfList INTEGER (0..2), 
   numElements INTEGER (0..31), 
   --<inline/>
   elements CHOICE {
      --<selector element="typeOfList" value="0"/>
      --<asn1typename>PartialTrkAreaIdent0</asn1typename>
      partTrkIdentList0 SEQUENCE {
         mcc-mnc MCCMNCPair, 
         --<inline/>
         --<length expr="@...numElements+1"/>
         tacs SEQUENCE (SIZE (1..32)) OF tac TrackingAreaCode
      }, 
      --<selector element="typeOfList" value="1"/>
      --<asn1typename>PartialTrkAreaIdent1</asn1typename>
      partTrkIdentList1 SEQUENCE {
         mcc-mnc MCCMNCPair, 
         tac TrackingAreaCode
      }, 
      --<selector element="typeOfList" value="2"/>
      --<asn1typename>PartialTrkAreaIdent2</asn1typename>
      --<length expr="@.numElements+1"/>
      partTrkIdentList2 SEQUENCE (SIZE (1..32)) OF TrackingAreaIdent 
   }
}


/* 9.9.3.34 - UE network capability */

UENetworkCapability ::= SEQUENCE {
   --<is3GLength/>
   length INTEGER (1..255), 

   -- EPS encryption algorithms supported
   epsEncryptAlgs EPSEncryptAlgsSupported, 

   -- EPS integrity algorithms supported 
   epsIntegAlgs EPSIntegAlgsSupported, 

   -- UMTS encryption algorithms supported
   --<noPresentBit/>
   umtsEncryptAlgs UMTSEncryptAlgsSupported OPTIONAL, 

   --<noPresentBit/>
   --<inline/>
   octet6 SEQUENCE {
      -- UCS2 character string support
      ucs2 BOOLEAN, 

      -- UMTS integrity algorithms supported 
      umtsIntegAlgs UMTSIntegAlgsSupported 
   } OPTIONAL,

   --<noPresentBit/>
   --<inline/>
   octet7 SEQUENCE {
      proSedd BOOLEAN, 
      proSe BOOLEAN,
      h245-ash BOOLEAN, 
      acc-csfb BOOLEAN, 
      lpp BOOLEAN, 
      lcs BOOLEAN, 
      x1xSR-VCC BOOLEAN, 
      nf BOOLEAN
   } OPTIONAL, 

   --<noPresentBit/>
   --<inline/>
   octet8 SEQUENCE {
      ePCO BOOLEAN, 
      hc-CP-CIoT BOOLEAN, 
      erwoPDN BOOLEAN, 
      s1-Udata BOOLEAN, 
      upCIoT BOOLEAN, 
      cpCIoT BOOLEAN, 
      prose-relay BOOLEAN, 
      proSedc BOOLEAN
   } OPTIONAL, 

   --<noPresentBit/>
   --<inline/>
   octet9 SEQUENCE {
      bearers BOOLEAN,
      sgc BOOLEAN,
      n1Mode BOOLEAN,
      dcnr BOOLEAN,
      cpBackoff BOOLEAN,
      restrictEC BOOLEAN,
      v2xPC5 BOOLEAN,
      multDRB BOOLEAN
   } OPTIONAL,

   --<noPresentBit/>
   --<inline/>
   octet10 SEQUENCE {
      spare INTEGER (0..63) DEFAULT 0, 
      wusa BOOLEAN,
      racs BOOLEAN
   } OPTIONAL,

   --<length fixed-size="0"/>
   --<noPresentBit/>
   spare4 OCTET STRING OPTIONAL
}

EPSEncryptAlgsSupported ::= SEQUENCE {
   eea0 BOOLEAN, 
   x128-eea1 BOOLEAN, 
   x128-eea2 BOOLEAN, 
   eea3 BOOLEAN, 
   eea4 BOOLEAN, 
   eea5 BOOLEAN, 
   eea6 BOOLEAN, 
   eea7 BOOLEAN
}

EPSIntegAlgsSupported ::= SEQUENCE {
   eia0 BOOLEAN, 
   eia1 BOOLEAN, 
   eia2 BOOLEAN, 
   eia3 BOOLEAN, 
   eia4 BOOLEAN, 
   eia5 BOOLEAN, 
   eia6 BOOLEAN, 
   eia7 BOOLEAN
}

UMTSEncryptAlgsSupported ::= SEQUENCE {
   uea0 BOOLEAN, 
   uea1 BOOLEAN, 
   uea2 BOOLEAN, 
   uea3 BOOLEAN, 
   uea4 BOOLEAN, 
   uea5 BOOLEAN, 
   uea6 BOOLEAN, 
   uea7 BOOLEAN
}

UMTSIntegAlgsSupported ::= SEQUENCE {
   uia1 BOOLEAN, 
   uia2 BOOLEAN, 
   uia3 BOOLEAN, 
   uia4 BOOLEAN, 
   uia5 BOOLEAN, 
   uia6 BOOLEAN, 
   uia7 BOOLEAN
}

GPRSIntegAlgsSupported ::= SEQUENCE {
   gea1 BOOLEAN, 
   gea2 BOOLEAN, 
   gea3 BOOLEAN, 
   gea4 BOOLEAN, 
   gea5 BOOLEAN, 
   gea6 BOOLEAN, 
   gea7 BOOLEAN
}

/* 9.9.3.35 - UE radio capability information update needed */

UERadioCapInfoUpdateNeeded ::= SEQUENCE {
   spare INTEGER (0..7), 
   value BOOLEAN
}

/* 9.9.3.36 - UE security capability */

UESecurityCapability ::= SEQUENCE {
   --<is3GLength/>
   length INTEGER (2..13), 

   -- EPS encryption algorithms supported
   epsEncryptAlgs EPSEncryptAlgsSupported, 

   -- EPS integrity algorithms supported 
   epsIntegAlgs EPSIntegAlgsSupported, 

   -- UMTS encryption algorithms supported
   --<noPresentBit/>
   umtsEncryptAlgs UMTSEncryptAlgsSupported OPTIONAL, 

   -- EPS integrity algorithms supported 
   --<noPresentBit/>
   --<inline/>
   octet6 SEQUENCE {
      spare BOOLEAN DEFAULT FALSE, 
      umtsIntegAlgs UMTSIntegAlgsSupported
   } OPTIONAL,

   -- GPRS integrity algorithms supported 
   --<noPresentBit/>
   --<inline/>
   octet7 SEQUENCE {
      spare BOOLEAN DEFAULT FALSE, 
      gprsIntegAlgs GPRSIntegAlgsSupported
   } OPTIONAL
}

/* 9.9.3.37a - Extended emergency number list */

ExtEmergencyNumberInfo ::= SEQUENCE {
   number SEQUENCE {
      --<is3GLength/>
      length INTEGER(0..255), 
      --<length fixed-size="0"/>
      digits TBCDString
   },
   subservices SEQUENCE {
      --<is3GLength/>
      subservicesLen INTEGER(0..255),
      --<length fixed-size="0"/>
      subservices OCTET STRING
   }
}

ExtEmergencyNumberList ::=  SEQUENCE {
   --<is3GLength/>
   length INTEGER (0..255), 
   spare INTEGER(0..127) DEFAULT 0,
   catValue BOOLEAN,
   --<is3GVarLenList lengthElem="length"/>
   --<storage>array</storage>
   numberInfo SEQUENCE OF ExtEmergencyNumberInfo
}

/* 9.9.3.38 - CLI */

CLI ::= SEQUENCE {
   --<is3GLength/>
   length INTEGER (0..255),
   --<length fixed-size="0"/>
   value TBCDString
}

/* 9.9.3.39 - SS Code */

SSCode ::= INTEGER (0..255)

/* 9.9.3.40 - LCS indicator */

LCSIndicator ::= INTEGER (0..255)

/* 9.9.3.41 - LCS client identity */

LCSClientIdentity ::= OCTET STRING (SIZE (1..255))

/* 9.9.3.42 - Generic message container type */

GenMsgContainerType ::= ENUMERATED { 
   lppMsgCont(1), lcsMsgCont(2), genMsgContainerTypeMAX(255) 
}

/* 9.9.3.43 - Generic message container */

--<length fixed-size="2"/>
GenMessageContainer ::= OCTET STRING (SIZE (0..65535))

/* 9.9.3.45 - GUTI type */

GUTIType ::= SEQUENCE {
   spare INTEGER (0..7) DEFAULT 0, 
   mapped BOOLEAN -- FALSE = native
}

/* 9.9.3.47 - Control Plane Service Type */

CtrlPlaneSvcType ::= SEQUENCE {
   activeFlag BOOLEAN, 
   svcTypeValue INTEGER (0..7)
      -- 0 = mobile originating request
      -- 1 = mobile terminating request
      -- 2 thru 7 - not used
}

/* 9.9.3.50 - Hash MME */

HashMME ::= SEQUENCE {
   length INTEGER (0..255), 
   hashValue OCTET STRING (SIZE (8))
}

/* 9.9.3.51 - Replayed NAS message container */

ReplayedNASMsgContainer ::= SEQUENCE {
   length INTEGER (0..65535),
   contents OCTET STRING (SIZE (1..65535))
}

/* 9.9.3.52 - Network policy */

NetworkPolicy ::= SEQUENCE {
   spare INTEGER (0..7) DEFAULT 0, 
   redirPolicy BOOLEAN
}

/* 9.9.3.53 - UE additional security capability */

UEAddlSecurityCapability ::= SEQUENCE {
   length INTEGER (0..255),
   contents SEQUENCE (SIZE (32)) OF BOOLEAN
}

/* 9.9.3.54 - UE status */

UEStatus ::= SEQUENCE {
   length INTEGER (0..255) DEFAULT 1,
   spare INTEGER (0..63) DEFAULT 0,
   n1RegStatus BOOLEAN,
   s1RegStatus BOOLEAN
}

/* 9.9.3.55 - Additional information requested */

AdditionalInfoReq ::= SEQUENCE {
   spare INTEGER (0..127) DEFAULT 0,
   dataRequested BOOLEAN
}

/* 9.9.3.56 - Ciphering key data */

CipherDataSet ::= SEQUENCE {
   cipherKey OCTET STRING (SIZE (16)),
   spare INTEGER (0..7) DEFAULT 0,
   c0Len INTEGER (0..31),
   --<length expr="@c0Len"/>
   c0 OCTET STRING,
   posSIBType SEQUENCE (SIZE (27)) OF BOOLEAN,
   spare2 INTEGER (0..31) DEFAULT 0,
   validityStartTime TimeZoneAndTime,
   validityDuration INTEGER (0..65535),
   taiList TrackingAreaIdentList
}

CipherKeyData ::= SEQUENCE {
   --<is3GLength/>
   length INTEGER(0..255),
   --<is3GVarLenList lengthElem="length"/>
   --<storage>array</storage>
   dataSet SEQUENCE (SIZE (1..16)) OF CipherDataSet
}

/* 9.9.3.57 - N1 UE network capability */
N1UENetCapability ::= SEQUENCE {
   length INTEGER (0..255),
   spare INTEGER (0..3) DEFAULT 0,
   pnbCIoT INTEGER (0..3),
   upCIoT BOOLEAN,
   hcCpCIoT BOOLEAN,
   n3Data BOOLEAN,
   cpCIoT BOOLEAN
}

/* 9.9.3.58 - UE radio capability ID availability */
UERadioCapIdAvailability ::= SEQUENCE {
   spare BOOLEAN DEFAULT FALSE,
   value INTEGER (0..7)
}

/* 9.9.3.59 - UE radio capability ID request */
UERadioCapIdRequest ::= SEQUENCE {
   spare INTEGER (0..127) DEFAULT 0,
   urcid-A BOOLEAN
}

/* 9.9.3.60 - UE radio capability ID */
UERadioCapId ::= SEQUENCE {
   length INTEGER (1..255),
   capId OCTET STRING
}

/* 9.9.3.61 - UE radio capability ID deletion indication */
UERadioCapIdDeletionInd ::= SEQUENCE {
   spare BOOLEAN DEFAULT FALSE,
   deletionReq INTEGER (0..7)
}

/* 9.9.3.62 - WUS assistance information - STILL MOSTLY TBD AS OF 16.3 */
WUSAssistanceInfo ::= SEQUENCE {
   --<is3GLength/>
   length INTEGER(0..255),
   --<is3GVarLenList lengthElem="length"/>
   --<storage>array</storage>
   types SEQUENCE (SIZE (1..255)) OF WUSAssistInfoType
}

WUSAssistInfoType ::= SEQUENCE {
   infoType InformationType,
   infoValue INTEGER (0..31)
}

InformationType ::= ENUMERATED {
   itUEPagingProbInfo(0),  itMAX(7)
}

/* 9.9.4 - EPS Session Management (ESM) information elements */

/* 9.9.4.2 - APN aggregate maximum bit rate */

APNAggMaxBitRate ::= SEQUENCE {
   --<is3GLength/>
   length INTEGER (2..6), 
   apnAmbrforDL INTEGER (0..255), 
   apnAmbrforUL INTEGER (0..255), 
   --<is3GVarLenList lengthElem="length"/>
   --<storage>array</storage>
   ext SEQUENCE (SIZE (0..2)) OF APNAggMaxBitRateExt 
}

APNAggMaxBitRateExt ::= SEQUENCE {
   apnAmbrforDL INTEGER (0..255), 
   apnAmbrforUL INTEGER (0..255)
}

/* 9.9.4.3 - EPS quality of service */

EPSQualityOfService ::= SEQUENCE {
   --<is3GLength/>
   length INTEGER (1|5|9|13), 
   qci INTEGER (0..255), 
   --<is3GVarLenList lengthElem="length"/>
   --<storage>array</storage>
   bitRates SEQUENCE (SIZE (0..3)) OF EPSQoSBitRates 
}

EPSQoSBitRates ::= SEQUENCE {
   maxBitRateforUL INTEGER (0..255), 
   maxBitRateforDL INTEGER (0..255), 
   guarBitRateforUL INTEGER (0..255), 
   guarBitRateforDL INTEGER (0..255)
}

/* 9.9.4.4 - ESM cause */

ESMCause ::= ENUMERATED {
 operDeterBarring(8), 
 insuffResources(26), 
 unkOrMissAPN(27),
 unknownPDNType(28),
 userAutheFailed(29),
 reqRejectByServingGW(30),
 reqRejectUnspecified(31),
 svcOptNotSupp(32),
 reqSvcOptNotSubscr(33),
 svcOptTempOutOfOrder(34),
 ptiAlreadyInUse(35),
 regularDeactivation(36),
 epsQoSNotAccepted(37),
 networkFailure(38),
 reactivateRequest(39), 
 semErrorInTFTOp(41),
 synErrorInTFTOp(42),
 invEPSBearerIdent(43),
 semErrorsInPktFilt(44),
 synErrorsInPktFilt(45),
 ptiMismatch(47),
 lastPDNDisconnNotAllow(49),
 pdnTypeIPv4OnlyAllow(50),
 pdnTypeIPv6OnlyAllow(51),
 singleAddrBearersOnlyAllow(52),
 esmInfoNotRcvd(53),
 pdnConnNotExist(54),
 multPDNConnsForAPNNotAllow(55),
 collWithNetwInitReq(56),
 pdnTypeIPv4v6OnlyAllow(57),
 pdnTypeNonIPOnlyAllow(58),
 unsuppQCIValue(59),
 bearerHandlingNotSupp(60), 
 pdnTypeEthOnlyAllow(61), 
 maxNumEPSBearersReached(65), 
 reqAPNNotSupp(66), 
 invPTIValue(81),
 semIncorrectMessage(95),
 invMandatoryInfo(96),
 msgTypeNonExistOrNotImpl(97),
 msgTypeNotCompatWithProtoState(98),
 ieNonExistOrNotImpl(99),
 condIEError(100),
 msgNotCompatWithProtoState(101),
 protocolErrorUnspecified(111),
 apnRestrValIncompWithBearerCtxt(112),
 multAccToPdnNotAllowed(113),
 eSMCauseMAX(255)
}

/* 9.9.4.5 - ESM information transfer flag */

ESMInfoXferFlag ::= SEQUENCE {
   spare INTEGER (0..7) DEFAULT 0, 
   eitValue BOOLEAN
}

/* 9.9.4.6 - Linked EPS bearer identity */

LinkedEPSBearerIdent ::= INTEGER (0..15)

/* 9.9.4.9 - PDN address */

PDNAddress ::= SEQUENCE {
   --<is3GLength/>
   length INTEGER (5..13), 
   spare INTEGER (0..31) DEFAULT 0, 
   pdnTypeValue PDNTypeValue, 
   --<inline/>
   --<length fixed-size="0"/>
   pdnAddrInfo OCTET STRING (SIZE (4..12))
}

PDNTypeValue ::= ENUMERATED { ipv4(1), ipv6(2), ipv4v6(3), nonip(5), eth(6),
                              pdnMAX(7) }

/* 9.9.4.10 - PDN type */

PDNType ::= SEQUENCE {
   spare BOOLEAN DEFAULT FALSE, 
   pdnTypeValue PDNTypeValue
}

/* 9.9.4.13A - Reattempt indicator */

ReattemptInd ::= SEQUENCE {
   spare INTEGER (0..63) DEFAULT 0,
   eplmNcValue BOOLEAN, 
   ratcValue BOOLEAN
}

/* 9.9.4.20 - Remote UE context list */

RemoteUECtxtList ::= SEQUENCE {
   --<is3GLength bitFieldSize="16"/>
   length INTEGER (5..65535), 
   numRemUECtxts INTEGER (1..255), 
   --<is3GVarLenList lengthElem="length"/>
   remUECtxts SEQUENCE OF RemoteUECtxt,
   spare INTEGER (0..31) DEFAULT 0,
   addrType RemoteUEAddrType,
   addrInfo OCTET STRING (SIZE (6..8))
}

RemoteUECtxt ::= SEQUENCE {
   --<is3GLength/>
   length INTEGER (0..255), 
   numUserIdents INTEGER (0..255),
   userIdentLength INTEGER (0..255),
   --<is3GVarLenList lengthElem="length"/>
   userIdents SEQUENCE OF OCTET STRING
}

RemoteUEAddrType ::= ENUMERATED { remUENoIp(0), remUEIpv4(1),
   remUEIpv6(2), remUEMAX(7) }

/* 9.9.4.21 - PKMF address IE */

PKMFAddress ::= SEQUENCE {
   --<is3GLength/>
   length INTEGER (0..255), 
   --<is3GVarLenList lengthElem="length"/>
   addrs SEQUENCE OF PKMFAddressType
}

PKMFAddressType ::= SEQUENCE {
   spare INTEGER (0..32) DEFAULT 0, 
   addrType INTEGER (0..7), -- 1 = ipv4, 2 = ipv6
   --<length fixed-size="0"/>
   addrInfo OCTET STRING (SIZE (0..16))
}

/* 9.9.4.22 - Header compression configuration */

HdrCompressConfig ::= SEQUENCE {
   --<is3GLength/>
   length INTEGER (3..255), 
   spare1 BOOLEAN DEFAULT FALSE,
   profile104 BOOLEAN,
   profile103 BOOLEAN,
   profile102 BOOLEAN,
   profile006 BOOLEAN,
   profile004 BOOLEAN,
   profile003 BOOLEAN,
   profile002 BOOLEAN,
   maxCID OCTET STRING (SIZE (2)),
   addlSetupType OCTET STRING,
   addlSetupContainer OCTET STRING (SIZE (1..251))
}

/* 9.9.4.23 - Control Plane Only Indication */

CtrlPlaneOnlyInd ::= SEQUENCE {
   spare4 BOOLEAN DEFAULT FALSE,
   spare3 BOOLEAN DEFAULT FALSE,
   spare2 BOOLEAN DEFAULT FALSE,
   cpoiValue BOOLEAN
}

/* 9.9.4.25 - Release assistance indication */

ReleaseAssistInd ::= SEQUENCE {
   spare4 BOOLEAN DEFAULT FALSE, 
   spare3 BOOLEAN DEFAULT FALSE, 
   ddx ENUMERATED { ddxNoInfo, ddxNoTrans, ddxSingleDLTrans, ddxReserved }
}

/* 9.9.4.27 - Header compression configuration status */

HdrCompressConfigStat ::= SEQUENCE {
   --<is3GLength/>
   length INTEGER (2), 
   ebi OCTET STRING (SIZE (2))
}

/* 9.9.4.28 - Serving PLMN rate control */

ServPLMNRateCtrl ::= OCTET STRING (SIZE (2))

/* 9.9.4.29 - Extended APN aggregate maximum bit rate */

ExtAPNAggMaxBitRate ::= SEQUENCE {
   extApnAmbrUnitForDL INTEGER (0..255),
   extApnAmbrForDL OCTET STRING (SIZE (2)),
   extApnAmbrUnitForUL INTEGER (0..255),
   extApnAmbrForUL OCTET STRING (SIZE (2))
}

END
