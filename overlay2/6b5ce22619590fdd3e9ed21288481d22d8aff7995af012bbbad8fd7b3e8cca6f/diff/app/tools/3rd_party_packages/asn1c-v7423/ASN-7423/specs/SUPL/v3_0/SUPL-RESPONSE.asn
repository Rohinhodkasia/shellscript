-- This file was generated by the Objective Systems ASN1C Compiler
-- (http://www.obj-sys.com).  Version: 6.8.A, Date: 18-Nov-2014.

SUPL-RESPONSE DEFINITIONS AUTOMATIC TAGS ::= BEGIN

IMPORTS

PosMethod, SLPAddress
FROM ULP-Components 

Ver2-SUPL-RESPONSE-extension
FROM ULP-Version-2-message-extensions 

Ver3-SUPL-RESPONSE-extension
FROM ULP-Version-3-message-extensions ;

-- Productions

SETAuthKey ::= CHOICE {
   shortKey [0] BIT STRING  (SIZE (128)),
   longKey [1] BIT STRING  (SIZE (256)),
   ...
}

KeyIdentity4 ::= BIT STRING  (SIZE (128))

SUPLRESPONSE ::= SEQUENCE {
   posMethod [0] PosMethod,
   sLPAddress [1] SLPAddress OPTIONAL,
   sETAuthKey [2] SETAuthKey OPTIONAL,
   keyIdentity4 [3] KeyIdentity4 OPTIONAL,
   ...,
   ver2-SUPL-RESPONSE-extension [4] Ver2-SUPL-RESPONSE-extension OPTIONAL,
   ver3-SUPL-RESPONSE-extension [5] Ver3-SUPL-RESPONSE-extension OPTIONAL
}

END
