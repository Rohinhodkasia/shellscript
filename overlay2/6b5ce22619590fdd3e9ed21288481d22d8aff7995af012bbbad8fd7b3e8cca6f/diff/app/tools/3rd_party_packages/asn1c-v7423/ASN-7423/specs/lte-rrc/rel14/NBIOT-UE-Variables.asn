-- This file was generated by the Objective Systems ASN1C Compiler
-- (http://www.obj-sys.com).  Version: 7.4.2, Date: 15-Jun-2020.

NBIOT-UE-Variables DEFINITIONS AUTOMATIC TAGS ::= BEGIN

IMPORTS

VarShortMAC-Input, VarShortResumeMAC-Input-r13
FROM EUTRA-UE-Variables ;

-- Productions

VarShortMAC-Input-NB-r13 ::= VarShortMAC-Input

VarShortResumeMAC-Input-NB-r13 ::= VarShortResumeMAC-Input-r13

END
