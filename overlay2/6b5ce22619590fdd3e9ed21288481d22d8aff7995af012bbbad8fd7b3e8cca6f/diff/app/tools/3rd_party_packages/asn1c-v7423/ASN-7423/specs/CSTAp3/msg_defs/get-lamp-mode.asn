CSTA-get-lamp-mode
{ iso( 1) identified-organization( 3) icd-ecma( 12)
	standard( 0) csta3( 285) get-lamp-mode( 266) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) }
ButtonID, LampID, LampColor, LampMode, LampBrightness 
FROM CSTA-physical-device-feature 
	{ iso( 1) identified-organization( 3) icd-ecma( 12)
		standard( 0) csta3( 285) physical-device-feature( 137) };

getLampMode OPERATION ::=
{	ARGUMENT 		GetLampModeArgument
	RESULT			GetLampModeResult
	ERRORS			{universalFailure }
	CODE			local: 	266 }

GetLampModeArgument ::= SEQUENCE
{	device 				DeviceID,
	lamp 				LampID					OPTIONAL,
	extensions 			CSTACommonArguments			OPTIONAL }

GetLampModeResult ::= SEQUENCE
{	lampModeList			LampModeList,
	lamp				LampID					OPTIONAL,
	extensions 			CSTACommonArguments			OPTIONAL }

LampModeList ::= SEQUENCE OF SEQUENCE
{	lamp				LampID,
	lampMode			LampMode,
	lampBrightness			[0] IMPLICIT LampBrightness		OPTIONAL,
	lampColor			[1] IMPLICIT LampColor			OPTIONAL,
	button				[2] IMPLICIT ButtonID			OPTIONAL }

END -- of CSTA-get-lamp-mode
