-- This file was generated by the Objective Systems ASN1C Compiler
-- (http://www.obj-sys.com).  Version: 6.8.A, Date: 15-Nov-2014.

ULP-Version-2-parameter-extensions DEFINITIONS AUTOMATIC TAGS ::= BEGIN

IMPORTS

GANSSSignals, ReportingCap
FROM Ver2-ULP-Components 

maxNumGeoArea, maxAreaId, maxAreaIdList
FROM SUPL-TRIGGERED-START ;

-- Productions

Ver2-Notification-extension ::= SEQUENCE {
   emergencyCallLocation [0] NULL OPTIONAL,
   ...
}

PosProtocolVersion3GPP ::= SEQUENCE {
   majorVersionField [0] INTEGER (0..255),
   technicalVersionField [1] INTEGER (0..255),
   editorialVersionField [2] INTEGER (0..255),
   ...
}

Supported3GPP2PosProtocolVersion ::= SEQUENCE {
   revisionNumber [0] BIT STRING  (SIZE (6)),
   pointReleaseNumber [1] INTEGER (0..255),
   internalEditLevel [2] INTEGER (0..255),
   ...
}

PosProtocolVersion3GPP2 ::= SEQUENCE (SIZE (1..8)) OF 
   Supported3GPP2PosProtocolVersion

GANSSPositioningMethodTypes ::= SEQUENCE {
   setAssisted [0] BOOLEAN,
   setBased [1] BOOLEAN,
   autonomous [2] BOOLEAN,
   ...
}

GANSSPositionMethod ::= SEQUENCE {
   ganssId [0] INTEGER (0..15),
   ganssSBASid [1] BIT STRING  (SIZE (3)) OPTIONAL,
   gANSSPositioningMethodTypes [2] GANSSPositioningMethodTypes,
   gANSSSignals [3] GANSSSignals,
   ...
}

GANSSPositionMethods ::= SEQUENCE (SIZE (1..16)) OF GANSSPositionMethod

Ver2-PosTechnology-extension ::= SEQUENCE {
   gANSSPositionMethods [0] GANSSPositionMethods OPTIONAL,
   ...
}

PosProtocolVersionOMA ::= SEQUENCE {
   majorVersionField [0] INTEGER (0..255),
   minorVersionField [1] INTEGER (0..255),
   ...
}

Ver2-PosProtocol-extension ::= SEQUENCE {
   lpp [0] BOOLEAN,
   posProtocolVersionRRLP [1] PosProtocolVersion3GPP OPTIONAL,
   posProtocolVersionRRC [2] PosProtocolVersion3GPP OPTIONAL,
   posProtocolVersionTIA801 [3] PosProtocolVersion3GPP2 OPTIONAL,
   posProtocolVersionLPP [4] PosProtocolVersion3GPP OPTIONAL,
   ...,
   lppe [5] BOOLEAN OPTIONAL,
   posProtocolVersionLPPe [6] PosProtocolVersionOMA OPTIONAL
}

ServicesSupported ::= SEQUENCE {
   periodicTrigger [0] BOOLEAN,
   areaEventTrigger [1] BOOLEAN,
   ...
}

GeoAreaShapesSupported ::= SEQUENCE {
   ellipticalArea [0] BOOLEAN,
   polygonArea [1] BOOLEAN,
   ...
}

EventTriggerCapabilities ::= SEQUENCE {
   geoAreaShapesSupported [0] GeoAreaShapesSupported,
   maxNumGeoAreaSupported [1] INTEGER (0..maxNumGeoArea) OPTIONAL,
   maxAreaIdListSupported [2] INTEGER (0..maxAreaIdList) OPTIONAL,
   maxAreaIdSupportedPerList [3] INTEGER (0..maxAreaId) OPTIONAL,
   ...
}

SessionCapabilities ::= SEQUENCE {
   maxNumberTotalSessions [0] INTEGER (1..128),
   maxNumberPeriodicSessions [1] INTEGER (1..32),
   maxNumberTriggeredSessions [2] INTEGER (1..32),
   ...
}

ServiceCapabilities ::= SEQUENCE {
   servicesSupported [0] ServicesSupported,
   reportingCapabilities [1] ReportingCap OPTIONAL,
   eventTriggerCapabilities [2] EventTriggerCapabilities OPTIONAL,
   sessionCapabilities [3] SessionCapabilities,
   ...
}

SupportedBearers ::= SEQUENCE {
   gsm [0] BOOLEAN,
   wcdma [1] BOOLEAN,
   lte [2] BOOLEAN,
   cdma [3] BOOLEAN,
   hprd [4] BOOLEAN,
   umb [5] BOOLEAN,
   wlan [6] BOOLEAN,
   wiMAX [7] BOOLEAN,
   ...
}

Ver2-SETCapabilities-extension ::= SEQUENCE {
   serviceCapabilities [0] ServiceCapabilities OPTIONAL,
   ...,
   supportedBearers [1] SupportedBearers OPTIONAL
}

GanssRequestedCommonAssistanceDataList ::= SEQUENCE {
   ganssReferenceTime [0] BOOLEAN,
   ganssIonosphericModel [1] BOOLEAN,
   ganssAdditionalIonosphericModelForDataID00 [2] BOOLEAN,
   ganssAdditionalIonosphericModelForDataID11 [3] BOOLEAN,
   ganssEarthOrientationParameters [4] BOOLEAN,
   ...,
   ganssAdditionalIonosphericModelForDataID01 [5] BOOLEAN OPTIONAL
}

DGANSS-Sig-Id-Req ::= BIT STRING  (SIZE (8))

SatellitesListRelatedData ::= SEQUENCE {
   satId [0] INTEGER (0..63),
   iod [1] INTEGER (0..1023),
   ...
}

SatellitesListRelatedDataList ::= SEQUENCE (SIZE (0..maxGANSSSat)) OF 
   SatellitesListRelatedData

GanssNavigationModelData ::= SEQUENCE {
   ganssWeek [0] INTEGER (0..4095),
   ganssToe [1] INTEGER (0..167),
   t-toeLimit [2] INTEGER (0..15),
   satellitesListRelatedDataList [3] SatellitesListRelatedDataList OPTIONAL,
   ...
}

ReqDataBitAssistanceList ::= SEQUENCE {
   gnssSignals [0] GANSSSignals,
   ganssDataBitInterval [1] INTEGER (0..15),
   ganssDataBitSatList [2] SEQUENCE (SIZE (1..maxGANSSSat)) OF INTEGER (0..63) OPTIONAL,
   ...
}

GanssDataBits ::= SEQUENCE {
   ganssTODmin [0] INTEGER (0..59),
   reqDataBitAssistanceList [1] ReqDataBitAssistanceList,
   ...
}

GanssAdditionalDataChoices ::= SEQUENCE {
   orbitModelID [0] INTEGER (0..7) OPTIONAL,
   clockModelID [1] INTEGER (0..7) OPTIONAL,
   utcModelID [2] INTEGER (0..7) OPTIONAL,
   almanacModelID [3] INTEGER (0..7) OPTIONAL,
   ...
}

ExtendedEphemeris ::= SEQUENCE {
   validity [0] INTEGER (1..256),
   ...
}

GANSSextEphTime ::= SEQUENCE {
   gANSSday [0] INTEGER (0..8191),
   gANSSTODhour [1] INTEGER (0..23),
   ...
}

GanssExtendedEphCheck ::= SEQUENCE {
   beginTime [0] GANSSextEphTime,
   endTime [1] GANSSextEphTime,
   ...
}

BDS-Sig-Id-Req ::= BIT STRING  (SIZE (8))

GanssReqGenericData ::= SEQUENCE {
   ganssId [0] INTEGER (0..15),
   ganssSBASid [1] BIT STRING  (SIZE (3)) OPTIONAL,
   ganssRealTimeIntegrity [2] BOOLEAN,
   ganssDifferentialCorrection [3] DGANSS-Sig-Id-Req OPTIONAL,
   ganssAlmanac [4] BOOLEAN,
   ganssNavigationModelData [5] GanssNavigationModelData OPTIONAL,
   ganssTimeModels [6] BIT STRING  (SIZE (16)) OPTIONAL,
   ganssReferenceMeasurementInfo [7] BOOLEAN,
   ganssDataBits [8] GanssDataBits OPTIONAL,
   ganssUTCModel [9] BOOLEAN,
   ganssAdditionalDataChoices [10] GanssAdditionalDataChoices OPTIONAL,
   ganssAuxiliaryInformation [11] BOOLEAN,
   ganssExtendedEphemeris [12] ExtendedEphemeris OPTIONAL,
   ganssExtendedEphemerisCheck [13] GanssExtendedEphCheck OPTIONAL,
   ...,
   bds-DifferentialCorrection [14] BDS-Sig-Id-Req OPTIONAL,
   bds-GridModelReq [15] BOOLEAN OPTIONAL
}

GanssRequestedGenericAssistanceDataList ::= SEQUENCE (SIZE (1..maxGANSS)) OF 
   GanssReqGenericData

GPSTime ::= SEQUENCE {
   gPSWeek [0] INTEGER (0..1023),
   gPSTOWhour [1] INTEGER (0..167),
   ...
}

ExtendedEphCheck ::= SEQUENCE {
   beginTime [0] GPSTime,
   endTime [1] GPSTime,
   ...
}

Ver2-RequestedAssistData-extension ::= SEQUENCE {
   ganssRequestedCommonAssistanceDataList [0] 
      GanssRequestedCommonAssistanceDataList OPTIONAL,
   ganssRequestedGenericAssistanceDataList [1] 
      GanssRequestedGenericAssistanceDataList OPTIONAL,
   extendedEphemeris [2] ExtendedEphemeris OPTIONAL,
   extendedEphemerisCheck [3] ExtendedEphCheck OPTIONAL,
   ...
}

Ver2-PosPayLoad-extension ::= SEQUENCE {
   lPPPayload [0] SEQUENCE (SIZE (1..3)) OF OCTET STRING (SIZE (1..60000)) OPTIONAL,
   tIA801Payload [1] SEQUENCE (SIZE (1..3)) OF OCTET STRING (SIZE (1..60000)) OPTIONAL
      ,
   ...
}

-- Value assignments

maxGANSS INTEGER ::= 16

maxGANSSSat INTEGER ::= 32


END
