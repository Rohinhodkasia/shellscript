-- This file was generated by the Objective Systems ASN1C Compiler
-- (http://www.obj-sys.com).  Version: 6.8.A, Date: 18-Nov-2014.

SUPL-START DEFINITIONS AUTOMATIC TAGS ::= BEGIN

IMPORTS

LocationId, QoP
FROM ULP-Components 

Ver2-SUPL-START-extension
FROM ULP-Version-2-message-extensions 

Ver2-SETCapabilities-extension, Ver2-PosProtocol-extension, 
   Ver2-PosTechnology-extension
FROM ULP-Version-2-parameter-extensions 

Ver3-SUPL-START-extension
FROM ULP-Version-3-message-extensions 

Ver3-PosProtocol-extension, Ver3-SETCapabilities-extension
FROM ULP-Version-3-parameter-extensions ;

-- Productions

PosTechnology ::= SEQUENCE {
   agpsSETassisted [0] BOOLEAN,
   agpsSETBased [1] BOOLEAN,
   autonomousGPS [2] BOOLEAN,
   aFLT [3] BOOLEAN,
   eCID [4] BOOLEAN,
   eOTD [5] BOOLEAN,
   oTDOA [6] BOOLEAN,
   ...,
   ver2-PosTechnology-extension [7] Ver2-PosTechnology-extension OPTIONAL
}

PrefMethod ::= ENUMERATED { agpsSETassistedPreferred(0), 
   agpsSETBasedPreferred(1), noPreference(2) }

PosProtocol ::= SEQUENCE {
   tia801 [0] BOOLEAN,
   rrlp [1] BOOLEAN,
   rrc [2] BOOLEAN,
   ...,
   ver2-PosProtocol-extension [3] Ver2-PosProtocol-extension OPTIONAL,
   ver3-PosProtocol-extension [4] Ver3-PosProtocol-extension OPTIONAL
}

SETCapabilities ::= SEQUENCE {
   posTechnology [0] PosTechnology,
   prefMethod [1] PrefMethod,
   posProtocol [2] PosProtocol,
   ...,
   ver2-SETCapabilities-extension [3] Ver2-SETCapabilities-extension OPTIONAL,
   ver3-SETCapabilities-extension [4] Ver3-SETCapabilities-extension OPTIONAL
}

SUPLSTART ::= SEQUENCE {
   sETCapabilities [0] SETCapabilities,
   locationId [1] LocationId,
   qoP [2] QoP OPTIONAL,
   ...,
   ver2-SUPL-START-extension [3] Ver2-SUPL-START-extension OPTIONAL,
   ver3-SUPL-START-extension [4] Ver3-SUPL-START-extension OPTIONAL
}

END
