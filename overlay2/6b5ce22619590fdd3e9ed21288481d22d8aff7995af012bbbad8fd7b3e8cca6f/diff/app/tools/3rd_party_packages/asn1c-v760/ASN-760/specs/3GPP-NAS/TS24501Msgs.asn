/* 
Module for 3GPP TS 24.501 Messages
Messages initially added using version 15.0.0
Current versions:
    v15.6.0
    v16.9.0
    v17.3.1
*/
TS24501Msgs DEFINITIONS AUTOMATIC TAGS ::=
BEGIN

IMPORTS
AuthParamAUTN, AuthParamRAND, AuthFailureParam,
GPRSTimer, GPRSTimer2, GPRSTimer3,
ExtProtoConfigOptions, IMEISVRequest,
NetworkName, TimeZone, TimeZoneAndTime, DaylightSavingTime,
PLMNList, EmergencyNumberList, MobileStationClassmark2, SupportedCodecList,
ExtDRXParams, Non3GPPNetPolicies
FROM TS24008IES

IMPORTS
AuthRespParam, NASKeySetIdentifier, NASSecurityAlgorithms,
UENetworkCapability, UEStatus, ExtEmergencyNumberList, EPSBearerContextStatus,
UERadioCapId, UERadioCapIdDeletionInd, ReleaseAssistInd,
ServPLMNRateCtrl, WUSAssistanceInfo, UserDataContainer
FROM TS24301IES

IMPORTS
ABBA, EAPMessage, MMCause, RegistrationType, MMCapability, NSSAI,
PDUSessionStatus, TrackingAreaIdent, MobileIdentity, UESecurityCapability,
UplinkDataStatus, MICOIndication, AllowedPDUSessionStatus, UEUsageSetting,
DRXParams, EPSMessageContainer, LADNIndication, PayloadContainerType,
OpaqueData, NetSliceIndication, UpdateType, MappedNSSAI,
AdditionalInfoRequested, NBN1ModeDRXParams, RegistrationResult,
TrackingAreaIdentList,RejectedNSSAIList, NetworkFeatureSupport,
SessionReactivateRslt, SessionReactivateCause, LADNList,
SORTransparentContainer, NSSAIInclusionMode, AccessCategoryDefinitions,
CipheringKeyData, CAGInfoList, TruncatedTMSIConfig, SORAck,
MultiPayloadContainer, PDUSessionId2, RequestType, SNSSAI, DNNList,
AdditionalInfo, MAPDUSessionInfo, SORSteering, UEParamUpdate, UEParamUpdateAck,
DeregistrationType, ServiceType, ConfigUpdateIndication, SMSIndication,
AddlConfigIndication, IdentityType, AccessType, NASSecurityAlgorithm,
AddlSecurityInfo, IntegrityProtMaxDataRate, PDUSessionType, SSCMode,
SMCapability, MaxSupportedPacketFilters, AlwaysOnPDUSessionReq,
SmPduDnReqContainer, HeaderCompressionConfig, DSTTEthMACAddr,
DSTTResidenceTime, PortMgmtInfoContainer, EthHdrCompressConfig, QoSRules,
SessionAMBR, SMCause, PDUAddress, AlwaysOnPDUSessionInd, EPSBearerCtxts,
QOSFlowDescriptions, SMNetworkFeatureSupport, ATSSSContainer,
ControlPlaneIndication, AllowedSSCMode, CongestionReattemptIndicator,
ReattemptIndicator, ControlPlaneServiceType, CIoTSmallDataContainer,
NASMessageContainer2, N5GCIndication, ExtRejectedNSSAIList
FROM TS24501IES

IMPORTS CP-PDU
FROM TS24011Msgs
;


PDU ::= SEQUENCE {
   --<cEncSrcFname>TS24501MsgEnc_PDU_secHdr.c</cEncSrcFname>
   --<cDecSrcFname>TS24501MsgDec_PDU_secHdr.c</cDecSrcFname>
   secHdr     NAS5GSecProtMsgHdr OPTIONAL, 
   protoDiscr NAS5G-PROTOCOL-CLASS.&protoDiscr ({TS24501-IE-OBJECTSET}), 
   --<inline/>
   hdrData CHOICE {
      --<selector element="protoDiscr" value="126"/>
      mm SEQUENCE {
         spare1     INTEGER (0..15) DEFAULT 0, 
         secHdrType NAS5GSecHdrType
      },
      --<selector element="protoDiscr" value="46"/>
      sm SEQUENCE {
         pduSessIdent PDUSessionIdentity, 
         procTransIdent INTEGER (0..255)
      }
   },
   msgType    NAS5G-PROTOCOL-CLASS.&msgType ({TS24501-IE-OBJECTSET}), 
   data       NAS5G-PROTOCOL-CLASS.&Value 
                ({TS24501-IE-OBJECTSET}{@protoDiscr,@msgType}), 
   --<cEncSrcFname>TS24501MsgEnc_PDU_eom.c</cEncSrcFname>   
   --<cDecSrcFname>TS24301MsgDec_PDU_eom.c</cDecSrcFname>   
   eom NULL       
}

NAS5GProtoDiscr ::= ENUMERATED {
   sessMgmt5G(46), -- 0x2E - session management
   mobMgmt5G(126),  -- 0x7E - mobility management
   maxProtoDiscr(255)  -- to set encoded bit field size
}

NAS5G-PROTOCOL-CLASS ::= CLASS {
   &protoDiscr NAS5GProtoDiscr, 
   &msgType INTEGER (0..255), 
   &Value
}
WITH SYNTAX {
   ID &protoDiscr, &msgType
   TYPE &Value
}

NAS5GSecHdrType ::= ENUMERATED {
   noSec, integProt, integProtAndCipher, integProtAnd5GSecCtxt, 
   integProtAndCipherAnd5GSecCtxt, secMax(15)
}

NAS5GSecProtMsgHdr ::= SEQUENCE {
   protoDiscr NAS5GProtoDiscr, 
   spare1 INTEGER (0..15) DEFAULT 0, 
   secHdrType NAS5GSecHdrType,
   msgAuthCode INTEGER(0..4294967295), -- Message authentication code (MAC)
   seqNumber   INTEGER(0..255)   -- Sequence number
}
   
PDUSessionIdentity ::= ENUMERATED {
   noPduId(0), pduId1(1), pduId2(2), pduId3(3), pduId4(4), pduId5(5),
   pduId6(6), pduId7(7), pduId8(8), pduId9(9), pduId10(10), pduId11(11),
   pduId12(12), pduId13(13), pduId14(14), pduId15(15), pduIdMax(255)
}

TS24501-IE-OBJECTSET NAS5G-PROTOCOL-CLASS ::= {
   -- Mobility messages
   obj-MMAuthRequest5G | obj-MMAuthResponse5G | obj-MMAuthResult5G |
   obj-MMAuthFailure5G | obj-MMAuthReject5G |
   obj-RegRequest5G | obj-RegAccept5G |obj-RegComplete5G | obj-RegReject5G |
   obj-ULNASTrans5G | obj-DLNASTrans5G |
   obj-DeregReqUEOrig5G | obj-DeregAcceptUEOrig5G |
   obj-DeregReqUETerm5G | obj-DeregAcceptUETerm5G |
   obj-ServRequest5G | obj-ServAccept5G | obj-ServReject5G |
   obj-CfgUpdateCmd5G | obj-CfgUpdateDone5G |
   obj-IdentityRequest5G | obj-IdentityResponse5G |
   obj-Notify5G | obj-NotifyResponse5G |
   obj-SecModeCmd5G | obj-SecModeDone5G | obj-SecModeReject5G |
   obj-MMStatus5G |
   -- Session messages
   obj-EstablishRequest5G | obj-EstablishAccept5G | obj-EstablishReject5G |
   obj-SMAuthCmd5G | obj-SMAuthDone5G | obj-SMAuthResult5G |
   obj-ModifyRequest5G | obj-ModifyReject5G | obj-ModifyCmd5G |
   obj-ModifyDone5G | obj-ModifyCmdReject5G |
   obj-ReleaseRequest5G | obj-ReleaseReject5G |
   obj-ReleaseCmd5G | obj-ReleaseDone5G |
   obj-SMStatus5G | obj-ControlPlaneServReq5G |
   obj-NetSliceAuthCmd5G | obj-NetSliceAuthDone5G | obj-NetSliceAuthResult5G
}


/* This SM object set and PDU are for SM messages that can reside in the MM
    ESMMessageContainer IE... */
PDU-SM ::= SEQUENCE {
   protoDiscr NAS5G-PROTOCOL-CLASS.&protoDiscr ({TS24501-IE-SM-OBJECTSET}),
   pduSessIdent PDUSessionIdentity,
   procTransIdent INTEGER (0..255),
   msgType    NAS5G-PROTOCOL-CLASS.&msgType ({TS24501-IE-SM-OBJECTSET}),
   data       NAS5G-PROTOCOL-CLASS.&Value
                ({TS24501-IE-SM-OBJECTSET}{@protoDiscr,@msgType})
}

TS24501-IE-SM-OBJECTSET NAS5G-PROTOCOL-CLASS ::= {
   obj-EstablishRequest5G | obj-EstablishAccept5G | obj-EstablishReject5G |
   obj-SMAuthCmd5G | obj-SMAuthDone5G | obj-SMAuthResult5G |
   obj-ModifyRequest5G | obj-ModifyReject5G | obj-ModifyCmd5G |
   obj-ModifyDone5G | obj-ModifyCmdReject5G |
   obj-ReleaseRequest5G | obj-ReleaseReject5G |
   obj-ReleaseCmd5G | obj-ReleaseDone5G |
   obj-SMStatus5G | obj-ControlPlaneServReq5G |
   obj-NetSliceAuthCmd5G | obj-NetSliceAuthDone5G | obj-NetSliceAuthResult5G
}


/* 9.11.3.39 - Payload container type N1 SM Information
   This covers the specific case where the payload container type is N1 SM.

   This is defined here rather than the IES ASN file because of the PDU-SM
   type above.  If this were in the IES file, it caused a circular reference
   issue, which changed some generated types' structs to pointers to those
   structs.  This created a backward compatability issue.  To get around that,
   it is defined here...
*/
N1SMPayloadContainer ::= SEQUENCE {
   --<is3GLength bitFieldSize="16"/>
   length INTEGER (0..65535),
   pduSm PDU-SM
}

/* 9.11.3.39 - Payload container type SMS
   This covers the specific case where the payload container type is SMS
   Message.

   This is defined here to avoid circular reference issues and resulting
   backward compatability problems...
*/
SMSMessage ::= SEQUENCE {
   --<is3GLength/>
   length INTEGER (0..255),
   cpPdu CP-PDU
}


/* -- MOBILITY MANAGEMENT MESSAGES --- */

/* 8.2.1 Authentication request */

mt-AuthRequest5G INTEGER ::= 86

obj-MMAuthRequest5G NAS5G-PROTOCOL-CLASS ::= {
   ID mobMgmt5G, mt-AuthRequest5G
   TYPE AuthRequest
}

--<is3GMessage/>
AuthRequest ::= SEQUENCE {
   spare INTEGER (0..15) DEFAULT 0, 
   nasKeySetIdent NASKeySetIdentifier,
   /* This field was added as optional in 15.1 and made mandatory in 15.3... */
   abba ABBA, -- 9.11.3.10
   --<iei format="tv" length="17">21</iei>
   authParamRAND AuthParamRAND OPTIONAL,
   --<iei format="tlv">20</iei>
   authParamAUTN AuthParamAUTN OPTIONAL,
   --<iei format="tlv-e">78</iei>
   eapMessage EAPMessage OPTIONAL
}
   
/* 8.2.2 Authentication response */

mt-AuthResponse5G INTEGER ::= 87

obj-MMAuthResponse5G NAS5G-PROTOCOL-CLASS ::= {
   ID mobMgmt5G, mt-AuthResponse5G
   TYPE AuthResponse
}

--<is3GMessage/>
AuthResponse ::= SEQUENCE {
   --<iei format="tlv">2D</iei>
   authRespParam AuthRespParam OPTIONAL,
   --<iei format="tlv-e">78</iei>
   eapMessage EAPMessage OPTIONAL
}

/* 8.2.3 Authentication result */

mt-AuthResult5G INTEGER ::= 90

obj-MMAuthResult5G NAS5G-PROTOCOL-CLASS ::= {
   ID mobMgmt5G, mt-AuthResult5G
   TYPE AuthResult
}

--<is3GMessage/>
AuthResult ::= SEQUENCE {
   spare INTEGER (0..15) DEFAULT 0,
   nasKeySetIdent NASKeySetIdentifier,
   eapMessage EAPMessage,
   --<iei format="tlv">38</iei>
   abba ABBA OPTIONAL -- added in v15.2.0
}

/* 8.2.4 Authentication failure */

mt-AuthFailure5G INTEGER ::= 89

obj-MMAuthFailure5G NAS5G-PROTOCOL-CLASS ::= {
   ID mobMgmt5G, mt-AuthFailure5G
   TYPE AuthFailure
}

--<is3GMessage/>
AuthFailure ::= SEQUENCE {
   cause MMCause,
   --<iei format="tlv">30</iei>
   authFailureParam AuthFailureParam OPTIONAL
}
   
/* 8.2.5 Authentication reject */

mt-AuthReject5G INTEGER ::= 88

obj-MMAuthReject5G NAS5G-PROTOCOL-CLASS ::= {
   ID mobMgmt5G, mt-AuthReject5G
   TYPE AuthReject
}

--<is3GMessage/>
AuthReject ::= SEQUENCE {
   --<iei format="tlv-e">78</iei>
   eapMessage EAPMessage OPTIONAL -- added in v15.2.0
}

/* 8.2.6 Registration request */

mt-RegRequest5G INTEGER ::= 65

obj-RegRequest5G NAS5G-PROTOCOL-CLASS ::= {
   ID mobMgmt5G, mt-RegRequest5G
   TYPE RegRequest
}

--<is3GMessage/>
RegRequest ::= SEQUENCE {
   nasKeySetIdent NASKeySetIdentifier,
   registrationType RegistrationType,
   mobileId MobileIdentity,
   --<iei format="tv" length="1">0C</iei>
   nativeNasKeySetIdent NASKeySetIdentifier OPTIONAL,
   --<iei format="tlv">10</iei>
   capability MMCapability OPTIONAL,
   --<iei format="tlv">2E</iei>
   securityCapability UESecurityCapability OPTIONAL,
   --<iei format="tlv">2F</iei>
   requestedNSSAI NSSAI OPTIONAL,
   --<iei format="tv" length="7">52</iei>
   lastVisitedTAI TrackingAreaIdent OPTIONAL,
   --<iei format="tlv">17</iei>
   s1NetworkCapability UENetworkCapability OPTIONAL,
   --<iei format="tlv">40</iei>
   uplinkStat UplinkDataStatus OPTIONAL,
   --<iei format="tlv">50</iei>
   sessionStat PDUSessionStatus OPTIONAL,
   --<iei format="tv" length="1">0B</iei>
   micoInd MICOIndication OPTIONAL,
   --<iei format="tlv">2B</iei>
   ueStat UEStatus OPTIONAL,
   --<iei format="tlv-e">77</iei>
   addlGUTI MobileIdentity OPTIONAL,
   --<iei format="tlv">25</iei>
   allowedSessionStat AllowedPDUSessionStatus OPTIONAL,
   --<iei format="tlv">18</iei>
   ueUsage UEUsageSetting OPTIONAL,
   --<iei format="tlv">51</iei>
   reqDrxParams DRXParams OPTIONAL, -- added in v15.2.0
   --<iei format="tlv-e">70</iei>
   epsContainer EPSMessageContainer OPTIONAL,
   --<iei format="tlv-e">74</iei>
   ladnInd LADNIndication OPTIONAL, -- added in v15.1.0
   --<iei format="tv" length="1">8</iei>
   containerType PayloadContainerType OPTIONAL, -- added in v15.3.0
   --<iei format="tlv-e">7B</iei>
   --<inline/>
   container CHOICE {
      /* The only option currently allowed is UE Policy.  See 8.2.6.17A. */
      --<selector element="containerType" value="5"/>
      uePolicy OpaqueData
   } OPTIONAL,  
   --<iei format="tv" length="1">9</iei>
   netSliceInd NetSliceIndication OPTIONAL, -- added in v15.2.0
   --<iei format="tlv">53</iei>
   updateType UpdateType OPTIONAL, -- added in v15.2.0
   --<iei format="tlv-e">71</iei>
   nasContainer NASMessageContainer2 OPTIONAL, -- added in v15.2.0
   --<iei format="tlv">60</iei>
   epsBearerStat EPSBearerContextStatus OPTIONAL, -- added in v15.4.0
   ...,
   [[ 16:
   --<iei format="tlv">41</iei>
   mobileStationClassmark2 MobileStationClassmark2 OPTIONAL, -- added in v16.2.0
   --<iei format="tlv">42</iei>
   supportedCodecs SupportedCodecList OPTIONAL, -- added in v16.2.0
   --<iei format="tlv">6E</iei>
   reqDRXParams ExtDRXParams OPTIONAL, -- added in v16.2.0
   --<iei format="tlv">6A</iei>
   t3324 GPRSTimer3 OPTIONAL, -- added in v16.2.0
   --<iei format="tlv">67</iei>
   ueRadioCapabilityId UERadioCapId OPTIONAL, -- added in v16.2.0
   --<iei format="tlv">35</iei>
   reqMappedNSSAI MappedNSSAI OPTIONAL, -- added in v16.3.0
   --<iei format="tlv">48</iei>
   addlInfoRequested AdditionalInfoRequested OPTIONAL, -- added in v16.3.0
   --<iei format="tlv">1A</iei>
   wusAssistInfo WUSAssistanceInfo OPTIONAL, -- added in v16.4.1
   --<iei format="tv" length="1">0A</iei>
   n5gcInd N5GCIndication OPTIONAL, -- added as NULL in v16.4.1; modified in v16.6.0
   --<iei format="tlv">30</iei>
   reqNBN1Params NBN1ModeDRXParams OPTIONAL -- added in v16.5.1
   ]]
   -- iei not yet defined in 17.3.0 format="tlv">
   -- ueRequestType UERequestType OPTIONAL,
   -- iei not yet defined in 17.3.0 format="tlv">
   -- pagingRestriction PagingRestriction OPTIONAL,
   -- iei not yet defined in 17.3.0 format="tlv-e">
   -- aaContainer ServiceLevelAAContainer OPTIONAL,
   -- iei not yet defined in 17.3.0 format="tlv">
   -- nid NetworkId OPTIONAL
}

/* 8.2.7 Registration accept */

mt-RegAccept5G INTEGER ::= 66

obj-RegAccept5G NAS5G-PROTOCOL-CLASS ::= {
   ID mobMgmt5G, mt-RegAccept5G
   TYPE RegAccept
}

--<is3GMessage/>
RegAccept ::= SEQUENCE {
   regResult RegistrationResult,
   --<iei format="tlv-e">77</iei>
   guti MobileIdentity OPTIONAL,
   --<iei format="tlv">4A</iei>
   plmnList PLMNList OPTIONAL,
   --<iei format="tlv">54</iei>
   taiList TrackingAreaIdentList OPTIONAL,
   --<iei format="tlv">15</iei>
   allowedNSSAI NSSAI OPTIONAL,
   --<iei format="tlv">11</iei>
   rejectedNSSAI RejectedNSSAIList OPTIONAL,
   --<iei format="tlv">31</iei>
   configuredNSSAI NSSAI OPTIONAL,
   --<iei format="tlv">21</iei>
   netSupport NetworkFeatureSupport OPTIONAL,
   --<iei format="tlv">50</iei>
   sessionStat PDUSessionStatus OPTIONAL,
   --<iei format="tlv">26</iei>
   reactivateRslt SessionReactivateRslt OPTIONAL,
   --<iei format="tlv-e">72</iei>
   reactivateRsltCause SessionReactivateCause OPTIONAL,
   --<iei format="tlv-e">79</iei>
   ladn LADNList OPTIONAL,
   --<iei format="tv" length="1">B</iei>
   micoInd MICOIndication OPTIONAL,
   --<iei format="tv" length="1">9</iei>
   netSliceInd NetSliceIndication OPTIONAL, -- added in v15.1.0
   --<iei format="tlv">27</iei>
   svcAreaList TrackingAreaIdentList OPTIONAL,
   --<iei format="tlv">5E</iei>
   t3512 GPRSTimer3 OPTIONAL,
   --<iei format="tlv">5D</iei>
   non3GPPDeregTimer GPRSTimer2 OPTIONAL,
   --<iei format="tlv">16</iei>
   t3502 GPRSTimer2 OPTIONAL,
   --<iei format="tlv">34</iei>
   emergencyNumList EmergencyNumberList OPTIONAL,
   --<iei format="tlv-e">7A</iei>
   extEmergencyNumList ExtEmergencyNumberList OPTIONAL, -- added in v15.1.0
   --<iei format="tlv-e">73</iei>
   transparentContainer SORTransparentContainer OPTIONAL, -- added in v15.1.0
   --<iei format="tlv-e">78</iei>
   eapMessage EAPMessage OPTIONAL,
   --<iei format="tv" length="1">A</iei>
   inclusionMode NSSAIInclusionMode OPTIONAL, -- added in v15.2.0
   --<iei format="tlv-e">76</iei>
   accessDefs AccessCategoryDefinitions OPTIONAL, -- added in v15.2.0
   --<iei format="tlv">51</iei>
   negotiatedDrxParams DRXParams OPTIONAL, -- added in v15.2.0
   --<iei format="tv" length="1">D</iei>
   non3GPPNWPolicies Non3GPPNetPolicies OPTIONAL, -- added in v15.4.0
   --<iei format="tlv">60</iei>
   epsBearerStat EPSBearerContextStatus OPTIONAL, -- added in v15.4.0
   ...,
   [[ 16:
   --<iei format="tlv">6E</iei>
   negotiatedExtDrxParams ExtDRXParams OPTIONAL, -- added in v16.2.0
   --<iei format="tlv">6C</iei>
   t3447 GPRSTimer3 OPTIONAL, -- added in v16.2.0
   --<iei format="tlv">6B</iei>
   t3448 GPRSTimer3 OPTIONAL, -- added in v16.2.0
   --<iei format="tlv">6A</iei>
   t3324 GPRSTimer3 OPTIONAL, -- added in v16.2.0
   --<iei format="tlv">67</iei>
   ueRadioCapabilityId UERadioCapId OPTIONAL, -- added in v16.2.0
   --<iei format="tv" length="1">0E</iei>
   ueRadioCapIdDeletionIndication UERadioCapIdDeletionInd OPTIONAL, -- added in v16.2.0
   --<iei format="tlv">39</iei>
   pendingNSSAI NSSAI OPTIONAL, -- added in v16.3
   --<iei format="tlv-e">74</iei>
   cipherKeyData CipheringKeyData OPTIONAL, -- added in v16.3
   --<iei format="tlv-e">75</iei>
   cagInfoList CAGInfoList OPTIONAL, -- added in v16.4.0
   --<iei format="tlv">1B</iei>
   truncatedConfig TruncatedTMSIConfig OPTIONAL, -- added in v16.4.1
   --<iei format="tlv">1C</iei>
   negotiatedWUSAssistInfo WUSAssistanceInfo OPTIONAL, -- added in v16.4.1
   --<iei format="tlv">29</iei>
   negotiatedNBN1Params NBN1ModeDRXParams OPTIONAL -- added in v16.5.1
   ]],
   [[ 17:
   --<iei format="tlv">68</iei>
   extRejectedNSSAI ExtRejectedNSSAIList OPTIONAL -- added in v17.0.0
   -- iei not yet defined in 17.3.0 format="tlv-e">
   -- aaContainer ServiceLevelAAContainer OPTIONAL
   ]]
}

/* 8.2.8 Registration complete */

mt-RegComplete5G INTEGER ::= 67

obj-RegComplete5G NAS5G-PROTOCOL-CLASS ::= {
   ID mobMgmt5G, mt-RegComplete5G
   TYPE RegComplete
}

--<is3GMessage/>
RegComplete ::= SEQUENCE {
   --<iei format="tlv-e">73</iei>
   transparentContainer SORTransparentContainer OPTIONAL -- added in v15.1.0
}

/* 8.2.9 Registration reject */

mt-RegReject5G INTEGER ::= 68

obj-RegReject5G NAS5G-PROTOCOL-CLASS ::= {
   ID mobMgmt5G, mt-RegReject5G
   TYPE RegReject
}

--<is3GMessage/>
RegReject ::= SEQUENCE {
   cause MMCause,
   --<iei format="tlv">5F</iei>
   t3346 GPRSTimer2 OPTIONAL,
   --<iei format="tlv">16</iei>
   t3502 GPRSTimer2 OPTIONAL,
   --<iei format="tlv-e">78</iei>
   eapMessage EAPMessage OPTIONAL,
   ...,
   [[ 16:
   --<iei format="tlv">69</iei>
   rejectedNSSAI RejectedNSSAIList OPTIONAL, -- added in v16.2.0
   --<iei format="tlv-e">75</iei>
   cagInfoList CAGInfoList OPTIONAL -- added in v16.5.1
   ]],
   [[ 17:
   --<iei format="tlv">68</iei>
   extRejectedNSSAI ExtRejectedNSSAIList OPTIONAL -- added in v17.0.0
   -- iei not yet defined in 17.3.0 format="tlv">
   -- mccList MCCList OPTIONAL
   ]]
}

/* 8.2.10 UL NAS transport */

mt-ULNASTrans5G INTEGER ::= 103

obj-ULNASTrans5G NAS5G-PROTOCOL-CLASS ::= {
   ID mobMgmt5G, mt-ULNASTrans5G
   TYPE ULNASTrans
}

--<is3GMessage/>
ULNASTrans ::= SEQUENCE {
   spare INTEGER (0..15) DEFAULT 0,
   containerType PayloadContainerType,
   --<inline/>
   container CHOICE {
      --<selector element="containerType" value="1"/>      
      n1sm N1SMPayloadContainer,
      --<selector element="containerType" value="2"/>
      sms SMSMessage,
      --<selector element="containerType" value="3"/>
      lpp OpaqueData,
      --<selector element="containerType" value="4"/>
      sor SORAck,
      --<selector element="containerType" value="5"/>
      uePolicy OpaqueData,
      --<selector element="containerType" value="6"/>
      ueParamUpdate UEParamUpdateAck,
      --<selector element="containerType" value="7"/>
      locSvcs OpaqueData,
      --<selector element="containerType" value="8"/>
      cIOTUserData UserDataContainer,
      --<selector element="containerType" value="15"/>
      multiple MultiPayloadContainer
   },
   --<iei format="tv" length="2">12</iei>
   pduSessionId PDUSessionId2 OPTIONAL,
   --<iei format="tv" length="2">59</iei>
   oldPduSessionId PDUSessionId2 OPTIONAL,
   --<iei format="tv" length="1">8</iei>
   requestType RequestType OPTIONAL,
   --<iei format="tlv">22</iei>
   snssai SNSSAI OPTIONAL,
   --<iei format="tlv">25</iei>
   dnn DNNList OPTIONAL,
   --<iei format="tlv">24</iei>
   addlInfo AdditionalInfo OPTIONAL,
   ...,
   [[ 16:
   --<iei format="tv" length="1">A</iei>
   maPduSessionInfo MAPDUSessionInfo OPTIONAL, -- added in v16.3
   --<iei format="tv" length="1">F</iei>
   relAssistInd ReleaseAssistInd OPTIONAL -- added in v16.3
   ]]
}

/* 8.2.11 DL NAS transport */

mt-DLNASTrans5G INTEGER ::= 104

obj-DLNASTrans5G NAS5G-PROTOCOL-CLASS ::= {
   ID mobMgmt5G, mt-DLNASTrans5G
   TYPE DLNASTrans
}

--<is3GMessage/>
DLNASTrans ::= SEQUENCE {
   spare INTEGER (0..15) DEFAULT 0,
   containerType PayloadContainerType,
   --<inline/>
   container CHOICE {
      --<selector element="containerType" value="1"/>      
      n1sm N1SMPayloadContainer,
      --<selector element="containerType" value="2"/>
      sms SMSMessage,
      --<selector element="containerType" value="3"/>
      lpp OpaqueData,
      --<selector element="containerType" value="4"/>
      sor SORSteering,
      --<selector element="containerType" value="5"/>
      uePolicy OpaqueData,
      --<selector element="containerType" value="6"/>
      ueParamUpdate UEParamUpdate,
      --<selector element="containerType" value="7"/>
      locSvcs OpaqueData,
      --<selector element="containerType" value="8"/>
      cIOTUserData UserDataContainer,
      --<selector element="containerType" value="15"/>
      multiple MultiPayloadContainer
   },   
   --<iei format="tv" length="2">12</iei>
   pduSessionId PDUSessionId2 OPTIONAL,
   --<iei format="tlv">24</iei>
   addlInfo AdditionalInfo OPTIONAL,
   --<iei format="tv" length="2">58</iei>
   cause MMCause OPTIONAL,
   --<iei format="tlv">37</iei>
   backoffTimer GPRSTimer3 OPTIONAL
}

/* 8.2.12 De-registration request - UE originating */

mt-DeregReqUEOrig5G INTEGER ::= 69

obj-DeregReqUEOrig5G NAS5G-PROTOCOL-CLASS ::= {
   ID mobMgmt5G, mt-DeregReqUEOrig5G
   TYPE DeregReqUEOrig
}

--<is3GMessage/>
DeregReqUEOrig ::= SEQUENCE {
   nasKeySetIdent NASKeySetIdentifier, -- added in v15.1.0
   deregType DeregistrationType,
   mobileId MobileIdentity
}

/* 8.2.13 De-registration accept - UE originating */

mt-DeregAcceptUEOrig5G INTEGER ::= 70

obj-DeregAcceptUEOrig5G NAS5G-PROTOCOL-CLASS ::= {
   ID mobMgmt5G, mt-DeregAcceptUEOrig5G
   TYPE NULL
}

/* 8.2.14 De-registration request - UE terminated */

mt-DeregReqUETerm5G INTEGER ::= 71

obj-DeregReqUETerm5G NAS5G-PROTOCOL-CLASS ::= {
   ID mobMgmt5G, mt-DeregReqUETerm5G
   TYPE DeregReqUETerm
}

--<is3GMessage/>
DeregReqUETerm ::= SEQUENCE {
   spare INTEGER (0..15) DEFAULT 0,
   deregType DeregistrationType,
   --<iei format="tv" length="2">58</iei>
   cause MMCause OPTIONAL,
   --<iei format="tlv">5F</iei>
   t3346 GPRSTimer2 OPTIONAL,
   ...,
   [[ 16:
   --<iei format="tlv">6D</iei>
   rejectedNSSAI RejectedNSSAIList OPTIONAL, -- added in 16.3
   --<iei format="tlv-e">75</iei>
   cagInfoList CAGInfoList OPTIONAL -- added in v16.6.0
   ]],
   [[ 17:
   --<iei format="tlv">68</iei>
   extRejectedNSSAI ExtRejectedNSSAIList OPTIONAL -- added in v17.0.0
   -- iei not yet defined in 17.3.0 format="tlv">
   -- mccList MCCList OPTIONAL
   ]]
}

/* 8.2.15 De-registration accept - UE terminated */

mt-DeregAcceptUETerm5G INTEGER ::= 72

obj-DeregAcceptUETerm5G NAS5G-PROTOCOL-CLASS ::= {
   ID mobMgmt5G, mt-DeregAcceptUETerm5G
   TYPE NULL
}

/* 8.2.16 Service request */

mt-ServRequest5G INTEGER ::= 76

obj-ServRequest5G NAS5G-PROTOCOL-CLASS ::= {
   ID mobMgmt5G, mt-ServRequest5G
   TYPE ServRequest
}

--<is3GMessage/>
ServRequest ::= SEQUENCE {
   serviceType ServiceType,
   nasKeySetIdent NASKeySetIdentifier,
   stmsi MobileIdentity,
   --<iei format="tlv">40</iei>
   uplinkStat UplinkDataStatus OPTIONAL,
   --<iei format="tlv">50</iei>
   sessionStat PDUSessionStatus OPTIONAL,
   --<iei format="tlv">25</iei>
   allowedSessionStat AllowedPDUSessionStatus OPTIONAL,
   --<iei format="tlv-e">71</iei>
   nasContainer NASMessageContainer2 OPTIONAL -- added in v15.2.0
   -- iei not yet defined in 17.3.0 format="tlv">
   -- ueRequestType UERequestType OPTIONAL
   -- iei not yet defined in 17.3.0 format="tlv">
   -- pagingRestriction PagingRestriction OPTIONAL
}

/* 8.2.17 Service accept */

mt-ServAccept5G INTEGER ::= 78

obj-ServAccept5G NAS5G-PROTOCOL-CLASS ::= {
   ID mobMgmt5G, mt-ServAccept5G
   TYPE ServAccept
}

--<is3GMessage/>
ServAccept ::= SEQUENCE {
   --<iei format="tlv">50</iei>
   sessionStat PDUSessionStatus OPTIONAL,
   --<iei format="tlv">26</iei>
   reactivateRslt SessionReactivateRslt OPTIONAL,
   --<iei format="tlv-e">72</iei>
   reactivateRsltCause SessionReactivateCause OPTIONAL,
   --<iei format="tlv-e">78</iei>
   eapMessage EAPMessage OPTIONAL,
   ...,
   [[ 16:
   --<iei format="tlv">6B</iei>
   t3448 GPRSTimer3 OPTIONAL -- added in v16.2.0
   ]]
}

/* 8.2.18 Service reject */

mt-ServReject5G INTEGER ::= 77

obj-ServReject5G NAS5G-PROTOCOL-CLASS ::= {
   ID mobMgmt5G, mt-ServReject5G
   TYPE ServReject
}

--<is3GMessage/>
ServReject ::= SEQUENCE {
   cause MMCause,
   --<iei format="tlv">50</iei>
   sessionStat PDUSessionStatus OPTIONAL,
   --<iei format="tlv">5F</iei>
   t3346 GPRSTimer2 OPTIONAL,
   --<iei format="tlv-e">78</iei>
   eapMessage EAPMessage OPTIONAL,
   ...,
   [[ 16:
   --<iei format="tlv">6B</iei>
   t3448 GPRSTimer3 OPTIONAL, -- added in v16.2.0
   --<iei format="tlv-e">75</iei>
   cagInfoList CAGInfoList OPTIONAL -- added in v16.5.1
   ]]
   -- iei not yet defined in 17.3.0 format="tlv">
   -- mccList MCCList OPTIONAL
}

/* 8.2.19 Configuration update command */

mt-CfgUpdateCmd5G INTEGER ::= 84

obj-CfgUpdateCmd5G NAS5G-PROTOCOL-CLASS ::= {
   ID mobMgmt5G, mt-CfgUpdateCmd5G
   TYPE CfgUpdateCmd
}

--<is3GMessage/>
CfgUpdateCmd ::= SEQUENCE {
   --<iei format="tv" length="1">0D</iei>
   cfgUpdIndication ConfigUpdateIndication OPTIONAL,
   --<iei format="tlv-e">77</iei>
   guti MobileIdentity OPTIONAL,
   --<iei format="tlv">54</iei>
   taiList TrackingAreaIdentList OPTIONAL,
   --<iei format="tlv">15</iei>
   allowedNSSAI NSSAI OPTIONAL,
   --<iei format="tlv">27</iei>
   svcAreaList TrackingAreaIdentList OPTIONAL,
   --<iei format="tlv">43</iei>
   fullNetworkName NetworkName OPTIONAL,
   --<iei format="tlv">45</iei>
   shortNetworkName NetworkName OPTIONAL,
   --<iei format="tv" length="2">46</iei>
   localTZ TimeZone OPTIONAL,
   --<iei format="tv" length="8">47</iei>
   univAndLocalTZ TimeZoneAndTime OPTIONAL,
   --<iei format="tlv">49</iei>
   dst DaylightSavingTime OPTIONAL,
   --<iei format="tlv-e">79</iei>
   ladn LADNList OPTIONAL,
   --<iei format="tv" length="1">0B</iei>
   micoInd MICOIndication OPTIONAL,
   --<iei format="tv" length="1">9</iei>
   netSliceInd NetSliceIndication OPTIONAL, -- added in v15.1.0
   --<iei format="tlv">31</iei>
   configuredNSSAI NSSAI OPTIONAL,
   --<iei format="tlv">11</iei>
   rejectedNSSAI RejectedNSSAIList OPTIONAL,
   --<iei format="tlv-e">76</iei>
   accessDefs AccessCategoryDefinitions OPTIONAL, -- added in v15.2.0
   --<iei format="tv" length="1">F</iei>
   smsInd SMSIndication OPTIONAL, -- added in v15.2.0
   ...,
   [[ 16:
   --<iei format="tlv">6C</iei>
   t3447 GPRSTimer3 OPTIONAL, -- added in v16.2.0
   --<iei format="tlv-e">75</iei>
   cagInfoList CAGInfoList OPTIONAL, -- added in v16.2.0
   --<iei format="tlv">67</iei>
   ueRadioCapabilityId UERadioCapId OPTIONAL, -- added in v16.2.0
   --<iei format="tv" length="1">0A</iei>
   ueRadioCapIdDeletionIndication UERadioCapIdDeletionInd OPTIONAL, -- added in v16.2.0
   --<iei format="tlv">44</iei>
   regResult RegistrationResult OPTIONAL, -- added in v16.3
   --<iei format="tlv">1B</iei>
   truncatedConfig TruncatedTMSIConfig OPTIONAL, -- added in v16.4.1
   --<iei format="tv" length="1">0C</iei>
   additionalConfigIndication AddlConfigIndication OPTIONAL -- added in v16.5.1
   ]],
   [[ 17:
   --<iei format="tlv">68</iei>
   extRejectedNSSAI ExtRejectedNSSAIList OPTIONAL -- added in v17.0.0
   -- iei not yet defined in 17.3.0 format="tlv-e">
   -- aaContainer ServiceLevelAAContainer OPTIONAL,
   ]]
}

/* 8.2.20 Configuration update complete */

mt-CfgUpdateDone5G INTEGER ::= 85

obj-CfgUpdateDone5G NAS5G-PROTOCOL-CLASS ::= {
   ID mobMgmt5G, mt-CfgUpdateDone5G
   TYPE NULL
}

/* 8.2.21 Identity request */

mt-IdentityRequest5G INTEGER ::= 91

obj-IdentityRequest5G NAS5G-PROTOCOL-CLASS ::= {
   ID mobMgmt5G, mt-IdentityRequest5G
   TYPE IdentityRequest
}

--<is3GMessage/>
IdentityRequest ::= SEQUENCE {
   spare INTEGER (0..15) DEFAULT 0,
   identity IdentityType
}

/* 8.2.22 Identity response */

mt-IdentityResponse5G INTEGER ::= 92

obj-IdentityResponse5G NAS5G-PROTOCOL-CLASS ::= {
   ID mobMgmt5G, mt-IdentityResponse5G
   TYPE IdentityResponse
}

--<is3GMessage/>
IdentityResponse ::= SEQUENCE {
   mobileId MobileIdentity
}

/* 8.2.23 Notification */

mt-Notify5G INTEGER ::= 101

obj-Notify5G NAS5G-PROTOCOL-CLASS ::= {
   ID mobMgmt5G, mt-Notify5G
   TYPE Notify
}

--<is3GMessage/>
Notify ::= SEQUENCE {
   spare INTEGER (0..15) DEFAULT 0,
   access AccessType
}

/* 8.2.24 Notification response */

mt-NotifyResponse5G INTEGER ::= 102

obj-NotifyResponse5G NAS5G-PROTOCOL-CLASS ::= {
   ID mobMgmt5G, mt-NotifyResponse5G
   TYPE NotifyResponse
}

--<is3GMessage/>
NotifyResponse ::= SEQUENCE {
   --<iei format="tlv">50</iei>
   sessionStat PDUSessionStatus OPTIONAL
}

/* 8.2.25 Security mode command */

mt-SecModeCmd5G INTEGER ::= 93

obj-SecModeCmd5G NAS5G-PROTOCOL-CLASS ::= {
   ID mobMgmt5G, mt-SecModeCmd5G
   TYPE SecModeCmd
}

--<is3GMessage/>
SecModeCmd ::= SEQUENCE {
   nasSecAlgorithm NASSecurityAlgorithm,
   spare INTEGER (0..15) DEFAULT 0, 
   nasKeySetIdent NASKeySetIdentifier,
   replayedUECapabilities UESecurityCapability,
   --<iei format="tv" length="1">0E</iei>
   imeisvReq IMEISVRequest OPTIONAL,
   --<iei format="tv" length="2">57</iei>
   epsSecAlgorithm NASSecurityAlgorithms OPTIONAL,
   --<iei format="tlv">36</iei>
   addlSecInfo AddlSecurityInfo OPTIONAL, -- added in v15.1.0
   --<iei format="tlv-e">78</iei>
   eapMessage EAPMessage OPTIONAL,
   --<iei format="tlv">38</iei>
   abba ABBA OPTIONAL, -- added in v15.2.0
   --<iei format="tlv">19</iei>
   replayedS1UECapabilities UESecurityCapability OPTIONAL -- added in v15.2.0
}

/* 8.2.26 Security mode complete */

mt-SecModeDone5G INTEGER ::= 94

obj-SecModeDone5G NAS5G-PROTOCOL-CLASS ::= {
   ID mobMgmt5G, mt-SecModeDone5G
   TYPE SecModeDone
}

--<is3GMessage/>
SecModeDone ::= SEQUENCE {
   --<iei format="tlv-e">77</iei>
   imeisv MobileIdentity OPTIONAL,
   --<iei format="tlv-e">71</iei>
   nasMsgContainer NASMessageContainer2 OPTIONAL,
   ...,
   [[ 16:
   --<iei format="tlv-e">78</iei>
   nonImeisvPei MobileIdentity OPTIONAL -- added in 16.3
   ]]
}

/* 8.2.27 Security mode reject */

mt-SecModeReject5G INTEGER ::= 95

obj-SecModeReject5G NAS5G-PROTOCOL-CLASS ::= {
   ID mobMgmt5G, mt-SecModeReject5G
   TYPE SecModeReject
}

--<is3GMessage/>
SecModeReject ::= SEQUENCE {
   cause MMCause
}

/* 8.2.29 5GMM status */

mt-MMStatus5G INTEGER ::= 100

obj-MMStatus5G NAS5G-PROTOCOL-CLASS ::= {
   ID mobMgmt5G, mt-MMStatus5G
   TYPE MMStatus
}

--<is3GMessage/>
MMStatus ::= SEQUENCE {
   cause MMCause
}

/* 8.2.30 Control Plane Service Request - message added in v16.2.0 */

mt-ControlPlaneServReq5G INTEGER ::= 79

obj-ControlPlaneServReq5G NAS5G-PROTOCOL-CLASS ::= {
   ID mobMgmt5G, mt-ControlPlaneServReq5G
   TYPE ControlPlaneServReq
}

--<is3GMessage/>
ControlPlaneServReq ::= SEQUENCE {
   nasKeySetIdent NASKeySetIdentifier,
   ctrlPlaneServType ControlPlaneServiceType,
   --<iei format="tv" length="1">08</iei>
   containerType PayloadContainerType OPTIONAL,
   --<iei format="tlv-e">7B</iei>
   --<inline/>
   container CHOICE {
      /* The only options currently allowed are CIoT user data, SMS or
         location services message.  See 8.2.30.4. */
      --<selector element="containerType" value="2"/>
      sms SMSMessage,
      --<selector element="containerType" value="7"/>
      locSvcs OpaqueData,
      --<selector element="containerType" value="8"/>
      cIOTUserData UserDataContainer
   } OPTIONAL,
   --<iei format="tv" length="2">12</iei>
   pduSessionId PDUSessionId2 OPTIONAL,
   --<iei format="tlv">50</iei>
   sessionStat PDUSessionStatus OPTIONAL,
   --<iei format="tv" length="1">0F</iei>
   releaseAssistIndication ReleaseAssistInd OPTIONAL,
   --<iei format="tlv">40</iei>
   uplinkStat UplinkDataStatus OPTIONAL,
   --<iei format="tlv-e">71</iei>
   nasMsgContainer NASMessageContainer2 OPTIONAL,
   ...,
   [[ 16:
   --<iei format="tlv">24</iei>
   addlInfo AdditionalInfo OPTIONAL, -- added in 16.3
   --<iei format="tlv">6F</iei>
   ciotSmallDataContainer CIoTSmallDataContainer OPTIONAL -- added in 16.4.0
   ]],
   [[ 17:
   --<iei format="tlv">25</iei>
   allowedPduSessStat AllowedPDUSessionStatus OPTIONAL -- added in v17.1.0
   -- iei not yet defined in 17.3.0 format="tlv">
   -- ueRequestType UERequestType OPTIONAL
   -- iei not yet defined in 17.3.0 format="tlv">
   -- pagingRestriction PagingRestriction OPTIONAL
   ]]
}

/* 8.2.31 Network slice-specific authentication command - message added in v16.4.0 */

mt-NetSliceAuthCmd5G INTEGER ::= 80

obj-NetSliceAuthCmd5G NAS5G-PROTOCOL-CLASS ::= {
   ID mobMgmt5G, mt-NetSliceAuthCmd5G
   TYPE NetSliceAuthCmd
}

--<is3GMessage/>
NetSliceAuthCmd ::= SEQUENCE {
   snssai SNSSAI,
   eapMessage EAPMessage
}

/* 8.2.32 Network slice-specific authentication complete - message added in v16.4.0 */

mt-NetSliceAuthDone5G INTEGER ::= 81

obj-NetSliceAuthDone5G NAS5G-PROTOCOL-CLASS ::= {
   ID mobMgmt5G, mt-NetSliceAuthDone5G
   TYPE NetSliceAuthDone
}

--<is3GMessage/>
NetSliceAuthDone ::= SEQUENCE {
   snssai SNSSAI,
   eapMessage EAPMessage
}

/* 8.2.33 Network slice-specific authentication result - message added in v16.4.0 */

mt-NetSliceAuthResult5G INTEGER ::= 82

obj-NetSliceAuthResult5G NAS5G-PROTOCOL-CLASS ::= {
   ID mobMgmt5G, mt-NetSliceAuthResult5G
   TYPE NetSliceAuthResult
}

--<is3GMessage/>
NetSliceAuthResult ::= SEQUENCE {
   snssai SNSSAI,
   eapMessage EAPMessage
}


/* -- SESSION MANAGEMENT MESSAGES --- */

/* 8.3.1 PDU session establishment request */

st-EstablishRequest5G INTEGER ::= 193

obj-EstablishRequest5G NAS5G-PROTOCOL-CLASS ::= {
   ID sessMgmt5G, st-EstablishRequest5G
   TYPE EstablishRequest
}

--<is3GMessage/>
EstablishRequest ::= SEQUENCE {
   integProtMaxRate IntegrityProtMaxDataRate, -- added in v15.1.0
   --<iei format="tv" length="1">9</iei>
   pduSessionType PDUSessionType OPTIONAL,
   --<iei format="tv" length="1">0A</iei>
   sscMode SSCMode OPTIONAL,
   --<iei format="tlv">28</iei>
   capability SMCapability OPTIONAL,
   --<iei format="tv" length="3">55</iei>
   maxPktFilters MaxSupportedPacketFilters OPTIONAL,
   --<iei format="tv" length="1">B</iei>
   alwaysOnPDUSession AlwaysOnPDUSessionReq OPTIONAL, -- added in v15.1.0
   --<iei format="tlv">39</iei>
   reqContainer SmPduDnReqContainer OPTIONAL, -- added in v15.2.0
   --<iei format="tlv-e">7B</iei>
   extProtoCfgOpts ExtProtoConfigOptions OPTIONAL,
   ...,
   [[ 16:
   --<iei format="tlv">66</iei>
   headerCompressionCfg HeaderCompressionConfig OPTIONAL, -- Added in v16.2.0
   --<iei format="tlv">6E</iei>
   dsttPortMacAddr DSTTEthMACAddr OPTIONAL, -- Added in v16.3
   --<iei format="tlv">6F</iei>
   dsttResidenceTime DSTTResidenceTime OPTIONAL, -- Added in v16.3
   --<iei format="tlv-e">74</iei>
   portMgmtInfoContainer PortMgmtInfoContainer OPTIONAL, -- Added in v16.3
   --<iei format="tlv">1F</iei>
   ethernetHdrCompressionCfg EthHdrCompressConfig OPTIONAL, -- Added in v16.5.1
   --<iei format="tlv">29</iei>
   suggestedInterfaceId PDUAddress OPTIONAL -- Added in v16.6
   ]]
}

/* 8.3.2 PDU session establishment accept */

st-EstablishAccept5G INTEGER ::= 194

obj-EstablishAccept5G NAS5G-PROTOCOL-CLASS ::= {
   ID sessMgmt5G, st-EstablishAccept5G
   TYPE EstablishAccept
}

--<is3GMessage/>
EstablishAccept ::= SEQUENCE {
   sscMode SSCMode,
   pduSessionType PDUSessionType,
   qosRules QoSRules,
   sessionAMBR SessionAMBR,
   --<iei format="tv" length="2">59</iei>
   cause SMCause OPTIONAL,
   --<iei format="tlv">29</iei>
   pduAddress PDUAddress OPTIONAL,
   --<iei format="tv" length="2">56</iei>
   rqTimer GPRSTimer OPTIONAL,
   --<iei format="tlv">22</iei>
   snssai SNSSAI OPTIONAL,
   --<iei format="tv" length="1">8</iei>
   alwaysOnPDUSession AlwaysOnPDUSessionInd OPTIONAL, -- added in v15.1.0
   --<iei format="tlv-e">75</iei>
   epsBearerCtxts EPSBearerCtxts OPTIONAL,
   --<iei format="tlv-e">78</iei>
   eapMessage EAPMessage OPTIONAL,
   --<iei format="tlv-e">79</iei>
   qosFlowDesr QOSFlowDescriptions OPTIONAL, -- added in v15.1.0
   --<iei format="tlv-e">7B</iei>
   extProtoCfgOpts ExtProtoConfigOptions OPTIONAL,
   --<iei format="tlv">25</iei>
   dnn DNNList OPTIONAL,
   ...,
   [[ 16:
   --<iei format="tlv">17</iei>
   smNetFeatureSupport SMNetworkFeatureSupport OPTIONAL, -- Added in v16.4.0
   --<iei format="tlv">18</iei>
   servingPLMNRateCtrl ServPLMNRateCtrl OPTIONAL, -- Added in v16.4.0
   --<iei format="tlv-e">77</iei>
   atsssContainer ATSSSContainer OPTIONAL, -- Added in v16.4.0
   --<iei format="tv" length="1">0C</iei>
   ctrlPlaneOnlyIndication ControlPlaneIndication OPTIONAL, -- Added in v16.4.0
   --<iei format="tlv">66</iei>
   headerCompressionCfg HeaderCompressionConfig OPTIONAL, -- Added in v16.2.0
   --<iei format="tlv">1F</iei>
   ethernetHdrCompressionCfg EthHdrCompressConfig OPTIONAL -- Added in v16.5.1
   ]]
}

/* 8.3.3 PDU session establishment reject */

st-EstablishReject5G INTEGER ::= 195

obj-EstablishReject5G NAS5G-PROTOCOL-CLASS ::= {
   ID sessMgmt5G, st-EstablishReject5G
   TYPE EstablishReject
}

--<is3GMessage/>
EstablishReject ::= SEQUENCE {
   cause SMCause,
   --<iei format="tlv">37</iei>
   backoffTimer GPRSTimer3 OPTIONAL,
   --<iei format="tv" length="1">0F</iei>
   allowedSSCMode AllowedSSCMode OPTIONAL, 
   --<iei format="tlv-e">78</iei>
   eapMessage EAPMessage OPTIONAL,
   --<iei format="tlv-e">7B</iei>
   extProtoCfgOpts ExtProtoConfigOptions OPTIONAL,
   --<iei format="tlv">61</iei>
   congestionReattemptInd CongestionReattemptIndicator OPTIONAL, -- Added in v15.4.0
   ...,
   [[ 16:
   --<iei format="tlv">1D</iei>
   reattemptInd ReattemptIndicator OPTIONAL -- Added in v16.4.1
   ]]
}

/* 8.3.4 PDU session authentication command */

st-AuthCmd5G INTEGER ::= 197

obj-SMAuthCmd5G NAS5G-PROTOCOL-CLASS ::= {
   ID sessMgmt5G, st-AuthCmd5G
   TYPE SMAuthCmd
}

--<is3GMessage/>
SMAuthCmd ::= SEQUENCE {
   eapMessage EAPMessage,
   --<iei format="tlv-e">7B</iei>
   extProtoCfgOpts ExtProtoConfigOptions OPTIONAL
}

/* 8.3.5 PDU session authentication complete */

st-AuthDone5G INTEGER ::= 198

obj-SMAuthDone5G NAS5G-PROTOCOL-CLASS ::= {
   ID sessMgmt5G, st-AuthDone5G
   TYPE SMAuthDone
}

--<is3GMessage/>
SMAuthDone ::= SEQUENCE {
   eapMessage EAPMessage,
   --<iei format="tlv-e">7B</iei>
   extProtoCfgOpts ExtProtoConfigOptions OPTIONAL
}

/* 8.3.6 PDU session authentication result */

st-AuthResult5G INTEGER ::= 199

obj-SMAuthResult5G NAS5G-PROTOCOL-CLASS ::= {
   ID sessMgmt5G, st-AuthResult5G
   TYPE SMAuthResult
}

--<is3GMessage/>
SMAuthResult ::= SEQUENCE {
   --<iei format="tlv-e">78</iei>
   eapMessage EAPMessage OPTIONAL,
   --<iei format="tlv-e">7B</iei>
   extProtoCfgOpts ExtProtoConfigOptions OPTIONAL
}

/* 8.3.7 PDU session modification request */

st-ModifyRequest5G INTEGER ::= 201

obj-ModifyRequest5G NAS5G-PROTOCOL-CLASS ::= {
   ID sessMgmt5G, st-ModifyRequest5G
   TYPE ModifyRequest
}

--<is3GMessage/>
ModifyRequest ::= SEQUENCE {
   --<iei format="tlv">28</iei>
   capability SMCapability OPTIONAL,
   --<iei format="tv" length="2">59</iei>
   cause SMCause OPTIONAL, -- added in v15.1.0
   --<iei format="tv" length="3">55</iei>
   maxPktFilters MaxSupportedPacketFilters OPTIONAL,
   --<iei format="tv" length="1">B</iei>
   alwaysOnPDUSession AlwaysOnPDUSessionReq OPTIONAL, -- added in v15.1.0
   --<iei format="tv" length="3">13</iei>
   integProtMaxRate IntegrityProtMaxDataRate OPTIONAL, -- added in v15.1.0
   --<iei format="tlv-e">7A</iei>
   qosRules QoSRules OPTIONAL,
   --<iei format="tlv-e">79</iei>
   qosFlowDesr QOSFlowDescriptions OPTIONAL, -- added in v15.1.0
   --<iei format="tlv-e">75</iei>
   epsBearerCtxts EPSBearerCtxts OPTIONAL, -- added in v15.2.0
   --<iei format="tlv-e">7B</iei>
   extProtoCfgOpts ExtProtoConfigOptions OPTIONAL,
   ...,
   [[ 16:
   --<iei format="tlv-e">74</iei>
   portMgmtInfoContainer PortMgmtInfoContainer OPTIONAL, -- Added in v16.3
   --<iei format="tlv">66</iei>
   headerCompressionCfg HeaderCompressionConfig OPTIONAL, -- Added in v16.4.1
   --<iei format="tlv">1F</iei>
   ethernetHdrCompressionCfg EthHdrCompressConfig OPTIONAL -- Added in v16.5.1
   ]]
}

/* 8.3.8 PDU session modification reject */

st-ModifyReject5G INTEGER ::= 202

obj-ModifyReject5G NAS5G-PROTOCOL-CLASS ::= {
   ID sessMgmt5G, st-ModifyReject5G
   TYPE ModifyReject
}

--<is3GMessage/>
ModifyReject ::= SEQUENCE {
   cause SMCause,
   --<iei format="tlv">37</iei>
   backoffTimer GPRSTimer3 OPTIONAL,
   --<iei format="tlv-e">7B</iei>
   extProtoCfgOpts ExtProtoConfigOptions OPTIONAL,
   --<iei format="tlv">61</iei>
   congestionReattemptInd CongestionReattemptIndicator OPTIONAL, -- Added in v15.4.0
   ...,
   [[ 16:
   --<iei format="tlv">1D</iei>
   reattemptInd ReattemptIndicator OPTIONAL -- Added in v16.4.1
   ]]
}

/* 8.3.9 PDU session modification command */

st-ModifyCmd5G INTEGER ::= 203

obj-ModifyCmd5G NAS5G-PROTOCOL-CLASS ::= {
   ID sessMgmt5G, st-ModifyCmd5G
   TYPE ModifyCmd
}

--<is3GMessage/>
ModifyCmd ::= SEQUENCE {
   --<iei format="tv" length="2">59</iei>
   cause SMCause OPTIONAL,
   --<iei format="tlv">2A</iei>
   sessionAMBR SessionAMBR OPTIONAL,
   --<iei format="tv" length="2">56</iei>
   rqTimer GPRSTimer OPTIONAL,
   --<iei format="tv" length="1">8</iei>
   alwaysOnPDUSession AlwaysOnPDUSessionReq OPTIONAL, -- added in v15.1.0
   --<iei format="tlv-e">7A</iei>
   qosRules QoSRules OPTIONAL,
   --<iei format="tlv-e">75</iei>
   epsBearerCtxts EPSBearerCtxts OPTIONAL,
   --<iei format="tlv-e">79</iei>
   qosFlowDesr QOSFlowDescriptions OPTIONAL, -- added in v15.1.0
   --<iei format="tlv-e">7B</iei>
   extProtoCfgOpts ExtProtoConfigOptions OPTIONAL,
   ...,
   [[ 16:
   --<iei format="tlv-e">77</iei>
   atsssContainer ATSSSContainer OPTIONAL, -- Added in v16.4.1
   --<iei format="tlv">66</iei>
   headerCompressionCfg HeaderCompressionConfig OPTIONAL, -- Added in v16.2.0
   --<iei format="tlv-e">74</iei>
   portMgmtInfoContainer PortMgmtInfoContainer OPTIONAL, -- Added in v16.3
   --<iei format="tlv">1E</iei>
   servingPLMNRateCtrl ServPLMNRateCtrl OPTIONAL, -- Added in v16.4.1
   --<iei format="tlv">1F</iei>
   ethernetHdrCompressionCfg EthHdrCompressConfig OPTIONAL -- Added in v16.5.1
   ]]
}

/* 8.3.10 PDU session modification complete */

st-ModifyDone5G INTEGER ::= 204

obj-ModifyDone5G NAS5G-PROTOCOL-CLASS ::= {
   ID sessMgmt5G, st-ModifyDone5G
   TYPE ModifyDone
}

--<is3GMessage/>
ModifyDone ::= SEQUENCE {
   --<iei format="tlv-e">7B</iei>
   extProtoCfgOpts ExtProtoConfigOptions OPTIONAL,
   ...,
   [[ 16:
   --<iei format="tlv-e">74</iei>
   portMgmtInfoContainer PortMgmtInfoContainer OPTIONAL -- Added in v16.3
   ]]
}

/* 8.3.11 PDU session modification command reject */

st-ModifyCmdReject5G INTEGER ::= 205

obj-ModifyCmdReject5G NAS5G-PROTOCOL-CLASS ::= {
   ID sessMgmt5G, st-ModifyCmdReject5G
   TYPE ModifyCmdReject
}

--<is3GMessage/>
ModifyCmdReject ::= SEQUENCE {
   cause SMCause,
   --<iei format="tlv-e">7B</iei>
   extProtoCfgOpts ExtProtoConfigOptions OPTIONAL
}

/* 8.3.12 PDU session release request */

st-ReleaseRequest5G INTEGER ::= 209

obj-ReleaseRequest5G NAS5G-PROTOCOL-CLASS ::= {
   ID sessMgmt5G, st-ReleaseRequest5G
   TYPE ReleaseRequest
}

--<is3GMessage/>
ReleaseRequest ::= SEQUENCE {
   --<iei format="tv" length="2">59</iei>
   cause SMCause OPTIONAL, -- added in v15.1.0
   --<iei format="tlv-e">7B</iei>
   extProtoCfgOpts ExtProtoConfigOptions OPTIONAL
}

/* 8.3.13 PDU session release reject */

st-ReleaseReject5G INTEGER ::= 210

obj-ReleaseReject5G NAS5G-PROTOCOL-CLASS ::= {
   ID sessMgmt5G, st-ReleaseReject5G
   TYPE ReleaseReject
}

--<is3GMessage/>
ReleaseReject ::= SEQUENCE {
   cause SMCause,
   --<iei format="tlv-e">7B</iei>
   extProtoCfgOpts ExtProtoConfigOptions OPTIONAL
}

/* 8.3.14 PDU session release command */

st-ReleaseCmd5G INTEGER ::= 211

obj-ReleaseCmd5G NAS5G-PROTOCOL-CLASS ::= {
   ID sessMgmt5G, st-ReleaseCmd5G
   TYPE ReleaseCmd
}

--<is3GMessage/>
ReleaseCmd ::= SEQUENCE {
   cause SMCause,
   --<iei format="tlv">37</iei>
   backoffTimer GPRSTimer3 OPTIONAL,
   --<iei format="tlv-e">78</iei>
   eapMessage EAPMessage OPTIONAL,
   --<iei format="tlv">61</iei>
   congestionReattemptInd CongestionReattemptIndicator OPTIONAL, -- Added in v15.4.0
   --<iei format="tlv-e">7B</iei>
   extProtoCfgOpts ExtProtoConfigOptions OPTIONAL,
   ...,
   [[ 16:
   --<iei format="tv" length="1">0D</iei>
   accessType AccessType OPTIONAL -- Added in v16.4.1
   ]]
}

/* 8.3.15 PDU session release complete */

st-ReleaseDone5G INTEGER ::= 212

obj-ReleaseDone5G NAS5G-PROTOCOL-CLASS ::= {
   ID sessMgmt5G, st-ReleaseDone5G
   TYPE ReleaseDone
}

--<is3GMessage/>
ReleaseDone ::= SEQUENCE {
   --<iei format="tv" length="2">59</iei>
   cause SMCause OPTIONAL, -- added in v15.1.0
   --<iei format="tlv-e">7B</iei>
   extProtoCfgOpts ExtProtoConfigOptions OPTIONAL
}

/* 8.3.16 5GSM status */

st-SMStatus5G INTEGER ::= 214

obj-SMStatus5G NAS5G-PROTOCOL-CLASS ::= {
   ID sessMgmt5G, st-SMStatus5G
   TYPE SMStatus
}

--<is3GMessage/>
SMStatus ::= SEQUENCE {
   cause SMCause
}

END
