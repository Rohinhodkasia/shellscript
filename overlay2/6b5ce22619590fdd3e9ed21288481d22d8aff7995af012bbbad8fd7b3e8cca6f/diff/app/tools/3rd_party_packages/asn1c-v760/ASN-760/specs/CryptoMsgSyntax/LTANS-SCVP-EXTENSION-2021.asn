LTANS-SCVP-EXTENSION-2021
{ iso(1) identified-organization(3) dod(6) internet(1)
  security(5) mechanisms(5) ltans(11) id-mod(0)
id-mod-ers-scvp(5) id-mod-ers-scvp-v2(2) }

DEFINITIONS IMPLICIT TAGS ::=
BEGIN

EXPORTS ALL;

IMPORTS

id-swb, CertBundle, WANT-BACK, AllWantBacks
FROM SCVP-2009 -- in [RFC5912]
{ iso(1) identified-organization(3) dod(6) internet(1)
  security(5) mechanisms(5) pkix(7) id-mod(0)
id-mod-scvp-02(52) }

EvidenceRecord
FROM ERS-2021 -- in [ThisRFC]
{ iso(1) identified-organization(3) dod(6) internet(1)
  security(5) mechanisms(5) ltans(11) id-mod(0)
id-mod-ers(1) id-mod-ers-v2(2) }
;

EvidenceRecordWantBack ::= SEQUENCE {
  targetWantBack  WANT-BACK.&id ({ExpandedWantBacks}),
evidenceRecord  EvidenceRecord OPTIONAL }

EvidenceRecordWantBacks ::= SEQUENCE SIZE (1..MAX) OF
EvidenceRecordWantBack

EvidenceRecords ::= SEQUENCE SIZE (1..MAX) OF EvidenceRecord

ExpandedWantBacks WANT-BACK ::= { AllWantBacks |
  NewWantBacks |
ERSWantBacks, ... }

NewWantBacks WANT-BACK ::= { swb-partial-cert-path, ... }

swb-partial-cert-path WANT-BACK ::=
{ CertBundle IDENTIFIED BY id-swb-partial-cert-path }

id-swb-partial-cert-path OBJECT IDENTIFIER ::= { id-swb 15 }

ERSWantBacks WANT-BACK ::= { swb-ers-pkc-cert |
  swb-ers-best-cert-path |
  swb-ers-partial-cert-path |
  swb-ers-revocation-info |
swb-ers-all, ... }

swb-ers-pkc-cert WANT-BACK ::=
{ EvidenceRecord IDENTIFIED BY id-swb-ers-pkc-cert }

id-swb-ers-pkc-cert OBJECT IDENTIFIER ::= { id-swb 16 }

swb-ers-best-cert-path WANT-BACK ::=
{ EvidenceRecord IDENTIFIED BY id-swb-ers-best-cert-path }

id-swb-ers-best-cert-path OBJECT IDENTIFIER ::= { id-swb 17 }

swb-ers-partial-cert-path WANT-BACK ::=
{ EvidenceRecord IDENTIFIED BY id-swb-ers-partial-cert-path }

id-swb-ers-partial-cert-path OBJECT IDENTIFIER ::= { id-swb 18 }

swb-ers-revocation-info WANT-BACK ::=
{ EvidenceRecords IDENTIFIED BY id-swb-ers-revocation-info }

id-swb-ers-revocation-info OBJECT IDENTIFIER ::= { id-swb 19 }

swb-ers-all WANT-BACK ::=
{ EvidenceRecordWantBacks IDENTIFIED BY id-swb-ers-all }

id-swb-ers-all OBJECT IDENTIFIER ::= { id-swb 20 }

END
