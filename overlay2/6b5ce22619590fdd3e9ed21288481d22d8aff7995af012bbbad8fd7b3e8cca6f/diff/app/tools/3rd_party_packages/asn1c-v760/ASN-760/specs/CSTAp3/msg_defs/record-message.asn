CSTA-record-message
	{ iso( 1) identified-organization( 3) icd-ecma( 12)
		standard( 0) csta3( 285) record-message( 511) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
ResourceID, MessageID, EncodingAlgorithm, TerminatingConditions 
	FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

recordMessage OPERATION ::=
{	ARGUMENT		RecordMessageArgument
	RESULT			RecordMessageResult
	ERRORS			{universalFailure }
	CODE			local: 511 }

RecordMessageArgument ::= SEQUENCE
{	callToBeRecorded		ConnectionID,
	resource			[2] IMPLICIT ResourceID			OPTIONAL,
	samplingRate			[0] IMPLICIT INTEGER			OPTIONAL,
	encodingAlgorithm		EncodingAlgorithm			OPTIONAL,
	maxDuration			[1] IMPLICIT INTEGER			OPTIONAL,
	termination			TerminatingConditions			OPTIONAL,
	extensions			CSTACommonArguments			OPTIONAL }

RecordMessageResult ::= SEQUENCE
{	resultingMessage		MessageID,
	extensions			CSTACommonArguments			OPTIONAL }

END  -- of CSTA-record-message
