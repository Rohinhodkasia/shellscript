-- This file was generated by the Objective Systems ASN1C Compiler
-- (http://www.obj-sys.com).  Version: 6.8.A, Date: 15-Nov-2014.

SUPL-TRIGGERED-START DEFINITIONS AUTOMATIC TAGS ::= BEGIN

IMPORTS

LocationId, QoP, Ver, Position
FROM ULP-Components 

MultipleLocationIds, CauseCode, ThirdParty, ApplicationID, ReportingCap, 
   Coordinate, CircularArea, EllipticalArea, PolygonArea
FROM Ver2-ULP-Components 

SETCapabilities
FROM SUPL-START 

Ver3-SUPL-TRIGGERED-START-extension
FROM ULP-Version-3-message-extensions ;

-- Productions

TriggerType ::= ENUMERATED { periodic(0), areaEvent(1), ... }

GeographicTargetArea ::= CHOICE {
   circularArea [0] CircularArea,
   ellipticalArea [1] EllipticalArea,
   polygonArea [2] PolygonArea,
   ...
}

GeographicTargetAreaList ::= SEQUENCE (SIZE (1..maxNumGeoArea)) OF GeographicTargetArea

GSMAreaId ::= SEQUENCE {
   refMCC [0] INTEGER (0..999) OPTIONAL,
   refMNC [1] INTEGER (0..999) OPTIONAL,
   refLAC [2] INTEGER (0..65535) OPTIONAL,
   refCI [3] INTEGER (0..65535) OPTIONAL,
   ...
}

WCDMAAreaId ::= SEQUENCE {
   refMCC [0] INTEGER (0..999) OPTIONAL,
   refMNC [1] INTEGER (0..999) OPTIONAL,
   refLAC [2] INTEGER (0..65535) OPTIONAL,
   refUC [3] INTEGER (0..268435455) OPTIONAL,
   ...
}

CDMAAreaId ::= SEQUENCE {
   refSID [0] INTEGER (0..65535) OPTIONAL,
   refNID [1] INTEGER (0..32767) OPTIONAL,
   refBASEID [2] INTEGER (0..65535) OPTIONAL,
   ...
}

HRPDAreaId ::= SEQUENCE {
   refSECTORID [0] BIT STRING  (SIZE (128)),
   ...
}

UMBAreaId ::= SEQUENCE {
   refMCC [0] INTEGER (0..999) OPTIONAL,
   refMNC [1] INTEGER (0..999) OPTIONAL,
   refSECTORID [2] BIT STRING  (SIZE (128)) OPTIONAL,
   ...
}

LTEAreaId ::= SEQUENCE {
   refMCC [0] INTEGER (0..999) OPTIONAL,
   refMNC [1] INTEGER (0..999) OPTIONAL,
   refCI [2] BIT STRING  (SIZE (29)) OPTIONAL,
   ...
}

WLANAreaId ::= SEQUENCE {
   apMACAddress [0] BIT STRING  (SIZE (48)),
   ...
}

WimaxAreaId ::= SEQUENCE {
   bsID-MSB [0] BIT STRING  (SIZE (24)) OPTIONAL,
   bsID-LSB [1] BIT STRING  (SIZE (24))
}

AreaId ::= CHOICE {
   gSMAreaId [0] GSMAreaId,
   wCDMAAreaId [1] WCDMAAreaId,
   cDMAAreaId [2] CDMAAreaId,
   hRPDAreaId [3] HRPDAreaId,
   uMBAreaId [4] UMBAreaId,
   lTEAreaId [5] LTEAreaId,
   wLANAreaId [6] WLANAreaId,
   wiMAXAreaId [7] WimaxAreaId,
   ...
}

AreaIdSet ::= SEQUENCE (SIZE (1..maxAreaId)) OF AreaId

AreaIdSetType ::= ENUMERATED { border(0), within(1), ... }

GeoAreaIndex ::= INTEGER (1..maxNumGeoArea)

GeoAreaMappingList ::= SEQUENCE (SIZE (1..maxNumGeoArea)) OF GeoAreaIndex

AreaIdList ::= SEQUENCE {
   areaIdSet [0] AreaIdSet,
   areaIdSetType [1] AreaIdSetType OPTIONAL,
   geoAreaMappingList [2] GeoAreaMappingList OPTIONAL
}

PeriodicParams ::= SEQUENCE {
   numberOfFixes [0] INTEGER (1..8639999),
   intervalBetweenFixes [1] INTEGER (1..8639999),
   startTime [2] INTEGER (0..2678400) OPTIONAL,
   ...
}

AreaEventType ::= ENUMERATED { enteringArea(0), insideArea(1), outsideArea(2), 
   leavingArea(3), ... }

RepeatedReportingParams ::= SEQUENCE {
   minimumIntervalTime [0] INTEGER (1..604800),
   maximumNumberOfReports [1] INTEGER (1..1024),
   ...
}

AreaEventParams ::= SEQUENCE {
   areaEventType [0] AreaEventType,
   locationEstimate [1] BOOLEAN,
   repeatedReportingParams [2] RepeatedReportingParams OPTIONAL,
   startTime [3] INTEGER (0..2678400) OPTIONAL,
   stopTime [4] INTEGER (0..11318399) OPTIONAL,
   geographicTargetAreaList [5] GeographicTargetAreaList OPTIONAL,
   areaIdLists [6] SEQUENCE (SIZE (1..maxAreaIdList)) OF AreaIdList OPTIONAL,
   ...
}

TriggerParams ::= CHOICE {
   periodicParams [0] PeriodicParams,
   areaEventParams [1] AreaEventParams,
   ...
}

Ver2-SUPLTRIGGEREDSTART ::= SEQUENCE {
   sETCapabilities [0] SETCapabilities,
   locationId [1] LocationId,
   ver [2] Ver OPTIONAL,
   qoP [3] QoP OPTIONAL,
   multipleLocationIds [4] MultipleLocationIds OPTIONAL,
   thirdParty [5] ThirdParty OPTIONAL,
   applicationID [6] ApplicationID OPTIONAL,
   triggerType [7] TriggerType OPTIONAL,
   triggerParams [8] TriggerParams OPTIONAL,
   position [9] Position OPTIONAL,
   reportingCap [10] ReportingCap OPTIONAL,
   causeCode [11] CauseCode OPTIONAL,
   ...,
   ver3-SUPL-TRIGGERED-START-extension [12] Ver3-SUPL-TRIGGERED-START-extension
       OPTIONAL
}

-- Value assignments

maxNumGeoArea INTEGER ::= 32

maxAreaId INTEGER ::= 256

maxAreaIdList INTEGER ::= 32


END
