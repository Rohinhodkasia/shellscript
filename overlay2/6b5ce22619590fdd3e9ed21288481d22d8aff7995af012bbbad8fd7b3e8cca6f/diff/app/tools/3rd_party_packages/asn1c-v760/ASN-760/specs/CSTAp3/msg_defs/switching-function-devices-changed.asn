CSTA-switching-function-devices-changed
	{ iso( 1) identified-organization( 3) icd-ecma( 12)
		standard( 0) csta3( 285) switching-function-devices-changed( 213) }

DEFINITIONS ::=
BEGIN

IMPORTS
OPERATION, ERROR FROM Remote-Operations-Information-Objects
	{joint-iso-itu-t remote-operations(4) informationObjects(5) version1(0) }

-- Data Types --
universalFailure FROM CSTA-error-definition
	{ iso( 1) identified-organization( 3) icd-ecma( 12)
		standard( 0) csta3( 285) error-definition( 120) }
SysStatRegisterID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

swFunctionDevicesChanged OPERATION ::=
{ 	ARGUMENT 		SwFunctionDevicesChangedArg
	RESULT 			SwFunctionDevicesChangedRes
	ERRORS 			{universalFailure }
	CODE 			local: 213 }

SwFunctionDevicesChangedArg ::= SEQUENCE
{ 	sysStatRegisterID 		SysStatRegisterID 		OPTIONAL,
	extensions 			CSTACommonArguments 		OPTIONAL }

SwFunctionDevicesChangedRes ::= CHOICE
{ 	extensions 			CSTACommonArguments,
	noData 				NULL }

END -- of CSTA-switching-function-devices-changed
