-- This file was generated by the Objective Systems ASN1C Compiler
-- (http://www.obj-sys.com).  Version: 7.1.4, Date: 06-Dec-2017.

LPP-PDU-Definitions 
{
itu-t (0) identified-organization (4) etsi (0) mobileDomain (0) 
eps-Access (21) modules (3) lpp (7) version1 (1) lpp-PDU-Definitions (1) }
DEFINITIONS AUTOMATIC TAGS ::= BEGIN

-- Productions

SequenceNumber ::= INTEGER (0..255)

Initiator ::= ENUMERATED { locationServer(0), targetDevice(1), ... }

TransactionNumber ::= INTEGER (0..255)

ARFCN-ValueEUTRA ::= INTEGER (0..maxEARFCN)

ARFCN-ValueEUTRA-v9a0 ::= INTEGER (maxEARFCN-Plus1..maxEARFCN2)

ARFCN-ValueUTRA ::= INTEGER (0..16383)

EPDU-ID ::= INTEGER (1..256)

EPDU-Name ::= VisibleString (SIZE (1..32))

EPDU-Body ::= OCTET STRING

LocationInformationType ::= ENUMERATED { locationEstimateRequired(0), 
   locationMeasurementsRequired(1), locationEstimatePreferred(2), 
   locationMeasurementsPreferred(3), ... }

ReportingDuration ::= INTEGER (0..255)

AdditionalInformation ::= ENUMERATED { onlyReturnInformationRequested(0), 
   mayReturnAditionalInformation(1), ... }

Environment ::= ENUMERATED { badArea(0), notBadArea(1), mixedArea(2), ... }

LocationFailureCause ::= ENUMERATED { undefined(0), 
   requestedMethodNotSupported(1), positionMethodFailure(2), 
   periodicLocationMeasurementsNotAvailable(3), ... }

EarlyFixReport-r12 ::= ENUMERATED { noMoreMessages(0), moreMessagesOnTheWay(1)
    }

LocationSource-r13 ::= BIT STRING  { a-gnss(0), wlan(1), bt(2), tbs(3), 
   sensor(4) } (SIZE (1..16))

LPP-TransactionID ::= SEQUENCE {
   initiator [0] Initiator,
   transactionNumber [1] TransactionNumber,
   ...
}

Acknowledgement ::= SEQUENCE {
   ackRequested [0] BOOLEAN,
   ackIndicator [1] SequenceNumber OPTIONAL
}

CommonIEsRequestCapabilities ::= SEQUENCE {
   ...
}

A-GNSS-RequestCapabilities ::= SEQUENCE {
   gnss-SupportListReq [0] BOOLEAN,
   assistanceDataSupportListReq [1] BOOLEAN,
   locationVelocityTypesReq [2] BOOLEAN,
   ...
}

OTDOA-RequestCapabilities ::= SEQUENCE {
   ...
}

ECID-RequestCapabilities ::= SEQUENCE {
   ...
}

EPDU-Identifier ::= SEQUENCE {
   ePDU-ID [0] EPDU-ID,
   ePDU-Name [1] EPDU-Name OPTIONAL,
   ...
}

EPDU ::= SEQUENCE {
   ePDU-Identifier [0] EPDU-Identifier,
   ePDU-Body [1] EPDU-Body
}

EPDU-Sequence ::= SEQUENCE (SIZE (1..maxEPDU)) OF EPDU

Sensor-RequestCapabilities-r13 ::= SEQUENCE {
   ...
}

TBS-RequestCapabilities-r13 ::= SEQUENCE {
   ...
}

WLAN-RequestCapabilities-r13 ::= SEQUENCE {
   ...
}

BT-RequestCapabilities-r13 ::= SEQUENCE {
   ...
}

RequestCapabilities-r9-IEs ::= SEQUENCE {
   commonIEsRequestCapabilities [0] CommonIEsRequestCapabilities OPTIONAL,
   a-gnss-RequestCapabilities [1] A-GNSS-RequestCapabilities OPTIONAL,
   otdoa-RequestCapabilities [2] OTDOA-RequestCapabilities OPTIONAL,
   ecid-RequestCapabilities [3] ECID-RequestCapabilities OPTIONAL,
   epdu-RequestCapabilities [4] EPDU-Sequence OPTIONAL,
   ...,
   [[ 2:
      sensor-RequestCapabilities-r13 [5] Sensor-RequestCapabilities-r13
          OPTIONAL,
      tbs-RequestCapabilities-r13 [6] TBS-RequestCapabilities-r13 OPTIONAL,
      wlan-RequestCapabilities-r13 [7] WLAN-RequestCapabilities-r13 OPTIONAL,
      bt-RequestCapabilities-r13 [8] BT-RequestCapabilities-r13 OPTIONAL
   ]]
}

RequestCapabilities ::= SEQUENCE {
   criticalExtensions [0] CHOICE {
      c1 [0] CHOICE {
         requestCapabilities-r9 [0] RequestCapabilities-r9-IEs,
         spare3 [1] NULL,
         spare2 [2] NULL,
         spare1 [3] NULL
      },
      criticalExtensionsFuture [1] SEQUENCE {

      }
   }
}

CommonIEsProvideCapabilities ::= SEQUENCE {
   ...
}

GNSS-ID ::= SEQUENCE {
   gnss-id [0] ENUMERATED { gps(0), sbas(1), qzss(2), galileo(3), glonass(4), 
      ..., bds(5) },
   ...
}

SBAS-IDs ::= SEQUENCE {
   sbas-IDs [0] BIT STRING  { waas(0), egnos(1), msas(2), gagan(3) } (SIZE (1..8)
      ),
   ...
}

PositioningModes ::= SEQUENCE {
   posModes [0] BIT STRING  { standalone(0), ue-based(1), ue-assisted(2) } (
      SIZE (1..8)),
   ...
}

GNSS-SignalIDs ::= SEQUENCE {
   gnss-SignalIDs [0] BIT STRING  (SIZE (8)),
   ...
}

AccessTypes ::= SEQUENCE {
   accessTypes [0] BIT STRING  { eutra(0), utra(1), gsm(2) } (SIZE (1..8)),
   ...
}

GNSS-SupportElement ::= SEQUENCE {
   gnss-ID [0] GNSS-ID,
   sbas-IDs [1] SBAS-IDs OPTIONAL,
   agnss-Modes [2] PositioningModes,
   gnss-Signals [3] GNSS-SignalIDs,
   fta-MeasSupport [4] SEQUENCE {
      cellTime [0] AccessTypes,
      mode [1] PositioningModes,
      ...
   } OPTIONAL,
   adr-Support [5] BOOLEAN,
   velocityMeasurementSupport [6] BOOLEAN,
   ...
}

GNSS-SupportList ::= SEQUENCE (SIZE (1..16)) OF GNSS-SupportElement

GNSS-ID-Bitmap ::= SEQUENCE {
   gnss-ids [0] BIT STRING  { gps(0), sbas(1), qzss(2), galileo(3), glonass(4)
      , bds(5) } (SIZE (1..16)),
   ...
}

GNSS-ReferenceTimeSupport ::= SEQUENCE {
   gnss-SystemTime [0] GNSS-ID-Bitmap,
   fta-Support [1] AccessTypes OPTIONAL,
   ...
}

GNSS-ReferenceLocationSupport ::= SEQUENCE {
   ...
}

GNSS-IonosphericModelSupport ::= SEQUENCE {
   ionoModel [0] BIT STRING  { klobuchar(0), neQuick(1) } (SIZE (1..8)),
   ...
}

GNSS-EarthOrientationParametersSupport ::= SEQUENCE {
   ...
}

GNSS-CommonAssistanceDataSupport ::= SEQUENCE {
   gnss-ReferenceTimeSupport [0] GNSS-ReferenceTimeSupport OPTIONAL,
   gnss-ReferenceLocationSupport [1] GNSS-ReferenceLocationSupport OPTIONAL,
   gnss-IonosphericModelSupport [2] GNSS-IonosphericModelSupport OPTIONAL,
   gnss-EarthOrientationParametersSupport [3] 
      GNSS-EarthOrientationParametersSupport OPTIONAL,
   ...
}

SBAS-ID ::= SEQUENCE {
   sbas-id [0] ENUMERATED { waas(0), egnos(1), msas(2), gagan(3), ... },
   ...
}

GNSS-TimeModelListSupport ::= SEQUENCE {
   ...
}

GNSS-DifferentialCorrectionsSupport ::= SEQUENCE {
   gnssSignalIDs [0] GNSS-SignalIDs,
   dgnss-ValidityTimeSup [1] BOOLEAN,
   ...
}

GNSS-NavigationModelSupport ::= SEQUENCE {
   clockModel [0] BIT STRING  { model-1(0), model-2(1), model-3(2), model-4(3)
      , model-5(4), model-6(5) } (SIZE (1..8)) OPTIONAL,
   orbitModel [1] BIT STRING  { model-1(0), model-2(1), model-3(2), model-4(3)
      , model-5(4), model-6(5) } (SIZE (1..8)) OPTIONAL,
   ...
}

GNSS-RealTimeIntegritySupport ::= SEQUENCE {
   ...
}

GNSS-DataBitAssistanceSupport ::= SEQUENCE {
   ...
}

GNSS-AcquisitionAssistanceSupport ::= SEQUENCE {
   ...,
   confidenceSupport-r10 [0] ENUMERATED { true(0) } OPTIONAL,
   dopplerUncertaintyExtSupport-r10 [1] ENUMERATED { true(0) } OPTIONAL
}

GNSS-AlmanacSupport ::= SEQUENCE {
   almanacModel [0] BIT STRING  { model-1(0), model-2(1), model-3(2), 
      model-4(3), model-5(4), model-6(5), model-7(6) } (SIZE (1..8)) OPTIONAL,
   ...
}

GNSS-UTC-ModelSupport ::= SEQUENCE {
   utc-Model [0] BIT STRING  { model-1(0), model-2(1), model-3(2), model-4(3), 
      model-5(4) } (SIZE (1..8)) OPTIONAL,
   ...
}

GNSS-AuxiliaryInformationSupport ::= SEQUENCE {
   ...
}

BDS-DifferentialCorrectionsSupport-r12 ::= SEQUENCE {
   gnssSignalIDs [0] GNSS-SignalIDs,
   ...
}

BDS-GridModelSupport-r12 ::= SEQUENCE {
   ...
}

GNSS-GenericAssistDataSupportElement ::= SEQUENCE {
   gnss-ID [0] GNSS-ID,
   sbas-ID [1] SBAS-ID OPTIONAL,
   gnss-TimeModelsSupport [2] GNSS-TimeModelListSupport OPTIONAL,
   gnss-DifferentialCorrectionsSupport [3] GNSS-DifferentialCorrectionsSupport
       OPTIONAL,
   gnss-NavigationModelSupport [4] GNSS-NavigationModelSupport OPTIONAL,
   gnss-RealTimeIntegritySupport [5] GNSS-RealTimeIntegritySupport OPTIONAL,
   gnss-DataBitAssistanceSupport [6] GNSS-DataBitAssistanceSupport OPTIONAL,
   gnss-AcquisitionAssistanceSupport [7] GNSS-AcquisitionAssistanceSupport
       OPTIONAL,
   gnss-AlmanacSupport [8] GNSS-AlmanacSupport OPTIONAL,
   gnss-UTC-ModelSupport [9] GNSS-UTC-ModelSupport OPTIONAL,
   gnss-AuxiliaryInformationSupport [10] GNSS-AuxiliaryInformationSupport
       OPTIONAL,
   ...,
   [[ 2:
      bds-DifferentialCorrectionsSupport-r12 [11] 
         BDS-DifferentialCorrectionsSupport-r12 OPTIONAL,
      bds-GridModelSupport-r12 [12] BDS-GridModelSupport-r12 OPTIONAL
   ]]
}

GNSS-GenericAssistanceDataSupport ::= SEQUENCE (SIZE (1..16)) OF 
   GNSS-GenericAssistDataSupportElement

AssistanceDataSupportList ::= SEQUENCE {
   gnss-CommonAssistanceDataSupport [0] GNSS-CommonAssistanceDataSupport,
   gnss-GenericAssistanceDataSupport [1] GNSS-GenericAssistanceDataSupport,
   ...
}

LocationCoordinateTypes ::= SEQUENCE {
   ellipsoidPoint [0] BOOLEAN,
   ellipsoidPointWithUncertaintyCircle [1] BOOLEAN,
   ellipsoidPointWithUncertaintyEllipse [2] BOOLEAN,
   polygon [3] BOOLEAN,
   ellipsoidPointWithAltitude [4] BOOLEAN,
   ellipsoidPointWithAltitudeAndUncertaintyEllipsoid [5] BOOLEAN,
   ellipsoidArc [6] BOOLEAN,
   ...
}

VelocityTypes ::= SEQUENCE {
   horizontalVelocity [0] BOOLEAN,
   horizontalWithVerticalVelocity [1] BOOLEAN,
   horizontalVelocityWithUncertainty [2] BOOLEAN,
   horizontalWithVerticalVelocityAndUncertainty [3] BOOLEAN,
   ...
}

A-GNSS-ProvideCapabilities ::= SEQUENCE {
   gnss-SupportList [0] GNSS-SupportList OPTIONAL,
   assistanceDataSupportList [1] AssistanceDataSupportList OPTIONAL,
   locationCoordinateTypes [2] LocationCoordinateTypes OPTIONAL,
   velocityTypes [3] VelocityTypes OPTIONAL,
   ...
}

SupportedBandEUTRA ::= SEQUENCE {
   bandEUTRA [0] INTEGER (1..maxFBI)
}

SupportedBandEUTRA-v9a0 ::= SEQUENCE {
   bandEUTRA-v9a0 [0] INTEGER (maxFBI-Plus1..maxFBI2) OPTIONAL
}

OTDOA-ProvideCapabilities ::= SEQUENCE {
   otdoa-Mode [0] BIT STRING  { ue-assisted(0) } (SIZE (1..8)),
   ...,
   supportedBandListEUTRA [1] SEQUENCE (SIZE (1..maxBands)) OF SupportedBandEUTRA
       OPTIONAL,
   supportedBandListEUTRA-v9a0 [2] SEQUENCE (SIZE (1..maxBands)) OF 
      SupportedBandEUTRA-v9a0 OPTIONAL,
   interFreqRSTDmeasurement-r10 [3] ENUMERATED { supported(0) } OPTIONAL,
   additionalNeighbourCellInfoList-r10 [4] ENUMERATED { supported(0) } OPTIONAL
}

ECID-ProvideCapabilities ::= SEQUENCE {
   ecid-MeasSupported [0] BIT STRING  { rsrpSup(0), rsrqSup(1), ueRxTxSup(2) }
       (SIZE (1..8)),
   ...,
   [[ 2:
      ueRxTxSupTDD-r13 [1] ENUMERATED { true(0) } OPTIONAL
   ]]
}

Sensor-ProvideCapabilities-r13 ::= SEQUENCE {
   sensor-Modes-r13 [0] BIT STRING  { standalone(0), ue-assisted(1) } (SIZE (1..8
      )),
   ...
}

TBS-ProvideCapabilities-r13 ::= SEQUENCE {
   tbs-Modes-r13 [0] BIT STRING  { standalone(0), ue-assisted(1) } (SIZE (1..8))
      ,
   ...
}

WLAN-ProvideCapabilities-r13 ::= SEQUENCE {
   wlan-Modes-r13 [0] BIT STRING  { standalone(0), ue-assisted(1) } (SIZE (1..8))
      ,
   wlan-MeasSupported-r13 [1] BIT STRING  { rssi-r13(0), rtt-r13(1) } (SIZE (1..8
      )),
   ...
}

BT-ProvideCapabilities-r13 ::= SEQUENCE {
   bt-Modes-r13 [0] BIT STRING  { standalone(0), ue-assisted(1) } (SIZE (1..8)),
   bt-MeasSupported-r13 [1] BIT STRING  { rssi-r13(0) } (SIZE (1..8)),
   ...
}

ProvideCapabilities-r9-IEs ::= SEQUENCE {
   commonIEsProvideCapabilities [0] CommonIEsProvideCapabilities OPTIONAL,
   a-gnss-ProvideCapabilities [1] A-GNSS-ProvideCapabilities OPTIONAL,
   otdoa-ProvideCapabilities [2] OTDOA-ProvideCapabilities OPTIONAL,
   ecid-ProvideCapabilities [3] ECID-ProvideCapabilities OPTIONAL,
   epdu-ProvideCapabilities [4] EPDU-Sequence OPTIONAL,
   ...,
   [[ 2:
      sensor-ProvideCapabilities-r13 [5] Sensor-ProvideCapabilities-r13
          OPTIONAL,
      tbs-ProvideCapabilities-r13 [6] TBS-ProvideCapabilities-r13 OPTIONAL,
      wlan-ProvideCapabilities-r13 [7] WLAN-ProvideCapabilities-r13 OPTIONAL,
      bt-ProvideCapabilities-r13 [8] BT-ProvideCapabilities-r13 OPTIONAL
   ]]
}

ProvideCapabilities ::= SEQUENCE {
   criticalExtensions [0] CHOICE {
      c1 [0] CHOICE {
         provideCapabilities-r9 [0] ProvideCapabilities-r9-IEs,
         spare3 [1] NULL,
         spare2 [2] NULL,
         spare1 [3] NULL
      },
      criticalExtensionsFuture [1] SEQUENCE {

      }
   }
}

ECGI ::= SEQUENCE {
   mcc [0] SEQUENCE (SIZE (3)) OF INTEGER (0..9),
   mnc [1] SEQUENCE (SIZE (2..3)) OF INTEGER (0..9),
   cellidentity [2] BIT STRING  (SIZE (28))
}

CommonIEsRequestAssistanceData ::= SEQUENCE {
   primaryCellID [0] ECGI OPTIONAL,
   ...
}

GNSS-ReferenceTimeReq ::= SEQUENCE {
   gnss-TimeReqPrefList [0] SEQUENCE (SIZE (1..8)) OF GNSS-ID,
   gps-TOW-assistReq [1] BOOLEAN OPTIONAL,
   notOfLeapSecReq [2] BOOLEAN OPTIONAL,
   ...
}

GNSS-ReferenceLocationReq ::= SEQUENCE {
   ...
}

GNSS-IonosphericModelReq ::= SEQUENCE {
   klobucharModelReq [0] BIT STRING  (SIZE (2)) OPTIONAL,
   neQuickModelReq [1] NULL OPTIONAL,
   ...
}

GNSS-EarthOrientationParametersReq ::= SEQUENCE {
   ...
}

GNSS-CommonAssistDataReq ::= SEQUENCE {
   gnss-ReferenceTimeReq [0] GNSS-ReferenceTimeReq OPTIONAL,
   gnss-ReferenceLocationReq [1] GNSS-ReferenceLocationReq OPTIONAL,
   gnss-IonosphericModelReq [2] GNSS-IonosphericModelReq OPTIONAL,
   gnss-EarthOrientationParametersReq [3] GNSS-EarthOrientationParametersReq
       OPTIONAL,
   ...
}

GNSS-TimeModelElementReq ::= SEQUENCE {
   gnss-TO-IDsReq [0] INTEGER (1..15),
   deltaTreq [1] BOOLEAN,
   ...
}

GNSS-TimeModelListReq ::= SEQUENCE (SIZE (1..15)) OF GNSS-TimeModelElementReq

GNSS-DifferentialCorrectionsReq ::= SEQUENCE {
   dgnss-SignalsReq [0] GNSS-SignalIDs,
   dgnss-ValidityTimeReq [1] BOOLEAN,
   ...
}

SV-ID ::= SEQUENCE {
   satellite-id [0] INTEGER (0..63),
   ...
}

SatListRelatedDataElement ::= SEQUENCE {
   svID [0] SV-ID,
   iod [1] BIT STRING  (SIZE (11)),
   clockModelID [2] INTEGER (1..8) OPTIONAL,
   orbitModelID [3] INTEGER (1..8) OPTIONAL,
   ...
}

SatListRelatedDataList ::= SEQUENCE (SIZE (1..64)) OF SatListRelatedDataElement

StoredNavListInfo ::= SEQUENCE {
   gnss-WeekOrDay [0] INTEGER (0..4095),
   gnss-Toe [1] INTEGER (0..255),
   t-toeLimit [2] INTEGER (0..15),
   satListRelatedDataList [3] SatListRelatedDataList OPTIONAL,
   ...
}

ReqNavListInfo ::= SEQUENCE {
   svReqList [0] BIT STRING  (SIZE (64)),
   clockModelID-PrefList [1] SEQUENCE (SIZE (1..8)) OF INTEGER (1..8) OPTIONAL,
   orbitModelID-PrefList [2] SEQUENCE (SIZE (1..8)) OF INTEGER (1..8) OPTIONAL,
   addNavparamReq [3] BOOLEAN OPTIONAL,
   ...
}

GNSS-NavigationModelReq ::= CHOICE {
   storedNavList [0] StoredNavListInfo,
   reqNavList [1] ReqNavListInfo,
   ...
}

GNSS-RealTimeIntegrityReq ::= SEQUENCE {
   ...
}

GNSS-DataBitsReqSatElement ::= SEQUENCE {
   svID [0] SV-ID,
   ...
}

GNSS-DataBitsReqSatList ::= SEQUENCE (SIZE (1..64)) OF GNSS-DataBitsReqSatElement

GNSS-DataBitAssistanceReq ::= SEQUENCE {
   gnss-TOD-Req [0] INTEGER (0..3599),
   gnss-TOD-FracReq [1] INTEGER (0..999) OPTIONAL,
   dataBitInterval [2] INTEGER (0..15),
   gnss-SignalType [3] GNSS-SignalIDs,
   gnss-DataBitsReq [4] GNSS-DataBitsReqSatList OPTIONAL,
   ...
}

GNSS-SignalID ::= SEQUENCE {
   gnss-SignalID [0] INTEGER (0..7),
   ...
}

GNSS-AcquisitionAssistanceReq ::= SEQUENCE {
   gnss-SignalID-Req [0] GNSS-SignalID,
   ...
}

GNSS-AlmanacReq ::= SEQUENCE {
   modelID [0] INTEGER (1..8) OPTIONAL,
   ...
}

GNSS-UTC-ModelReq ::= SEQUENCE {
   modelID [0] INTEGER (1..8) OPTIONAL,
   ...
}

GNSS-AuxiliaryInformationReq ::= SEQUENCE {
   ...
}

BDS-DifferentialCorrectionsReq-r12 ::= SEQUENCE {
   dgnss-SignalsReq [0] GNSS-SignalIDs,
   ...
}

BDS-GridModelReq-r12 ::= SEQUENCE {
   ...
}

GNSS-GenericAssistDataReqElement ::= SEQUENCE {
   gnss-ID [0] GNSS-ID,
   sbas-ID [1] SBAS-ID OPTIONAL,
   gnss-TimeModelsReq [2] GNSS-TimeModelListReq OPTIONAL,
   gnss-DifferentialCorrectionsReq [3] GNSS-DifferentialCorrectionsReq OPTIONAL
      ,
   gnss-NavigationModelReq [4] GNSS-NavigationModelReq OPTIONAL,
   gnss-RealTimeIntegrityReq [5] GNSS-RealTimeIntegrityReq OPTIONAL,
   gnss-DataBitAssistanceReq [6] GNSS-DataBitAssistanceReq OPTIONAL,
   gnss-AcquisitionAssistanceReq [7] GNSS-AcquisitionAssistanceReq OPTIONAL,
   gnss-AlmanacReq [8] GNSS-AlmanacReq OPTIONAL,
   gnss-UTCModelReq [9] GNSS-UTC-ModelReq OPTIONAL,
   gnss-AuxiliaryInformationReq [10] GNSS-AuxiliaryInformationReq OPTIONAL,
   ...,
   [[ 2:
      bds-DifferentialCorrectionsReq-r12 [11] 
         BDS-DifferentialCorrectionsReq-r12 OPTIONAL,
      bds-GridModelReq-r12 [12] BDS-GridModelReq-r12 OPTIONAL
   ]]
}

GNSS-GenericAssistDataReq ::= SEQUENCE (SIZE (1..16)) OF 
   GNSS-GenericAssistDataReqElement

A-GNSS-RequestAssistanceData ::= SEQUENCE {
   gnss-CommonAssistDataReq [0] GNSS-CommonAssistDataReq OPTIONAL,
   gnss-GenericAssistDataReq [1] GNSS-GenericAssistDataReq OPTIONAL,
   ...
}

OTDOA-RequestAssistanceData ::= SEQUENCE {
   physCellId [0] INTEGER (0..503),
   ...
}

RequestAssistanceData-r9-IEs ::= SEQUENCE {
   commonIEsRequestAssistanceData [0] CommonIEsRequestAssistanceData OPTIONAL,
   a-gnss-RequestAssistanceData [1] A-GNSS-RequestAssistanceData OPTIONAL,
   otdoa-RequestAssistanceData [2] OTDOA-RequestAssistanceData OPTIONAL,
   epdu-RequestAssistanceData [3] EPDU-Sequence OPTIONAL,
   ...
}

RequestAssistanceData ::= SEQUENCE {
   criticalExtensions [0] CHOICE {
      c1 [0] CHOICE {
         requestAssistanceData-r9 [0] RequestAssistanceData-r9-IEs,
         spare3 [1] NULL,
         spare2 [2] NULL,
         spare1 [3] NULL
      },
      criticalExtensionsFuture [1] SEQUENCE {

      }
   }
}

CommonIEsProvideAssistanceData ::= SEQUENCE {
   ...
}

GPS-TOW-AssistElement ::= SEQUENCE {
   satelliteID [0] INTEGER (1..64),
   tlmWord [1] INTEGER (0..16383),
   antiSpoof [2] INTEGER (0..1),
   alert [3] INTEGER (0..1),
   tlmRsvdBits [4] INTEGER (0..3),
   ...
}

GPS-TOW-Assist ::= SEQUENCE (SIZE (1..64)) OF GPS-TOW-AssistElement

GNSS-SystemTime ::= SEQUENCE {
   gnss-TimeID [0] GNSS-ID,
   gnss-DayNumber [1] INTEGER (0..32767),
   gnss-TimeOfDay [2] INTEGER (0..86399),
   gnss-TimeOfDayFrac-msec [3] INTEGER (0..999) OPTIONAL,
   notificationOfLeapSecond [4] BIT STRING  (SIZE (2)) OPTIONAL,
   gps-TOW-Assist [5] GPS-TOW-Assist OPTIONAL,
   ...
}

CellGlobalIdEUTRA-AndUTRA ::= SEQUENCE {
   plmn-Identity [0] SEQUENCE {
      mcc [0] SEQUENCE (SIZE (3)) OF INTEGER (0..9),
      mnc [1] SEQUENCE (SIZE (2..3)) OF INTEGER (0..9)
   },
   cellIdentity [1] CHOICE {
      eutra [0] BIT STRING  (SIZE (28)),
      utra [1] BIT STRING  (SIZE (32))
   },
   ...
}

CellGlobalIdGERAN ::= SEQUENCE {
   plmn-Identity [0] SEQUENCE {
      mcc [0] SEQUENCE (SIZE (3)) OF INTEGER (0..9),
      mnc [1] SEQUENCE (SIZE (2..3)) OF INTEGER (0..9)
   },
   locationAreaCode [1] BIT STRING  (SIZE (16)),
   cellIdentity [2] BIT STRING  (SIZE (16)),
   ...
}

NetworkTime ::= SEQUENCE {
   secondsFromFrameStructureStart [0] INTEGER (0..12533),
   fractionalSecondsFromFrameStructureStart [1] INTEGER (0..3999999),
   frameDrift [2] INTEGER (-64..63) OPTIONAL,
   cellID [3] CHOICE {
      eUTRA [0] SEQUENCE {
         physCellId [0] INTEGER (0..503),
         cellGlobalIdEUTRA [1] CellGlobalIdEUTRA-AndUTRA OPTIONAL,
         earfcn [2] ARFCN-ValueEUTRA,
         ...,
         [[ 2:
            earfcn-v9a0 [3] ARFCN-ValueEUTRA-v9a0 OPTIONAL
         ]]
      },
      uTRA [1] SEQUENCE {
         mode [0] CHOICE {
            fdd [0] SEQUENCE {
               primary-CPICH-Info [0] INTEGER (0..511),
               ...
            },
            tdd [1] SEQUENCE {
               cellParameters [0] INTEGER (0..127),
               ...
            }
         },
         cellGlobalIdUTRA [1] CellGlobalIdEUTRA-AndUTRA OPTIONAL,
         uarfcn [2] ARFCN-ValueUTRA,
         ...
      },
      gSM [2] SEQUENCE {
         bcchCarrier [0] INTEGER (0..1023),
         bsic [1] INTEGER (0..63),
         cellGlobalIdGERAN [2] CellGlobalIdGERAN OPTIONAL,
         ...
      },
      ...
   },
   ...
}

GNSS-ReferenceTimeForOneCell ::= SEQUENCE {
   networkTime [0] NetworkTime,
   referenceTimeUnc [1] INTEGER (0..127),
   bsAlign [2] ENUMERATED { true(0) } OPTIONAL,
   ...
}

GNSS-ReferenceTime ::= SEQUENCE {
   gnss-SystemTime [0] GNSS-SystemTime,
   referenceTimeUnc [1] INTEGER (0..127) OPTIONAL,
   gnss-ReferenceTimeForCells [2] SEQUENCE (SIZE (1..16)) OF 
      GNSS-ReferenceTimeForOneCell OPTIONAL,
   ...
}

EllipsoidPointWithAltitudeAndUncertaintyEllipsoid ::= SEQUENCE {
   latitudeSign [0] ENUMERATED { north(0), south(1) },
   degreesLatitude [1] INTEGER (0..8388607),
   degreesLongitude [2] INTEGER (-8388608..8388607),
   altitudeDirection [3] ENUMERATED { height(0), depth(1) },
   altitude [4] INTEGER (0..32767),
   uncertaintySemiMajor [5] INTEGER (0..127),
   uncertaintySemiMinor [6] INTEGER (0..127),
   orientationMajorAxis [7] INTEGER (0..179),
   uncertaintyAltitude [8] INTEGER (0..127),
   confidence [9] INTEGER (0..100)
}

GNSS-ReferenceLocation ::= SEQUENCE {
   threeDlocation [0] EllipsoidPointWithAltitudeAndUncertaintyEllipsoid,
   ...
}

KlobucharModelParameter ::= SEQUENCE {
   dataID [0] BIT STRING  (SIZE (2)),
   alfa0 [1] INTEGER (-128..127),
   alfa1 [2] INTEGER (-128..127),
   alfa2 [3] INTEGER (-128..127),
   alfa3 [4] INTEGER (-128..127),
   beta0 [5] INTEGER (-128..127),
   beta1 [6] INTEGER (-128..127),
   beta2 [7] INTEGER (-128..127),
   beta3 [8] INTEGER (-128..127),
   ...
}

NeQuickModelParameter ::= SEQUENCE {
   ai0 [0] INTEGER (0..2047),
   ai1 [1] INTEGER (-1024..1023),
   ai2 [2] INTEGER (-8192..8191),
   ionoStormFlag1 [3] INTEGER (0..1) OPTIONAL,
   ionoStormFlag2 [4] INTEGER (0..1) OPTIONAL,
   ionoStormFlag3 [5] INTEGER (0..1) OPTIONAL,
   ionoStormFlag4 [6] INTEGER (0..1) OPTIONAL,
   ionoStormFlag5 [7] INTEGER (0..1) OPTIONAL,
   ...
}

GNSS-IonosphericModel ::= SEQUENCE {
   klobucharModel [0] KlobucharModelParameter OPTIONAL,
   neQuickModel [1] NeQuickModelParameter OPTIONAL,
   ...
}

GNSS-EarthOrientationParameters ::= SEQUENCE {
   teop [0] INTEGER (0..65535),
   pmX [1] INTEGER (-1048576..1048575),
   pmXdot [2] INTEGER (-16384..16383),
   pmY [3] INTEGER (-1048576..1048575),
   pmYdot [4] INTEGER (-16384..16383),
   deltaUT1 [5] INTEGER (-1073741824..1073741823),
   deltaUT1dot [6] INTEGER (-262144..262143),
   ...
}

GNSS-CommonAssistData ::= SEQUENCE {
   gnss-ReferenceTime [0] GNSS-ReferenceTime OPTIONAL,
   gnss-ReferenceLocation [1] GNSS-ReferenceLocation OPTIONAL,
   gnss-IonosphericModel [2] GNSS-IonosphericModel OPTIONAL,
   gnss-EarthOrientationParameters [3] GNSS-EarthOrientationParameters OPTIONAL
      ,
   ...
}

GNSS-TimeModelElement ::= SEQUENCE {
   gnss-TimeModelRefTime [0] INTEGER (0..65535),
   tA0 [1] INTEGER (-67108864..67108863),
   tA1 [2] INTEGER (-4096..4095) OPTIONAL,
   tA2 [3] INTEGER (-64..63) OPTIONAL,
   gnss-TO-ID [4] INTEGER (1..15),
   weekNumber [5] INTEGER (0..8191) OPTIONAL,
   deltaT [6] INTEGER (-128..127) OPTIONAL,
   ...
}

GNSS-TimeModelList ::= SEQUENCE (SIZE (1..15)) OF GNSS-TimeModelElement

DGNSS-CorrectionsElement ::= SEQUENCE {
   svID [0] SV-ID,
   iod [1] BIT STRING  (SIZE (11)),
   udre [2] INTEGER (0..3),
   pseudoRangeCor [3] INTEGER (-2047..2047),
   rangeRateCor [4] INTEGER (-127..127),
   udreGrowthRate [5] INTEGER (0..7) OPTIONAL,
   udreValidityTime [6] INTEGER (0..7) OPTIONAL,
   ...
}

DGNSS-SatList ::= SEQUENCE (SIZE (1..64)) OF DGNSS-CorrectionsElement

DGNSS-SgnTypeElement ::= SEQUENCE {
   gnss-SignalID [0] GNSS-SignalID,
   gnss-StatusHealth [1] INTEGER (0..7),
   dgnss-SatList [2] DGNSS-SatList,
   ...
}

DGNSS-SgnTypeList ::= SEQUENCE (SIZE (1..3)) OF DGNSS-SgnTypeElement

GNSS-DifferentialCorrections ::= SEQUENCE {
   dgnss-RefTime [0] INTEGER (0..3599),
   dgnss-SgnTypeList [1] DGNSS-SgnTypeList,
   ...
}

StandardClockModelElement ::= SEQUENCE {
   stanClockToc [0] INTEGER (0..16383),
   stanClockAF2 [1] INTEGER (-32..31),
   stanClockAF1 [2] INTEGER (-1048576..1048575),
   stanClockAF0 [3] INTEGER (-1073741824..1073741823),
   stanClockTgd [4] INTEGER (-512..511) OPTIONAL,
   sisa [5] INTEGER (0..255),
   stanModelID [6] INTEGER (0..1) OPTIONAL,
   ...
}

StandardClockModelList ::= SEQUENCE (SIZE (1..2)) OF StandardClockModelElement

NAV-ClockModel ::= SEQUENCE {
   navToc [0] INTEGER (0..37799),
   navaf2 [1] INTEGER (-128..127),
   navaf1 [2] INTEGER (-32768..32767),
   navaf0 [3] INTEGER (-2097152..2097151),
   navTgd [4] INTEGER (-128..127),
   ...
}

CNAV-ClockModel ::= SEQUENCE {
   cnavToc [0] INTEGER (0..2015),
   cnavTop [1] INTEGER (0..2015),
   cnavURA0 [2] INTEGER (-16..15),
   cnavURA1 [3] INTEGER (0..7),
   cnavURA2 [4] INTEGER (0..7),
   cnavAf2 [5] INTEGER (-512..511),
   cnavAf1 [6] INTEGER (-524288..524287),
   cnavAf0 [7] INTEGER (-33554432..33554431),
   cnavTgd [8] INTEGER (-4096..4095),
   cnavISCl1cp [9] INTEGER (-4096..4095) OPTIONAL,
   cnavISCl1cd [10] INTEGER (-4096..4095) OPTIONAL,
   cnavISCl1ca [11] INTEGER (-4096..4095) OPTIONAL,
   cnavISCl2c [12] INTEGER (-4096..4095) OPTIONAL,
   cnavISCl5i5 [13] INTEGER (-4096..4095) OPTIONAL,
   cnavISCl5q5 [14] INTEGER (-4096..4095) OPTIONAL,
   ...
}

GLONASS-ClockModel ::= SEQUENCE {
   gloTau [0] INTEGER (-2097152..2097151),
   gloGamma [1] INTEGER (-1024..1023),
   gloDeltaTau [2] INTEGER (-16..15) OPTIONAL,
   ...
}

SBAS-ClockModel ::= SEQUENCE {
   sbasTo [0] INTEGER (0..5399),
   sbasAgfo [1] INTEGER (-2048..2047),
   sbasAgf1 [2] INTEGER (-128..127),
   ...
}

BDS-ClockModel-r12 ::= SEQUENCE {
   bdsAODC-r12 [0] INTEGER (0..31),
   bdsToc-r12 [1] INTEGER (0..131071),
   bdsA0-r12 [2] INTEGER (-8388608..8388607),
   bdsA1-r12 [3] INTEGER (-2097152..2097151),
   bdsA2-r12 [4] INTEGER (-1024..1023),
   bdsTgd1-r12 [5] INTEGER (-512..511),
   ...
}

GNSS-ClockModel ::= CHOICE {
   standardClockModelList [0] StandardClockModelList,
   nav-ClockModel [1] NAV-ClockModel,
   cnav-ClockModel [2] CNAV-ClockModel,
   glonass-ClockModel [3] GLONASS-ClockModel,
   sbas-ClockModel [4] SBAS-ClockModel,
   ...,
   bds-ClockModel-r12 [5] BDS-ClockModel-r12
}

NavModelKeplerianSet ::= SEQUENCE {
   keplerToe [0] INTEGER (0..16383),
   keplerW [1] INTEGER (-2147483648..2147483647),
   keplerDeltaN [2] INTEGER (-32768..32767),
   keplerM0 [3] INTEGER (-2147483648..2147483647),
   keplerOmegaDot [4] INTEGER (-8388608..8388607),
   keplerE [5] INTEGER (0..4294967295),
   keplerIDot [6] INTEGER (-8192..8191),
   keplerAPowerHalf [7] INTEGER (0..4294967295),
   keplerI0 [8] INTEGER (-2147483648..2147483647),
   keplerOmega0 [9] INTEGER (-2147483648..2147483647),
   keplerCrs [10] INTEGER (-32768..32767),
   keplerCis [11] INTEGER (-32768..32767),
   keplerCus [12] INTEGER (-32768..32767),
   keplerCrc [13] INTEGER (-32768..32767),
   keplerCic [14] INTEGER (-32768..32767),
   keplerCuc [15] INTEGER (-32768..32767),
   ...
}

NavModelNAV-KeplerianSet ::= SEQUENCE {
   navURA [0] INTEGER (0..15),
   navFitFlag [1] INTEGER (0..1),
   navToe [2] INTEGER (0..37799),
   navOmega [3] INTEGER (-2147483648..2147483647),
   navDeltaN [4] INTEGER (-32768..32767),
   navM0 [5] INTEGER (-2147483648..2147483647),
   navOmegaADot [6] INTEGER (-8388608..8388607),
   navE [7] INTEGER (0..4294967295),
   navIDot [8] INTEGER (-8192..8191),
   navAPowerHalf [9] INTEGER (0..4294967295),
   navI0 [10] INTEGER (-2147483648..2147483647),
   navOmegaA0 [11] INTEGER (-2147483648..2147483647),
   navCrs [12] INTEGER (-32768..32767),
   navCis [13] INTEGER (-32768..32767),
   navCus [14] INTEGER (-32768..32767),
   navCrc [15] INTEGER (-32768..32767),
   navCic [16] INTEGER (-32768..32767),
   navCuc [17] INTEGER (-32768..32767),
   addNAVparam [18] SEQUENCE {
      ephemCodeOnL2 [0] INTEGER (0..3),
      ephemL2Pflag [1] INTEGER (0..1),
      ephemSF1Rsvd [2] SEQUENCE {
         reserved1 [0] INTEGER (0..8388607),
         reserved2 [1] INTEGER (0..16777215),
         reserved3 [2] INTEGER (0..16777215),
         reserved4 [3] INTEGER (0..65535)
      },
      ephemAODA [3] INTEGER (0..31)
   } OPTIONAL,
   ...
}

NavModelCNAV-KeplerianSet ::= SEQUENCE {
   cnavTop [0] INTEGER (0..2015),
   cnavURAindex [1] INTEGER (-16..15),
   cnavDeltaA [2] INTEGER (-33554432..33554431),
   cnavAdot [3] INTEGER (-16777216..16777215),
   cnavDeltaNo [4] INTEGER (-65536..65535),
   cnavDeltaNoDot [5] INTEGER (-4194304..4194303),
   cnavMo [6] INTEGER (-4294967296..4294967295),
   cnavE [7] INTEGER (0..8589934591),
   cnavOmega [8] INTEGER (-4294967296..4294967295),
   cnavOMEGA0 [9] INTEGER (-4294967296..4294967295),
   cnavDeltaOmegaDot [10] INTEGER (-65536..65535),
   cnavIo [11] INTEGER (-4294967296..4294967295),
   cnavIoDot [12] INTEGER (-16384..16383),
   cnavCis [13] INTEGER (-32768..32767),
   cnavCic [14] INTEGER (-32768..32767),
   cnavCrs [15] INTEGER (-8388608..8388607),
   cnavCrc [16] INTEGER (-8388608..8388607),
   cnavCus [17] INTEGER (-1048576..1048575),
   cnavCuc [18] INTEGER (-1048576..1048575),
   ...
}

NavModel-GLONASS-ECEF ::= SEQUENCE {
   gloEn [0] INTEGER (0..31),
   gloP1 [1] BIT STRING  (SIZE (2)),
   gloP2 [2] BOOLEAN,
   gloM [3] INTEGER (0..3),
   gloX [4] INTEGER (-67108864..67108863),
   gloXdot [5] INTEGER (-8388608..8388607),
   gloXdotdot [6] INTEGER (-16..15),
   gloY [7] INTEGER (-67108864..67108863),
   gloYdot [8] INTEGER (-8388608..8388607),
   gloYdotdot [9] INTEGER (-16..15),
   gloZ [10] INTEGER (-67108864..67108863),
   gloZdot [11] INTEGER (-8388608..8388607),
   gloZdotdot [12] INTEGER (-16..15),
   ...
}

NavModel-SBAS-ECEF ::= SEQUENCE {
   sbasTo [0] INTEGER (0..5399) OPTIONAL,
   sbasAccuracy [1] BIT STRING  (SIZE (4)),
   sbasXg [2] INTEGER (-536870912..536870911),
   sbasYg [3] INTEGER (-536870912..536870911),
   sbasZg [4] INTEGER (-16777216..16777215),
   sbasXgDot [5] INTEGER (-65536..65535),
   sbasYgDot [6] INTEGER (-65536..65535),
   sbasZgDot [7] INTEGER (-131072..131071),
   sbasXgDotDot [8] INTEGER (-512..511),
   sbagYgDotDot [9] INTEGER (-512..511),
   sbasZgDotDot [10] INTEGER (-512..511),
   ...
}

NavModel-BDS-KeplerianSet-r12 ::= SEQUENCE {
   bdsAODE-r12 [0] INTEGER (0..31),
   bdsURAI-r12 [1] INTEGER (0..15),
   bdsToe-r12 [2] INTEGER (0..131071),
   bdsAPowerHalf-r12 [3] INTEGER (0..4294967295),
   bdsE-r12 [4] INTEGER (0..4294967295),
   bdsW-r12 [5] INTEGER (-2147483648..2147483647),
   bdsDeltaN-r12 [6] INTEGER (-32768..32767),
   bdsM0-r12 [7] INTEGER (-2147483648..2147483647),
   bdsOmega0-r12 [8] INTEGER (-2147483648..2147483647),
   bdsOmegaDot-r12 [9] INTEGER (-8388608..8388607),
   bdsI0-r12 [10] INTEGER (-2147483648..2147483647),
   bdsIDot-r12 [11] INTEGER (-8192..8191),
   bdsCuc-r12 [12] INTEGER (-131072..131071),
   bdsCus-r12 [13] INTEGER (-131072..131071),
   bdsCrc-r12 [14] INTEGER (-131072..131071),
   bdsCrs-r12 [15] INTEGER (-131072..131071),
   bdsCic-r12 [16] INTEGER (-131072..131071),
   bdsCis-r12 [17] INTEGER (-131072..131071),
   ...
}

GNSS-OrbitModel ::= CHOICE {
   keplerianSet [0] NavModelKeplerianSet,
   nav-KeplerianSet [1] NavModelNAV-KeplerianSet,
   cnav-KeplerianSet [2] NavModelCNAV-KeplerianSet,
   glonass-ECEF [3] NavModel-GLONASS-ECEF,
   sbas-ECEF [4] NavModel-SBAS-ECEF,
   ...,
   bds-KeplerianSet-r12 [5] NavModel-BDS-KeplerianSet-r12
}

GNSS-NavModelSatelliteElement ::= SEQUENCE {
   svID [0] SV-ID,
   svHealth [1] BIT STRING  (SIZE (8)),
   iod [2] BIT STRING  (SIZE (11)),
   gnss-ClockModel [3] GNSS-ClockModel,
   gnss-OrbitModel [4] GNSS-OrbitModel,
   ...,
   [[ 2:
      svHealthExt-v1240 [5] BIT STRING  (SIZE (4)) OPTIONAL
   ]]
}

GNSS-NavModelSatelliteList ::= SEQUENCE (SIZE (1..64)) OF 
   GNSS-NavModelSatelliteElement

GNSS-NavigationModel ::= SEQUENCE {
   nonBroadcastIndFlag [0] INTEGER (0..1),
   gnss-SatelliteList [1] GNSS-NavModelSatelliteList,
   ...
}

BadSignalElement ::= SEQUENCE {
   badSVID [0] SV-ID,
   badSignalID [1] GNSS-SignalIDs OPTIONAL,
   ...
}

GNSS-BadSignalList ::= SEQUENCE (SIZE (1..64)) OF BadSignalElement

GNSS-RealTimeIntegrity ::= SEQUENCE {
   gnss-BadSignalList [0] GNSS-BadSignalList,
   ...
}

GNSS-DataBitsSgnElement ::= SEQUENCE {
   gnss-SignalType [0] GNSS-SignalID,
   gnss-DataBits [1] BIT STRING  (SIZE (1..1024)),
   ...
}

GNSS-DataBitsSgnList ::= SEQUENCE (SIZE (1..8)) OF GNSS-DataBitsSgnElement

GNSS-DataBitsSatElement ::= SEQUENCE {
   svID [0] SV-ID,
   gnss-DataBitsSgnList [1] GNSS-DataBitsSgnList,
   ...
}

GNSS-DataBitsSatList ::= SEQUENCE (SIZE (1..64)) OF GNSS-DataBitsSatElement

GNSS-DataBitAssistance ::= SEQUENCE {
   gnss-TOD [0] INTEGER (0..3599),
   gnss-TODfrac [1] INTEGER (0..999) OPTIONAL,
   gnss-DataBitsSatList [2] GNSS-DataBitsSatList,
   ...
}

GNSS-AcquisitionAssistElement ::= SEQUENCE {
   svID [0] SV-ID,
   doppler0 [1] INTEGER (-2048..2047),
   doppler1 [2] INTEGER (0..63),
   dopplerUncertainty [3] INTEGER (0..4),
   codePhase [4] INTEGER (0..1022),
   intCodePhase [5] INTEGER (0..127),
   codePhaseSearchWindow [6] INTEGER (0..31),
   azimuth [7] INTEGER (0..511),
   elevation [8] INTEGER (0..127),
   ...,
   codePhase1023 [9] BOOLEAN OPTIONAL,
   dopplerUncertaintyExt-r10 [10] ENUMERATED { d60(0), d80(1), d100(2), d120(3)
      , noInformation(4), ... } OPTIONAL
}

GNSS-AcquisitionAssistList ::= SEQUENCE (SIZE (1..64)) OF 
   GNSS-AcquisitionAssistElement

GNSS-AcquisitionAssistance ::= SEQUENCE {
   gnss-SignalID [0] GNSS-SignalID,
   gnss-AcquisitionAssistList [1] GNSS-AcquisitionAssistList,
   ...,
   confidence-r10 [2] INTEGER (0..100) OPTIONAL
}

AlmanacKeplerianSet ::= SEQUENCE {
   svID [0] SV-ID,
   kepAlmanacE [1] INTEGER (0..2047),
   kepAlmanacDeltaI [2] INTEGER (-1024..1023),
   kepAlmanacOmegaDot [3] INTEGER (-1024..1023),
   kepSV-StatusINAV [4] BIT STRING  (SIZE (4)),
   kepSV-StatusFNAV [5] BIT STRING  (SIZE (2)) OPTIONAL,
   kepAlmanacAPowerHalf [6] INTEGER (-4096..4095),
   kepAlmanacOmega0 [7] INTEGER (-32768..32767),
   kepAlmanacW [8] INTEGER (-32768..32767),
   kepAlmanacM0 [9] INTEGER (-32768..32767),
   kepAlmanacAF0 [10] INTEGER (-32768..32767),
   kepAlmanacAF1 [11] INTEGER (-4096..4095),
   ...
}

AlmanacNAV-KeplerianSet ::= SEQUENCE {
   svID [0] SV-ID,
   navAlmE [1] INTEGER (0..65535),
   navAlmDeltaI [2] INTEGER (-32768..32767),
   navAlmOMEGADOT [3] INTEGER (-32768..32767),
   navAlmSVHealth [4] INTEGER (0..255),
   navAlmSqrtA [5] INTEGER (0..16777215),
   navAlmOMEGAo [6] INTEGER (-8388608..8388607),
   navAlmOmega [7] INTEGER (-8388608..8388607),
   navAlmMo [8] INTEGER (-8388608..8388607),
   navAlmaf0 [9] INTEGER (-1024..1023),
   navAlmaf1 [10] INTEGER (-1024..1023),
   ...
}

AlmanacReducedKeplerianSet ::= SEQUENCE {
   svID [0] SV-ID,
   redAlmDeltaA [1] INTEGER (-128..127),
   redAlmOmega0 [2] INTEGER (-64..63),
   redAlmPhi0 [3] INTEGER (-64..63),
   redAlmL1Health [4] BOOLEAN,
   redAlmL2Health [5] BOOLEAN,
   redAlmL5Health [6] BOOLEAN,
   ...
}

AlmanacMidiAlmanacSet ::= SEQUENCE {
   svID [0] SV-ID,
   midiAlmE [1] INTEGER (0..2047),
   midiAlmDeltaI [2] INTEGER (-1024..1023),
   midiAlmOmegaDot [3] INTEGER (-1024..1023),
   midiAlmSqrtA [4] INTEGER (0..131071),
   midiAlmOmega0 [5] INTEGER (-32768..32767),
   midiAlmOmega [6] INTEGER (-32768..32767),
   midiAlmMo [7] INTEGER (-32768..32767),
   midiAlmaf0 [8] INTEGER (-1024..1023),
   midiAlmaf1 [9] INTEGER (-512..511),
   midiAlmL1Health [10] BOOLEAN,
   midiAlmL2Health [11] BOOLEAN,
   midiAlmL5Health [12] BOOLEAN,
   ...
}

AlmanacGLONASS-AlmanacSet ::= SEQUENCE {
   gloAlm-NA [0] INTEGER (1..1461),
   gloAlmnA [1] INTEGER (1..24),
   gloAlmHA [2] INTEGER (0..31),
   gloAlmLambdaA [3] INTEGER (-1048576..1048575),
   gloAlmtlambdaA [4] INTEGER (0..2097151),
   gloAlmDeltaIa [5] INTEGER (-131072..131071),
   gloAlmDeltaTA [6] INTEGER (-2097152..2097151),
   gloAlmDeltaTdotA [7] INTEGER (-64..63),
   gloAlmEpsilonA [8] INTEGER (0..32767),
   gloAlmOmegaA [9] INTEGER (-32768..32767),
   gloAlmTauA [10] INTEGER (-512..511),
   gloAlmCA [11] INTEGER (0..1),
   gloAlmMA [12] BIT STRING  (SIZE (2)) OPTIONAL,
   ...
}

AlmanacECEF-SBAS-AlmanacSet ::= SEQUENCE {
   sbasAlmDataID [0] INTEGER (0..3),
   svID [1] SV-ID,
   sbasAlmHealth [2] BIT STRING  (SIZE (8)),
   sbasAlmXg [3] INTEGER (-16384..16383),
   sbasAlmYg [4] INTEGER (-16384..16383),
   sbasAlmZg [5] INTEGER (-256..255),
   sbasAlmXgdot [6] INTEGER (-4..3),
   sbasAlmYgDot [7] INTEGER (-4..3),
   sbasAlmZgDot [8] INTEGER (-8..7),
   sbasAlmTo [9] INTEGER (0..2047),
   ...
}

AlmanacBDS-AlmanacSet-r12 ::= SEQUENCE {
   svID [0] SV-ID,
   bdsAlmToa-r12 [1] INTEGER (0..255) OPTIONAL,
   bdsAlmSqrtA-r12 [2] INTEGER (0..16777215),
   bdsAlmE-r12 [3] INTEGER (0..131071),
   bdsAlmW-r12 [4] INTEGER (-8388608..8388607),
   bdsAlmM0-r12 [5] INTEGER (-8388608..8388607),
   bdsAlmOmega0-r12 [6] INTEGER (-8388608..8388607),
   bdsAlmOmegaDot-r12 [7] INTEGER (-65536..65535),
   bdsAlmDeltaI-r12 [8] INTEGER (-32768..32767),
   bdsAlmA0-r12 [9] INTEGER (-1024..1023),
   bdsAlmA1-r12 [10] INTEGER (-1024..1023),
   bdsSvHealth-r12 [11] BIT STRING  (SIZE (9)) OPTIONAL,
   ...
}

GNSS-AlmanacElement ::= CHOICE {
   keplerianAlmanacSet [0] AlmanacKeplerianSet,
   keplerianNAV-Almanac [1] AlmanacNAV-KeplerianSet,
   keplerianReducedAlmanac [2] AlmanacReducedKeplerianSet,
   keplerianMidiAlmanac [3] AlmanacMidiAlmanacSet,
   keplerianGLONASS [4] AlmanacGLONASS-AlmanacSet,
   ecef-SBAS-Almanac [5] AlmanacECEF-SBAS-AlmanacSet,
   ...,
   keplerianBDS-Almanac-r12 [6] AlmanacBDS-AlmanacSet-r12
}

GNSS-AlmanacList ::= SEQUENCE (SIZE (1..64)) OF GNSS-AlmanacElement

GNSS-Almanac ::= SEQUENCE {
   weekNumber [0] INTEGER (0..255) OPTIONAL,
   toa [1] INTEGER (0..255) OPTIONAL,
   ioda [2] INTEGER (0..3) OPTIONAL,
   completeAlmanacProvided [3] BOOLEAN,
   gnss-AlmanacList [4] GNSS-AlmanacList,
   ...,
   [[ 2:
      toa-ext-v1240 [5] INTEGER (256..1023) OPTIONAL,
      ioda-ext-v1240 [6] INTEGER (4..15) OPTIONAL
   ]]
}

UTC-ModelSet1 ::= SEQUENCE {
   gnss-Utc-A1 [0] INTEGER (-8388608..8388607),
   gnss-Utc-A0 [1] INTEGER (-2147483648..2147483647),
   gnss-Utc-Tot [2] INTEGER (0..255),
   gnss-Utc-WNt [3] INTEGER (0..255),
   gnss-Utc-DeltaTls [4] INTEGER (-128..127),
   gnss-Utc-WNlsf [5] INTEGER (0..255),
   gnss-Utc-DN [6] INTEGER (-128..127),
   gnss-Utc-DeltaTlsf [7] INTEGER (-128..127),
   ...
}

UTC-ModelSet2 ::= SEQUENCE {
   utcA0 [0] INTEGER (-32768..32767),
   utcA1 [1] INTEGER (-4096..4095),
   utcA2 [2] INTEGER (-64..63),
   utcDeltaTls [3] INTEGER (-128..127),
   utcTot [4] INTEGER (0..65535),
   utcWNot [5] INTEGER (0..8191),
   utcWNlsf [6] INTEGER (0..255),
   utcDN [7] BIT STRING  (SIZE (4)),
   utcDeltaTlsf [8] INTEGER (-128..127),
   ...
}

UTC-ModelSet3 ::= SEQUENCE {
   nA [0] INTEGER (1..1461),
   tauC [1] INTEGER (-2147483648..2147483647),
   b1 [2] INTEGER (-1024..1023) OPTIONAL,
   b2 [3] INTEGER (-512..511) OPTIONAL,
   kp [4] BIT STRING  (SIZE (2)) OPTIONAL,
   ...
}

UTC-ModelSet4 ::= SEQUENCE {
   utcA1wnt [0] INTEGER (-8388608..8388607),
   utcA0wnt [1] INTEGER (-2147483648..2147483647),
   utcTot [2] INTEGER (0..255),
   utcWNt [3] INTEGER (0..255),
   utcDeltaTls [4] INTEGER (-128..127),
   utcWNlsf [5] INTEGER (0..255),
   utcDN [6] INTEGER (-128..127),
   utcDeltaTlsf [7] INTEGER (-128..127),
   utcStandardID [8] INTEGER (0..7),
   ...
}

UTC-ModelSet5-r12 ::= SEQUENCE {
   utcA0-r12 [0] INTEGER (-2147483648..2147483647),
   utcA1-r12 [1] INTEGER (-8388608..8388607),
   utcDeltaTls-r12 [2] INTEGER (-128..127),
   utcWNlsf-r12 [3] INTEGER (0..255),
   utcDN-r12 [4] INTEGER (0..255),
   utcDeltaTlsf-r12 [5] INTEGER (-128..127),
   ...
}

GNSS-UTC-Model ::= CHOICE {
   utcModel1 [0] UTC-ModelSet1,
   utcModel2 [1] UTC-ModelSet2,
   utcModel3 [2] UTC-ModelSet3,
   utcModel4 [3] UTC-ModelSet4,
   ...,
   utcModel5-r12 [4] UTC-ModelSet5-r12
}

GNSS-ID-GPS-SatElement ::= SEQUENCE {
   svID [0] SV-ID,
   signalsAvailable [1] GNSS-SignalIDs,
   ...
}

GNSS-ID-GPS ::= SEQUENCE (SIZE (1..64)) OF GNSS-ID-GPS-SatElement

GNSS-ID-GLONASS-SatElement ::= SEQUENCE {
   svID [0] SV-ID,
   signalsAvailable [1] GNSS-SignalIDs,
   channelNumber [2] INTEGER (-7..13) OPTIONAL,
   ...
}

GNSS-ID-GLONASS ::= SEQUENCE (SIZE (1..64)) OF GNSS-ID-GLONASS-SatElement

GNSS-AuxiliaryInformation ::= CHOICE {
   gnss-ID-GPS [0] GNSS-ID-GPS,
   gnss-ID-GLONASS [1] GNSS-ID-GLONASS,
   ...
}

DBDS-CorrectionElement-r12 ::= SEQUENCE {
   svID [0] SV-ID,
   bds-UDREI-r12 [1] INTEGER (0..15),
   bds-RURAI-r12 [2] INTEGER (0..15),
   bds-ECC-DeltaT-r12 [3] INTEGER (-4096..4095),
   ...
}

DBDS-CorrectionList-r12 ::= SEQUENCE (SIZE (1..64)) OF DBDS-CorrectionElement-r12

BDS-SgnTypeElement-r12 ::= SEQUENCE {
   gnss-SignalID [0] GNSS-SignalID OPTIONAL,
   dbds-CorrectionList-r12 [1] DBDS-CorrectionList-r12,
   ...
}

BDS-SgnTypeList-r12 ::= SEQUENCE (SIZE (1..3)) OF BDS-SgnTypeElement-r12

BDS-DifferentialCorrections-r12 ::= SEQUENCE {
   dbds-RefTime-r12 [0] INTEGER (0..3599),
   bds-SgnTypeList-r12 [1] BDS-SgnTypeList-r12,
   ...
}

GridIonElement-r12 ::= SEQUENCE {
   igp-ID-r12 [0] INTEGER (1..320),
   dt-r12 [1] INTEGER (0..511),
   givei-r12 [2] INTEGER (0..15),
   ...
}

GridIonList-r12 ::= SEQUENCE (SIZE (1..320)) OF GridIonElement-r12

BDS-GridModelParameter-r12 ::= SEQUENCE {
   bds-RefTime-r12 [0] INTEGER (0..3599),
   gridIonList-r12 [1] GridIonList-r12,
   ...
}

GNSS-GenericAssistDataElement ::= SEQUENCE {
   gnss-ID [0] GNSS-ID,
   sbas-ID [1] SBAS-ID OPTIONAL,
   gnss-TimeModels [2] GNSS-TimeModelList OPTIONAL,
   gnss-DifferentialCorrections [3] GNSS-DifferentialCorrections OPTIONAL,
   gnss-NavigationModel [4] GNSS-NavigationModel OPTIONAL,
   gnss-RealTimeIntegrity [5] GNSS-RealTimeIntegrity OPTIONAL,
   gnss-DataBitAssistance [6] GNSS-DataBitAssistance OPTIONAL,
   gnss-AcquisitionAssistance [7] GNSS-AcquisitionAssistance OPTIONAL,
   gnss-Almanac [8] GNSS-Almanac OPTIONAL,
   gnss-UTC-Model [9] GNSS-UTC-Model OPTIONAL,
   gnss-AuxiliaryInformation [10] GNSS-AuxiliaryInformation OPTIONAL,
   ...,
   [[ 2:
      bds-DifferentialCorrections-r12 [11] BDS-DifferentialCorrections-r12
          OPTIONAL,
      bds-GridModel-r12 [12] BDS-GridModelParameter-r12 OPTIONAL
   ]]
}

GNSS-GenericAssistData ::= SEQUENCE (SIZE (1..16)) OF 
   GNSS-GenericAssistDataElement

GNSS-LocationServerErrorCauses ::= SEQUENCE {
   cause [0] ENUMERATED { undefined(0), 
      undeliveredAssistanceDataIsNotSupportedByServer(1), 
      undeliveredAssistanceDataIsSupportedButCurrentlyNotAvailableByServer(2), 
      undeliveredAssistanceDataIsPartlyNotSupportedAndPartlyNotAvailableByServer(3)
      , ... },
   ...
}

GNSS-TargetDeviceErrorCauses ::= SEQUENCE {
   cause [0] ENUMERATED { undefined(0), thereWereNotEnoughSatellitesReceived(1)
      , assistanceDataMissing(2), notAllRequestedMeasurementsPossible(3), ... }
      ,
   fineTimeAssistanceMeasurementsNotPossible [1] NULL OPTIONAL,
   adrMeasurementsNotPossible [2] NULL OPTIONAL,
   multiFrequencyMeasurementsNotPossible [3] NULL OPTIONAL,
   ...
}

A-GNSS-Error ::= CHOICE {
   locationServerErrorCauses [0] GNSS-LocationServerErrorCauses,
   targetDeviceErrorCauses [1] GNSS-TargetDeviceErrorCauses,
   ...
}

A-GNSS-ProvideAssistanceData ::= SEQUENCE {
   gnss-CommonAssistData [0] GNSS-CommonAssistData OPTIONAL,
   gnss-GenericAssistData [1] GNSS-GenericAssistData OPTIONAL,
   gnss-Error [2] A-GNSS-Error OPTIONAL,
   ...
}

PRS-Info ::= SEQUENCE {
   prs-Bandwidth [0] ENUMERATED { n6(0), n15(1), n25(2), n50(3), n75(4), 
      n100(5), ... },
   prs-ConfigurationIndex [1] INTEGER (0..4095),
   numDL-Frames [2] ENUMERATED { sf-1(0), sf-2(1), sf-4(2), sf-6(3), ... },
   ...,
   prs-MutingInfo-r9 [3] CHOICE {
      po2-r9 [0] BIT STRING  (SIZE (2)),
      po4-r9 [1] BIT STRING  (SIZE (4)),
      po8-r9 [2] BIT STRING  (SIZE (8)),
      po16-r9 [3] BIT STRING  (SIZE (16)),
      ...
   } OPTIONAL
}

OTDOA-ReferenceCellInfo ::= SEQUENCE {
   physCellId [0] INTEGER (0..503),
   cellGlobalId [1] ECGI OPTIONAL,
   earfcnRef [2] ARFCN-ValueEUTRA OPTIONAL,
   antennaPortConfig [3] ENUMERATED { ports1-or-2(0), ports4(1), ... } OPTIONAL
      ,
   cpLength [4] ENUMERATED { normal(0), extended(1), ... },
   prsInfo [5] PRS-Info OPTIONAL,
   ...,
   [[ 2:
      earfcnRef-v9a0 [6] ARFCN-ValueEUTRA-v9a0 OPTIONAL
   ]]
}

OTDOA-NeighbourCellInfoElement ::= SEQUENCE {
   physCellId [0] INTEGER (0..503),
   cellGlobalId [1] ECGI OPTIONAL,
   earfcn [2] ARFCN-ValueEUTRA OPTIONAL,
   cpLength [3] ENUMERATED { normal(0), extended(1), ... } OPTIONAL,
   prsInfo [4] PRS-Info OPTIONAL,
   antennaPortConfig [5] ENUMERATED { ports-1-or-2(0), ports-4(1), ... }
       OPTIONAL,
   slotNumberOffset [6] INTEGER (0..19) OPTIONAL,
   prs-SubframeOffset [7] INTEGER (0..1279) OPTIONAL,
   expectedRSTD [8] INTEGER (0..16383),
   expectedRSTD-Uncertainty [9] INTEGER (0..1023),
   ...,
   [[ 2:
      earfcn-v9a0 [10] ARFCN-ValueEUTRA-v9a0 OPTIONAL
   ]]
}

OTDOA-NeighbourFreqInfo ::= SEQUENCE (SIZE (1..24)) OF 
   OTDOA-NeighbourCellInfoElement

OTDOA-NeighbourCellInfoList ::= SEQUENCE (SIZE (1..maxFreqLayers)) OF OTDOA-NeighbourFreqInfo
   

OTDOA-LocationServerErrorCauses ::= SEQUENCE {
   cause [0] ENUMERATED { undefined(0), assistanceDataNotSupportedByServer(1), 
      assistanceDataSupportedButCurrentlyNotAvailableByServer(2), ... },
   ...
}

OTDOA-TargetDeviceErrorCauses ::= SEQUENCE {
   cause [0] ENUMERATED { undefined(0), assistance-data-missing(1), 
      unableToMeasureReferenceCell(2), unableToMeasureAnyNeighbourCell(3), 
      attemptedButUnableToMeasureSomeNeighbourCells(4), ... },
   ...
}

OTDOA-Error ::= CHOICE {
   locationServerErrorCauses [0] OTDOA-LocationServerErrorCauses,
   targetDeviceErrorCauses [1] OTDOA-TargetDeviceErrorCauses,
   ...
}

OTDOA-ProvideAssistanceData ::= SEQUENCE {
   otdoa-ReferenceCellInfo [0] OTDOA-ReferenceCellInfo OPTIONAL,
   otdoa-NeighbourCellInfo [1] OTDOA-NeighbourCellInfoList OPTIONAL,
   otdoa-Error [2] OTDOA-Error OPTIONAL,
   ...
}

ProvideAssistanceData-r9-IEs ::= SEQUENCE {
   commonIEsProvideAssistanceData [0] CommonIEsProvideAssistanceData OPTIONAL,
   a-gnss-ProvideAssistanceData [1] A-GNSS-ProvideAssistanceData OPTIONAL,
   otdoa-ProvideAssistanceData [2] OTDOA-ProvideAssistanceData OPTIONAL,
   epdu-Provide-Assistance-Data [3] EPDU-Sequence OPTIONAL,
   ...
}

ProvideAssistanceData ::= SEQUENCE {
   criticalExtensions [0] CHOICE {
      c1 [0] CHOICE {
         provideAssistanceData-r9 [0] ProvideAssistanceData-r9-IEs,
         spare3 [1] NULL,
         spare2 [2] NULL,
         spare1 [3] NULL
      },
      criticalExtensionsFuture [1] SEQUENCE {

      }
   }
}

TriggeredReportingCriteria ::= SEQUENCE {
   cellChange [0] BOOLEAN,
   reportingDuration [1] ReportingDuration,
   ...
}

PeriodicalReportingCriteria ::= SEQUENCE {
   reportingAmount [0] ENUMERATED { ra1(0), ra2(1), ra4(2), ra8(3), ra16(4), 
      ra32(5), ra64(6), ra-Infinity(7) } DEFAULT ra-Infinity,
   reportingInterval [1] ENUMERATED { noPeriodicalReporting(0), ri0-25(1), 
      ri0-5(2), ri1(3), ri2(4), ri4(5), ri8(6), ri16(7), ri32(8), ri64(9) }
}

HorizontalAccuracy ::= SEQUENCE {
   accuracy [0] INTEGER (0..127),
   confidence [1] INTEGER (0..100),
   ...
}

VerticalAccuracy ::= SEQUENCE {
   accuracy [0] INTEGER (0..127),
   confidence [1] INTEGER (0..100),
   ...
}

ResponseTime ::= SEQUENCE {
   time [0] INTEGER (1..128),
   ...,
   [[ 2:
      responseTimeEarlyFix-r12 [1] INTEGER (1..128) OPTIONAL
   ]]
}

QoS ::= SEQUENCE {
   horizontalAccuracy [0] HorizontalAccuracy OPTIONAL,
   verticalCoordinateRequest [1] BOOLEAN,
   verticalAccuracy [2] VerticalAccuracy OPTIONAL,
   responseTime [3] ResponseTime OPTIONAL,
   velocityRequest [4] BOOLEAN,
   ...
}

CommonIEsRequestLocationInformation ::= SEQUENCE {
   locationInformationType [0] LocationInformationType,
   triggeredReporting [1] TriggeredReportingCriteria OPTIONAL,
   periodicalReporting [2] PeriodicalReportingCriteria OPTIONAL,
   additionalInformation [3] AdditionalInformation OPTIONAL,
   qos [4] QoS OPTIONAL,
   environment [5] Environment OPTIONAL,
   locationCoordinateTypes [6] LocationCoordinateTypes OPTIONAL,
   velocityTypes [7] VelocityTypes OPTIONAL,
   ...
}

GNSS-PositioningInstructions ::= SEQUENCE {
   gnss-Methods [0] GNSS-ID-Bitmap,
   fineTimeAssistanceMeasReq [1] BOOLEAN,
   adrMeasReq [2] BOOLEAN,
   multiFreqMeasReq [3] BOOLEAN,
   assistanceAvailability [4] BOOLEAN,
   ...
}

A-GNSS-RequestLocationInformation ::= SEQUENCE {
   gnss-PositioningInstructions [0] GNSS-PositioningInstructions,
   ...
}

OTDOA-RequestLocationInformation ::= SEQUENCE {
   assistanceAvailability [0] BOOLEAN,
   ...
}

ECID-RequestLocationInformation ::= SEQUENCE {
   requestedMeasurements [0] BIT STRING  { rsrpReq(0), rsrqReq(1), ueRxTxReq(2)
       } (SIZE (1..8)),
   ...
}

Sensor-RequestLocationInformation-r13 ::= SEQUENCE {
   uncompensatedBarometricPressureReq-r13 [0] BOOLEAN,
   ...
}

TBS-RequestLocationInformation-r13 ::= SEQUENCE {
   mbsSgnMeasListReq-r13 [0] BOOLEAN,
   ...
}

WLAN-RequestLocationInformation-r13 ::= SEQUENCE {
   requestedMeasurements-r13 [0] BIT STRING  { rssi(0), rtt(1) } (SIZE (1..8)),
   ...
}

BT-RequestLocationInformation-r13 ::= SEQUENCE {
   requestedMeasurements-r13 [0] BIT STRING  { rssi(0) } (SIZE (1..8)),
   ...
}

RequestLocationInformation-r9-IEs ::= SEQUENCE {
   commonIEsRequestLocationInformation [0] CommonIEsRequestLocationInformation
       OPTIONAL,
   a-gnss-RequestLocationInformation [1] A-GNSS-RequestLocationInformation
       OPTIONAL,
   otdoa-RequestLocationInformation [2] OTDOA-RequestLocationInformation
       OPTIONAL,
   ecid-RequestLocationInformation [3] ECID-RequestLocationInformation OPTIONAL
      ,
   epdu-RequestLocationInformation [4] EPDU-Sequence OPTIONAL,
   ...,
   [[ 2:
      sensor-RequestLocationInformation-r13 [5] 
         Sensor-RequestLocationInformation-r13 OPTIONAL,
      tbs-RequestLocationInformation-r13 [6] TBS-RequestLocationInformation-r13
          OPTIONAL,
      wlan-RequestLocationInformation-r13 [7] 
         WLAN-RequestLocationInformation-r13 OPTIONAL,
      bt-RequestLocationInformation-r13 [8] BT-RequestLocationInformation-r13
          OPTIONAL
   ]]
}

RequestLocationInformation ::= SEQUENCE {
   criticalExtensions [0] CHOICE {
      c1 [0] CHOICE {
         requestLocationInformation-r9 [0] RequestLocationInformation-r9-IEs,
         spare3 [1] NULL,
         spare2 [2] NULL,
         spare1 [3] NULL
      },
      criticalExtensionsFuture [1] SEQUENCE {

      }
   }
}

Ellipsoid-Point ::= SEQUENCE {
   latitudeSign [0] ENUMERATED { north(0), south(1) },
   degreesLatitude [1] INTEGER (0..8388607),
   degreesLongitude [2] INTEGER (-8388608..8388607)
}

Ellipsoid-PointWithUncertaintyCircle ::= SEQUENCE {
   latitudeSign [0] ENUMERATED { north(0), south(1) },
   degreesLatitude [1] INTEGER (0..8388607),
   degreesLongitude [2] INTEGER (-8388608..8388607),
   uncertainty [3] INTEGER (0..127)
}

EllipsoidPointWithUncertaintyEllipse ::= SEQUENCE {
   latitudeSign [0] ENUMERATED { north(0), south(1) },
   degreesLatitude [1] INTEGER (0..8388607),
   degreesLongitude [2] INTEGER (-8388608..8388607),
   uncertaintySemiMajor [3] INTEGER (0..127),
   uncertaintySemiMinor [4] INTEGER (0..127),
   orientationMajorAxis [5] INTEGER (0..179),
   confidence [6] INTEGER (0..100)
}

PolygonPoints ::= SEQUENCE {
   latitudeSign [0] ENUMERATED { north(0), south(1) },
   degreesLatitude [1] INTEGER (0..8388607),
   degreesLongitude [2] INTEGER (-8388608..8388607)
}

Polygon ::= SEQUENCE (SIZE (3..15)) OF PolygonPoints

EllipsoidPointWithAltitude ::= SEQUENCE {
   latitudeSign [0] ENUMERATED { north(0), south(1) },
   degreesLatitude [1] INTEGER (0..8388607),
   degreesLongitude [2] INTEGER (-8388608..8388607),
   altitudeDirection [3] ENUMERATED { height(0), depth(1) },
   altitude [4] INTEGER (0..32767)
}

EllipsoidArc ::= SEQUENCE {
   latitudeSign [0] ENUMERATED { north(0), south(1) },
   degreesLatitude [1] INTEGER (0..8388607),
   degreesLongitude [2] INTEGER (-8388608..8388607),
   innerRadius [3] INTEGER (0..65535),
   uncertaintyRadius [4] INTEGER (0..127),
   offsetAngle [5] INTEGER (0..179),
   includedAngle [6] INTEGER (0..179),
   confidence [7] INTEGER (0..100)
}

LocationCoordinates ::= CHOICE {
   ellipsoidPoint [0] Ellipsoid-Point,
   ellipsoidPointWithUncertaintyCircle [1] Ellipsoid-PointWithUncertaintyCircle
      ,
   ellipsoidPointWithUncertaintyEllipse [2] 
      EllipsoidPointWithUncertaintyEllipse,
   polygon [3] Polygon,
   ellipsoidPointWithAltitude [4] EllipsoidPointWithAltitude,
   ellipsoidPointWithAltitudeAndUncertaintyEllipsoid [5] 
      EllipsoidPointWithAltitudeAndUncertaintyEllipsoid,
   ellipsoidArc [6] EllipsoidArc,
   ...
}

HorizontalVelocity ::= SEQUENCE {
   bearing [0] INTEGER (0..359),
   horizontalSpeed [1] INTEGER (0..2047)
}

HorizontalWithVerticalVelocity ::= SEQUENCE {
   bearing [0] INTEGER (0..359),
   horizontalSpeed [1] INTEGER (0..2047),
   verticalDirection [2] ENUMERATED { upward(0), downward(1) },
   verticalSpeed [3] INTEGER (0..255)
}

HorizontalVelocityWithUncertainty ::= SEQUENCE {
   bearing [0] INTEGER (0..359),
   horizontalSpeed [1] INTEGER (0..2047),
   uncertaintySpeed [2] INTEGER (0..255)
}

HorizontalWithVerticalVelocityAndUncertainty ::= SEQUENCE {
   bearing [0] INTEGER (0..359),
   horizontalSpeed [1] INTEGER (0..2047),
   verticalDirection [2] ENUMERATED { upward(0), downward(1) },
   verticalSpeed [3] INTEGER (0..255),
   horizontalUncertaintySpeed [4] INTEGER (0..255),
   verticalUncertaintySpeed [5] INTEGER (0..255)
}

Velocity ::= CHOICE {
   horizontalVelocity [0] HorizontalVelocity,
   horizontalWithVerticalVelocity [1] HorizontalWithVerticalVelocity,
   horizontalVelocityWithUncertainty [2] HorizontalVelocityWithUncertainty,
   horizontalWithVerticalVelocityAndUncertainty [3] 
      HorizontalWithVerticalVelocityAndUncertainty,
   ...
}

LocationError ::= SEQUENCE {
   locationfailurecause [0] LocationFailureCause,
   ...
}

CommonIEsProvideLocationInformation ::= SEQUENCE {
   locationEstimate [0] LocationCoordinates OPTIONAL,
   velocityEstimate [1] Velocity OPTIONAL,
   locationError [2] LocationError OPTIONAL,
   ...,
   [[ 2:
      earlyFixReport-r12 [3] EarlyFixReport-r12 OPTIONAL
   ]],
   [[ 3:
      locationSource-r13 [4] LocationSource-r13 OPTIONAL,
      locationTimestamp-r13 [5] UTCTime OPTIONAL
   ]]
}

MeasurementReferenceTime ::= SEQUENCE {
   gnss-TOD-msec [0] INTEGER (0..3599999),
   gnss-TOD-frac [1] INTEGER (0..3999) OPTIONAL,
   gnss-TOD-unc [2] INTEGER (0..127) OPTIONAL,
   gnss-TimeID [3] GNSS-ID,
   networkTime [4] CHOICE {
      eUTRA [0] SEQUENCE {
         physCellId [0] INTEGER (0..503),
         cellGlobalId [1] CellGlobalIdEUTRA-AndUTRA OPTIONAL,
         systemFrameNumber [2] BIT STRING  (SIZE (10)),
         ...
      },
      uTRA [1] SEQUENCE {
         mode [0] CHOICE {
            fdd [0] SEQUENCE {
               primary-CPICH-Info [0] INTEGER (0..511),
               ...
            },
            tdd [1] SEQUENCE {
               cellParameters [0] INTEGER (0..127),
               ...
            }
         },
         cellGlobalId [1] CellGlobalIdEUTRA-AndUTRA OPTIONAL,
         referenceSystemFrameNumber [2] INTEGER (0..4095),
         ...
      },
      gSM [2] SEQUENCE {
         bcchCarrier [0] INTEGER (0..1023),
         bsic [1] INTEGER (0..63),
         cellGlobalId [2] CellGlobalIdGERAN OPTIONAL,
         referenceFrame [3] SEQUENCE {
            referenceFN [0] INTEGER (0..65535),
            referenceFNMSB [1] INTEGER (0..63) OPTIONAL,
            ...
         },
         deltaGNSS-TOD [4] INTEGER (0..127) OPTIONAL,
         ...
      },
      ...
   } OPTIONAL,
   ...
}

GNSS-SatMeasElement ::= SEQUENCE {
   svID [0] SV-ID,
   cNo [1] INTEGER (0..63),
   mpathDet [2] ENUMERATED { notMeasured(0), low(1), medium(2), high(3), ... }
      ,
   carrierQualityInd [3] INTEGER (0..3) OPTIONAL,
   codePhase [4] INTEGER (0..2097151),
   integerCodePhase [5] INTEGER (0..127) OPTIONAL,
   codePhaseRMSError [6] INTEGER (0..63),
   doppler [7] INTEGER (-32768..32767) OPTIONAL,
   adr [8] INTEGER (0..33554431) OPTIONAL,
   ...
}

GNSS-SatMeasList ::= SEQUENCE (SIZE (1..64)) OF GNSS-SatMeasElement

GNSS-SgnMeasElement ::= SEQUENCE {
   gnss-SignalID [0] GNSS-SignalID,
   gnss-CodePhaseAmbiguity [1] INTEGER (0..127) OPTIONAL,
   gnss-SatMeasList [2] GNSS-SatMeasList,
   ...
}

GNSS-SgnMeasList ::= SEQUENCE (SIZE (1..8)) OF GNSS-SgnMeasElement

GNSS-MeasurementForOneGNSS ::= SEQUENCE {
   gnss-ID [0] GNSS-ID,
   gnss-SgnMeasList [1] GNSS-SgnMeasList,
   ...
}

GNSS-MeasurementList ::= SEQUENCE (SIZE (1..16)) OF GNSS-MeasurementForOneGNSS

GNSS-SignalMeasurementInformation ::= SEQUENCE {
   measurementReferenceTime [0] MeasurementReferenceTime,
   gnss-MeasurementList [1] GNSS-MeasurementList,
   ...
}

GNSS-LocationInformation ::= SEQUENCE {
   measurementReferenceTime [0] MeasurementReferenceTime,
   agnss-List [1] GNSS-ID-Bitmap,
   ...
}

A-GNSS-ProvideLocationInformation ::= SEQUENCE {
   gnss-SignalMeasurementInformation [0] GNSS-SignalMeasurementInformation
       OPTIONAL,
   gnss-LocationInformation [1] GNSS-LocationInformation OPTIONAL,
   gnss-Error [2] A-GNSS-Error OPTIONAL,
   ...
}

OTDOA-MeasQuality ::= SEQUENCE {
   error-Resolution [0] BIT STRING  (SIZE (2)),
   error-Value [1] BIT STRING  (SIZE (5)),
   error-NumSamples [2] BIT STRING  (SIZE (3)) OPTIONAL,
   ...
}

NeighbourMeasurementElement ::= SEQUENCE {
   physCellIdNeighbour [0] INTEGER (0..503),
   cellGlobalIdNeighbour [1] ECGI OPTIONAL,
   earfcnNeighbour [2] ARFCN-ValueEUTRA OPTIONAL,
   rstd [3] INTEGER (0..12711),
   rstd-Quality [4] OTDOA-MeasQuality,
   ...,
   [[ 2:
      earfcnNeighbour-v9a0 [5] ARFCN-ValueEUTRA-v9a0 OPTIONAL
   ]]
}

NeighbourMeasurementList ::= SEQUENCE (SIZE (1..24)) OF 
   NeighbourMeasurementElement

OTDOA-SignalMeasurementInformation ::= SEQUENCE {
   systemFrameNumber [0] BIT STRING  (SIZE (10)),
   physCellIdRef [1] INTEGER (0..503),
   cellGlobalIdRef [2] ECGI OPTIONAL,
   earfcnRef [3] ARFCN-ValueEUTRA OPTIONAL,
   referenceQuality [4] OTDOA-MeasQuality OPTIONAL,
   neighbourMeasurementList [5] NeighbourMeasurementList,
   ...,
   [[ 2:
      earfcnRef-v9a0 [6] ARFCN-ValueEUTRA-v9a0 OPTIONAL
   ]]
}

OTDOA-ProvideLocationInformation ::= SEQUENCE {
   otdoaSignalMeasurementInformation [0] OTDOA-SignalMeasurementInformation
       OPTIONAL,
   otdoa-Error [1] OTDOA-Error OPTIONAL,
   ...
}

MeasuredResultsElement ::= SEQUENCE {
   physCellId [0] INTEGER (0..503),
   cellGlobalId [1] CellGlobalIdEUTRA-AndUTRA OPTIONAL,
   arfcnEUTRA [2] ARFCN-ValueEUTRA,
   systemFrameNumber [3] BIT STRING  (SIZE (10)) OPTIONAL,
   rsrp-Result [4] INTEGER (0..97) OPTIONAL,
   rsrq-Result [5] INTEGER (0..34) OPTIONAL,
   ue-RxTxTimeDiff [6] INTEGER (0..4095) OPTIONAL,
   ...,
   [[ 2:
      arfcnEUTRA-v9a0 [7] ARFCN-ValueEUTRA-v9a0 OPTIONAL
   ]]
}

MeasuredResultsList ::= SEQUENCE (SIZE (1..32)) OF MeasuredResultsElement

ECID-SignalMeasurementInformation ::= SEQUENCE {
   primaryCellMeasuredResults [0] MeasuredResultsElement OPTIONAL,
   measuredResultsList [1] MeasuredResultsList,
   ...
}

ECID-LocationServerErrorCauses ::= SEQUENCE {
   cause [0] ENUMERATED { undefined(0), ... },
   ...
}

ECID-TargetDeviceErrorCauses ::= SEQUENCE {
   cause [0] ENUMERATED { undefined(0), requestedMeasurementNotAvailable(1), 
      notAllrequestedMeasurementsPossible(2), ... },
   rsrpMeasurementNotPossible [1] NULL OPTIONAL,
   rsrqMeasurementNotPossible [2] NULL OPTIONAL,
   ueRxTxMeasurementNotPossible [3] NULL OPTIONAL,
   ...
}

ECID-Error ::= CHOICE {
   locationServerErrorCauses [0] ECID-LocationServerErrorCauses,
   targetDeviceErrorCauses [1] ECID-TargetDeviceErrorCauses,
   ...
}

ECID-ProvideLocationInformation ::= SEQUENCE {
   ecid-SignalMeasurementInformation [0] ECID-SignalMeasurementInformation
       OPTIONAL,
   ecid-Error [1] ECID-Error OPTIONAL,
   ...
}

Sensor-MeasurementInformation-r13 ::= SEQUENCE {
   measurementReferenceTime-r13 [0] UTCTime OPTIONAL,
   uncompensatedBarometricPressure-r13 [1] INTEGER (30000..115000) OPTIONAL,
   ...
}

Sensor-LocationServerErrorCauses-r13 ::= SEQUENCE {
   cause-r13 [0] ENUMERATED { undefined(0), ... },
   ...
}

Sensor-TargetDeviceErrorCauses-r13 ::= SEQUENCE {
   cause-r13 [0] ENUMERATED { undefined(0), ... },
   ...
}

Sensor-Error-r13 ::= CHOICE {
   locationServerErrorCauses-r13 [0] Sensor-LocationServerErrorCauses-r13,
   targetDeviceErrorCauses-r13 [1] Sensor-TargetDeviceErrorCauses-r13,
   ...
}

Sensor-ProvideLocationInformation-r13 ::= SEQUENCE {
   sensor-MeasurementInformation-r13 [0] Sensor-MeasurementInformation-r13
       OPTIONAL,
   sensor-Error-r13 [1] Sensor-Error-r13 OPTIONAL,
   ...
}

MBS-BeaconMeasElement-r13 ::= SEQUENCE {
   transmitterID-r13 [0] INTEGER (0..32767),
   codePhase-r13 [1] INTEGER (0..2097151),
   codePhaseRMSError-r13 [2] INTEGER (0..63),
   ...
}

MBS-BeaconMeasList-r13 ::= SEQUENCE (SIZE (1..64)) OF MBS-BeaconMeasElement-r13

TBS-MeasurementInformation-r13 ::= SEQUENCE {
   measurementReferenceTime-r13 [0] UTCTime OPTIONAL,
   mbs-SgnMeasList-r13 [1] MBS-BeaconMeasList-r13 OPTIONAL,
   ...
}

TBS-LocationServerErrorCauses-r13 ::= SEQUENCE {
   cause-r13 [0] ENUMERATED { undefined(0), ... },
   ...
}

TBS-TargetDeviceErrorCauses-r13 ::= SEQUENCE {
   cause-r13 [0] ENUMERATED { undefined(0), 
      thereWereNotEnoughMBSBeaconsReceived(1), ... },
   ...
}

TBS-Error-r13 ::= CHOICE {
   locationServerErrorCauses-r13 [0] TBS-LocationServerErrorCauses-r13,
   targetDeviceErrorCauses-r13 [1] TBS-TargetDeviceErrorCauses-r13,
   ...
}

TBS-ProvideLocationInformation-r13 ::= SEQUENCE {
   tbs-MeasurementInformation-r13 [0] TBS-MeasurementInformation-r13 OPTIONAL,
   tbs-Error-r13 [1] TBS-Error-r13 OPTIONAL,
   ...
}

WLAN-AP-Identifier-r13 ::= SEQUENCE {
   bssid-r13 [0] OCTET STRING (SIZE (6)),
   ssid-r13 [1] OCTET STRING (SIZE (1..32)) OPTIONAL,
   ...
}

WLAN-RTT-r13 ::= SEQUENCE {
   rttValue-r13 [0] INTEGER (0..16777215),
   rttUnits-r13 [1] ENUMERATED { microseconds(0), hundredsofnanoseconds(1), 
      tensofnanoseconds(2), nanoseconds(3), tenthsofnanoseconds(4), ... },
   rttAccuracy-r13 [2] INTEGER (0..255) OPTIONAL,
   ...
}

WLAN-MeasurementElement-r13 ::= SEQUENCE {
   wlan-AP-Identifier-r13 [0] WLAN-AP-Identifier-r13,
   rssi-r13 [1] INTEGER (-127..128) OPTIONAL,
   rtt-r13 [2] WLAN-RTT-r13 OPTIONAL,
   apChannelFrequency-r13 [3] INTEGER (0..256) OPTIONAL,
   servingFlag-r13 [4] BOOLEAN OPTIONAL,
   ...
}

WLAN-MeasurementList-r13 ::= SEQUENCE (SIZE (1..maxWLAN-AP-r13)) OF 
   WLAN-MeasurementElement-r13

WLAN-MeasurementInformation-r13 ::= SEQUENCE {
   measurementReferenceTime-r13 [0] UTCTime OPTIONAL,
   wlan-MeasurementList-r13 [1] WLAN-MeasurementList-r13 OPTIONAL,
   ...
}

WLAN-LocationServerErrorCauses-r13 ::= SEQUENCE {
   cause-r13 [0] ENUMERATED { undefined(0), ... },
   ...
}

WLAN-TargetDeviceErrorCauses-r13 ::= SEQUENCE {
   cause-r13 [0] ENUMERATED { undefined(0), 
      requestedMeasurementsNotAvailable(1), 
      notAllrequestedMeasurementsPossible(2), ... },
   wlan-AP-RSSI-MeasurementNotPossible-r13 [1] NULL OPTIONAL,
   wlan-AP-RTT-MeasurementNotPossible-r13 [2] NULL OPTIONAL,
   ...
}

WLAN-Error-r13 ::= CHOICE {
   locationServerErrorCauses-r13 [0] WLAN-LocationServerErrorCauses-r13,
   targetDeviceErrorCauses-r13 [1] WLAN-TargetDeviceErrorCauses-r13,
   ...
}

WLAN-ProvideLocationInformation-r13 ::= SEQUENCE {
   wlan-MeasurementInformation-r13 [0] WLAN-MeasurementInformation-r13 OPTIONAL
      ,
   wlan-Error-r13 [1] WLAN-Error-r13 OPTIONAL,
   ...
}

BT-MeasurementElement-r13 ::= SEQUENCE {
   btAddr-r13 [0] BIT STRING  (SIZE (48)),
   rssi-r13 [1] INTEGER (-128..127) OPTIONAL,
   ...
}

BT-MeasurementList-r13 ::= SEQUENCE (SIZE (1..maxBT-Beacon-r13)) OF BT-MeasurementElement-r13

BT-MeasurementInformation-r13 ::= SEQUENCE {
   measurementReferenceTime-r13 [0] UTCTime OPTIONAL,
   bt-MeasurementList-r13 [1] BT-MeasurementList-r13 OPTIONAL,
   ...
}

BT-LocationServerErrorCauses-r13 ::= SEQUENCE {
   cause-r13 [0] ENUMERATED { undefined(0), ... },
   ...
}

BT-TargetDeviceErrorCauses-r13 ::= SEQUENCE {
   cause-r13 [0] ENUMERATED { undefined(0), 
      requestedMeasurementsNotAvailable(1), 
      notAllrequestedMeasurementsPossible(2), ... },
   bt-Beacon-rssiMeasurementNotPossible-r13 [1] NULL OPTIONAL,
   ...
}

BT-Error-r13 ::= CHOICE {
   locationServerErrorCauses-r13 [0] BT-LocationServerErrorCauses-r13,
   targetDeviceErrorCauses-r13 [1] BT-TargetDeviceErrorCauses-r13,
   ...
}

BT-ProvideLocationInformation-r13 ::= SEQUENCE {
   bt-MeasurementInformation-r13 [0] BT-MeasurementInformation-r13 OPTIONAL,
   bt-Error-r13 [1] BT-Error-r13 OPTIONAL,
   ...
}

ProvideLocationInformation-r9-IEs ::= SEQUENCE {
   commonIEsProvideLocationInformation [0] CommonIEsProvideLocationInformation
       OPTIONAL,
   a-gnss-ProvideLocationInformation [1] A-GNSS-ProvideLocationInformation
       OPTIONAL,
   otdoa-ProvideLocationInformation [2] OTDOA-ProvideLocationInformation
       OPTIONAL,
   ecid-ProvideLocationInformation [3] ECID-ProvideLocationInformation OPTIONAL
      ,
   epdu-ProvideLocationInformation [4] EPDU-Sequence OPTIONAL,
   ...,
   [[ 2:
      sensor-ProvideLocationInformation-r13 [5] 
         Sensor-ProvideLocationInformation-r13 OPTIONAL,
      tbs-ProvideLocationInformation-r13 [6] TBS-ProvideLocationInformation-r13
          OPTIONAL,
      wlan-ProvideLocationInformation-r13 [7] 
         WLAN-ProvideLocationInformation-r13 OPTIONAL,
      bt-ProvideLocationInformation-r13 [8] BT-ProvideLocationInformation-r13
          OPTIONAL
   ]]
}

ProvideLocationInformation ::= SEQUENCE {
   criticalExtensions [0] CHOICE {
      c1 [0] CHOICE {
         provideLocationInformation-r9 [0] ProvideLocationInformation-r9-IEs,
         spare3 [1] NULL,
         spare2 [2] NULL,
         spare1 [3] NULL
      },
      criticalExtensionsFuture [1] SEQUENCE {

      }
   }
}

CommonIEsAbort ::= SEQUENCE {
   abortCause [0] ENUMERATED { undefined(0), stopPeriodicReporting(1), 
      targetDeviceAbort(2), networkAbort(3), ... }
}

Abort-r9-IEs ::= SEQUENCE {
   commonIEsAbort [0] CommonIEsAbort OPTIONAL,
   ...,
   epdu-Abort [1] EPDU-Sequence OPTIONAL
}

Abort ::= SEQUENCE {
   criticalExtensions [0] CHOICE {
      c1 [0] CHOICE {
         abort-r9 [0] Abort-r9-IEs,
         spare3 [1] NULL,
         spare2 [2] NULL,
         spare1 [3] NULL
      },
      criticalExtensionsFuture [1] SEQUENCE {

      }
   }
}

CommonIEsError ::= SEQUENCE {
   errorCause [0] ENUMERATED { undefined(0), lppMessageHeaderError(1), 
      lppMessageBodyError(2), epduError(3), incorrectDataValue(4), ... }
}

Error-r9-IEs ::= SEQUENCE {
   commonIEsError [0] CommonIEsError OPTIONAL,
   ...,
   epdu-Error [1] EPDU-Sequence OPTIONAL
}

Error ::= CHOICE {
   error-r9 [0] Error-r9-IEs,
   criticalExtensionsFuture [1] SEQUENCE {

   }
}

LPP-MessageBody ::= CHOICE {
   c1 [0] CHOICE {
      requestCapabilities [0] RequestCapabilities,
      provideCapabilities [1] ProvideCapabilities,
      requestAssistanceData [2] RequestAssistanceData,
      provideAssistanceData [3] ProvideAssistanceData,
      requestLocationInformation [4] RequestLocationInformation,
      provideLocationInformation [5] ProvideLocationInformation,
      abort [6] Abort,
      error [7] Error,
      spare7 [8] NULL,
      spare6 [9] NULL,
      spare5 [10] NULL,
      spare4 [11] NULL,
      spare3 [12] NULL,
      spare2 [13] NULL,
      spare1 [14] NULL,
      spare0 [15] NULL
   },
   messageClassExtension [1] SEQUENCE {

   }
}

LPP-Message ::= SEQUENCE {
   transactionID [0] LPP-TransactionID OPTIONAL,
   endTransaction [1] BOOLEAN,
   sequenceNumber [2] SequenceNumber OPTIONAL,
   acknowledgement [3] Acknowledgement OPTIONAL,
   lpp-MessageBody [4] LPP-MessageBody OPTIONAL
}

-- Value assignments

maxEARFCN INTEGER ::= 65535

maxEARFCN-Plus1 INTEGER ::= 65536

maxEARFCN2 INTEGER ::= 262143

maxEPDU INTEGER ::= 16

maxFreqLayers INTEGER ::= 3

maxBands INTEGER ::= 64

maxFBI INTEGER ::= 64

maxFBI-Plus1 INTEGER ::= 65

maxFBI2 INTEGER ::= 256

maxWLAN-AP-r13 INTEGER ::= 64

maxBT-Beacon-r13 INTEGER ::= 32


END
