-- *************************************
-- From CAP v3 specification:
-- *************************************

CAP-datatypes {ccitt(0) identified-organization(4) etsi(0) mobileDomain(0) umts-network(1) modules(3) cap-datatypes(52) version3(2)}
-- This module contains the type definitions for the CAP v.3 data types.

DEFINITIONS IMPLICIT TAGS ::= BEGIN


IMPORTS

	CallingPartysCategory,
	Duration,
	HighLayerCompatibility,
	Integer4,
	Interval,
	LegID,
	RedirectionInformation,
	ServiceKey
		FROM CS1-DataTypes {ccitt(0) identified-organization(4) 
		etsi(0) inDomain(1) in-network(1) modules(0) 
		cs1-datatypes(2) version1(0)}

	BothwayThroughConnectionInd,
	CriticalityType,
	MiscCallInfo
		FROM CS2-datatypes {ccitt(0) identified-organization(4) 
		etsi(0) inDomain(1) in-network(1) cS2(20) modules(0) 
		in-cs2-datatypes(0) version1(0)}

	IMSI,
	ISDN-AddressString,
	Ext-BasicServiceCode,
	NAEA-CIC
		FROM MAP-CommonDataTypes {ccitt(0) identified-organization(4) 
		etsi(0) mobileDomain(0) gsm-network(1) modules(3) 
		map-CommonDataTypes(18) version6(6)}

	Ext-QoS-Subscribed,
	GSN-Address,
	LocationInformation,
        LSAIdentity, 
	QoS-Subscribed,
	SubscriberState
		FROM MAP-MS-DataTypes {ccitt(0) identified-organization(4) 
		etsi(0) mobileDomain(0) gsm-network(1) modules(3) 
		map-MS-DataTypes(11) version6(6)}

	CallReferenceNumber,
	SuppressionOfAnnouncement
		FROM MAP-CH-DataTypes {ccitt(0) identified-organization(4) 
		etsi(0) mobileDomain(0) gsm-network(1) modules(3) 
		map-CH-DataTypes(13) version6(6)}

        ExtensionContainer 
                FROM MAP-ExtensionDataTypes {
                itu-t identified-organization (4) etsi (0) mobileDomain (0)
                gsm-Network (1) modules (3) map-ExtensionDataTypes (21) 
                version12 (12)}

	EXTENSION,
	PARAMETERS-BOUND,
	SupportedExtensions {}
		FROM CAP-classes {ccitt(0) identified-organization(4) etsi(0) 
		mobileDomain(0) umts-network(1) modules(3) cap-classes(54) 
		version3(2)}


;

AccessPointName {PARAMETERS-BOUND: bound}::= OCTET STRING (SIZE(
	bound.&minAccessPointNameLength .. bound.&maxAccessPointNameLength))
-- Indicates the AccessPointName, refer to 3GPP TS 24.008 [12] for the encoding.

AChBillingChargingCharacteristics {PARAMETERS-BOUND : bound} ::= OCTET STRING (SIZE
	(bound.&minAChBillingChargingLength .. bound.&maxAChBillingChargingLength))
	(CONSTRAINED BY {-- shall be the result of the BER-encoded value of the type --
	CAMEL-AchBillingChargingCharacteristics {bound}})
-- The AChBillingChargingCharacteristics parameter specifies the charging related information
-- to be provided by the gsmSSF and the conditions on which this information has to be reported
-- back to the gsmSCF with the ApplyChargingReport operation. The value of the 
-- AchBillingChargingCharacteristics of type OCTET STRING carries a value of the ASN.1 data type:
-- CAMEL-AchBillingChargingCharacteristics. The normal encoding rules are used to encode this 
-- value.
-- The violation of the UserDefinedConstraint shall be handled as an ASN.1 syntax error.

AdditionalCallingPartyNumber {PARAMETERS-BOUND : bound} 	::= Digits {bound}
-- Indicates the Additional Calling Party Number. 

AlertingPattern 						::= OCTET STRING (SIZE(3))
-- Indicates a specific pattern that is used to alert a subscriber
-- (e.g. distinctive ringing, tones, etc.).
-- The encoding of the last octet of this parameter is as defined in 3GPP TS 29.002 [13].
-- Only the trailing OCTET is used, the remaining OCTETS shall be sent as NULL (zero)
-- The receiving side shall ignore the leading two OCTETS.

AOCBeforeAnswer						::= SEQUENCE {
	aOCInitial				[0] CAI-GSM0224,
	aOCSubsequent				[1] AOCSubsequent OPTIONAL
	}

AOCGPRS							::= SEQUENCE {
	aOCInitial				[0] CAI-GSM0224,
	aOCSubsequent				[1] AOCSubsequent OPTIONAL
	}

AOCSubsequent						::= SEQUENCE {
	cAI-GSM0224				[0] CAI-GSM0224	,
	tariffSwitchInterval			[1] INTEGER (1..86400) OPTIONAL
	}
-- tariffSwitchInterval is measured in 1 second units

AppendFreeFormatData 	::= ENUMERATED {
	overwrite		(0),
	append			(1)
	} 

ApplicationTimer 					::=INTEGER (0..2047)
-- Used by the gsmSCF to set a timer in the gsmSSF. The timer is in seconds.

AssistingSSPIPRoutingAddress {PARAMETERS-BOUND : bound} 	::= Digits {bound}
-- Indicates the destination address of the gsmSRF for the assist procedure.

BackwardServiceInteractionInd 		::= SEQUENCE {
	conferenceTreatmentIndicator		[1] OCTET STRING (SIZE(1))	OPTIONAL,
	-- acceptConferenceRequest	'xxxx xx01'B
	-- rejectConferenceRequest	'xxxx xx10'B
	-- network default is accept conference request
	callCompletionTreatmentIndicator	[2] OCTET STRING (SIZE(1))	OPTIONAL,
	-- acceptCallCompletionServiceRequest	'xxxx xx01'B,
	-- rejectCallCompletionServiceRequest	'xxxx xx10'B
	-- network default is accept call completion service request 
	...
	}

BasicGapCriteria {PARAMETERS-BOUND : bound} 	::= CHOICE {
	calledAddressValue		[0] Digits {bound},
	gapOnService			[2] GapOnService,
	calledAddressAndService		[29] SEQUENCE {
		calledAddressValue		[0] Digits {bound},
		serviceKey			[1] ServiceKey,
		...
		},
	callingAddressAndService	[30] SEQUENCE {
		callingAddressValue		[0] Digits {bound},
		serviceKey			[1] ServiceKey,
		...
		}
	}
-- Both calledAddressValue and callingAddressValue can be
-- incomplete numbers, in the sense that a limited amount of digits can be given.
-- For the handling of numbers starting with the same digit string refer to the detailed 
-- procedure of the CallGap operation

BCSMEvent {PARAMETERS-BOUND : bound} ::= SEQUENCE {
	eventTypeBCSM		[0] EventTypeBCSM,
	monitorMode			[1] MonitorMode,
	legID				[2] LegID									OPTIONAL,
	dpSpecificCriteria	[30] DpSpecificCriteria {bound}				OPTIONAL
	}
-- Indicates the BCSM Event information for monitoring.

BearerCapability {PARAMETERS-BOUND : bound} ::= CHOICE {
	bearerCap				[0] OCTET STRING (SIZE(2..bound.&maxBearerCapabilityLength))
	}
-- Indicates the type of bearer capability connection to the user. For bearerCap, the ISUP User
-- Service Information, ETS 300 356-1 [8]
-- encoding shall be used. 

CAI-GSM0224				::= SEQUENCE {
	e1		[0] INTEGER (0..8191)			OPTIONAL,
	e2		[1] INTEGER (0..8191) 			OPTIONAL,
	e3		[2] INTEGER (0..8191) 			OPTIONAL,
	e4		[3] INTEGER (0..8191) 			OPTIONAL,
	e5		[4] INTEGER (0..8191) 			OPTIONAL,
	e6		[5] INTEGER (0..8191) 			OPTIONAL,
	e7		[6] INTEGER (0..8191) 			OPTIONAL
	}
-- Indicates Charge Advice Information to the Mobile Station. For information regarding
-- parameter usage, refer to 3GPP TS 22.040 [26].

CalledPartyBCDNumber {PARAMETERS-BOUND : bound} 	::= OCTET STRING (SIZE(
	bound.&minCalledPartyBCDNumberLength .. bound.&maxCalledPartyBCDNumberLength))
-- Indicates the Called Party Number, including service selection information.
-- Refer to 3GPP TS 24.008 [12]
-- for encoding. This data type carries only the "type of number", "numbering plan 
-- identification" and "number digit" fields defined in 3GPP TS 24.008 [12]; 
-- it does not carry the "called party 
-- BCD number IEI" or "length of called party BCD number contents".

CalledPartyNumber {PARAMETERS-BOUND : bound} 	::= OCTET STRING (SIZE(
	bound.&minCalledPartyNumberLength .. bound.&maxCalledPartyNumberLength))
-- Indicates the Called Party Number. Refer to ITU-T Q.763 [20] for encoding.

CallingPartyNumber {PARAMETERS-BOUND : bound} 	::= OCTET STRING (SIZE(
	bound.&minCallingPartyNumberLength .. bound.&maxCallingPartyNumberLength))
-- Indicates the Calling Party Number. Refer to ETS 300 356-1 [8] for encoding.

CallResult {PARAMETERS-BOUND : bound} ::= OCTET STRING (SIZE(
	bound.&minCallResultLength .. bound.&maxCallResultLength))
	(CONSTRAINED BY {-- shall be the result of the BER-encoded value of type -
	CAMEL-CallResult {bound}})

-- The violation of the UserDefinedConstraint shall be handled as an ASN.1 syntax error.

-- This parameter provides the gsmSCF with the charging related information previously requested
-- using the ApplyCharging operation. This shall include the partyToCharge parameter as
-- received in the related ApplyCharging operation to correlate the result to the request

CAMEL-AChBillingChargingCharacteristics {PARAMETERS-BOUND : bound} ::= CHOICE {
	timeDurationCharging			[0] SEQUENCE {
	maxCallPeriodDuration			[0] INTEGER (1..864000),
	releaseIfdurationExceeded		[1] BOOLEAN DEFAULT FALSE,
	tariffSwitchInterval			[2] INTEGER (1..86400)			OPTIONAL,
	tone					[3] BOOLEAN DEFAULT FALSE,
	extensions				[4] SEQUENCE SIZE(1..bound.&numOfExtensions) OF 
								ExtensionField	{bound} OPTIONAL,
			...
		}
	}
--  tariffSwitchInterval is measured in 1 second units.
--  maxCallPeriodDuration is measured in100 millisecond units

CAMEL-CallResult {PARAMETERS-BOUND : bound}		::= CHOICE {
	timeDurationChargingResult		[0] SEQUENCE {
	partyToCharge				[0] ReceivingSideID,
	timeInformation				[1] TimeInformation,
	callActive				[2] BOOLEAN 			DEFAULT TRUE,
	callReleasedAtTcpExpiry			[3] NULL			OPTIONAL,
	extensions				[4] SEQUENCE SIZE(1..bound.&numOfExtensions)	OF
								ExtensionField	{bound}	OPTIONAL,
		...
		}
	}

CAMEL-SCIBillingChargingCharacteristics ::= CHOICE {
 	aOCBeforeAnswer				[0] AOCBeforeAnswer,
 	aOCAfterAnswer				[1] AOCSubsequent
	}

CAMEL-SCIGPRSBillingChargingCharacteristics ::= SEQUENCE {
	aOCGPRS					[0] AOCGPRS,
 	pDPID					[1] PDPID		OPTIONAL,
	...
	}

Carrier {PARAMETERS-BOUND : bound} ::= OCTET STRING (SIZE(
	bound.&minCarrierLength .. bound.&maxCarrierLength))
-- This parameter is only used for North America (na)
-- It contains the carrier selection field (first octet) followed by Carrier ID
-- information (North America (na)).

-- The Carrier selection is one octet and is encoded as:
-- 00000000		No indication
-- 00000001		Selected carrier identification code (CIC) pre subscribed and not
--				input by calling party
-- 00000010		Selected carrier identification code (CIC) pre subscribed and input by
--				calling party
-- 00000011		Selected carrier identification code (CIC) pre subscribed, no
--				indication of whether input by calling party (undetermined)
-- 00000100 	Selected carrier identification code (CIC) not pre subscribed and
--				input by calling party 
-- 00000101
-- 	to			Spare
-- 11111110
-- 11111111		Reserved

-- Refer to ANSI ISUP T1.113 [53] for encoding of na carrier ID information (3 octets).

Cause {PARAMETERS-BOUND : bound} 			::= OCTET STRING (SIZE(
	bound.&minCauseLength .. bound.&maxCauseLength))
-- Indicates the cause for interface related information. 
-- Refer to ETS 300 356-1 [8] Cause parameter for encoding.
-- For the use of cause and location values refer to ITU-T Recommendation Q.850 [22] 
-- Shall always include the cause value and shall also include the diagnostics field,
-- if available.

CGEncountered 								::= ENUMERATED {
	noCGencountered			(0),
	manualCGencountered		(1),
	scpOverload				(2)
	}
-- Indicates the type of automatic call gapping encountered, if any.

ChargeNumber {PARAMETERS-BOUND : bound} ::= LocationNumber {bound}
-- Information sent in either direction indicating the chargeable number for the call and 
-- consisting of the odd/even indicator, nature of address indicator, numbering plan indicator,
-- and address signals.
-- Uses the LocationNumber format which is based on the Q.763 Location Number format
-- For example, the ChargeNumber may be a third party number to which a call is billed for
-- the 3rd party billing service. In this case, the calling party may request operator assistance
-- to charge the call to, for example, their home number.

-- For NA, this parameter uniquely identifies the chargeable number for a call sent into a North 
-- American long distance carrier. It transports the ChargeNumber Parameter Field
--  as defined in ANSI ISUP T1.113 [53]. This provides
--  - 1 octet for the nature of address indicator field, plus
--  - 1 octet for a numbering plan field, plus
--  - up to 5 octets for the address signal (up to 10 digits)

-- The Charge Number in ANSI T1.113 [53] normally contains a 10 digit national number within
-- the North American Numbering Plan (NANP); longer (e.g. international) charge numbers are not
-- supported in T1.113 [53].

ChargingCharacteristics 			::= CHOICE {
	maxTransferredVolume			[0]	INTEGER (1..4294967295),
	maxElapsedTime					[1] INTEGER (1..86400)
	}
--	maxTransferredVolume is measured in number of bytes
--	maxElapsedTime is measured in seconds

ChargingResult 						::= CHOICE {
	transferredVolume				[0] TransferredVolume,
	elapsedTime						[1]	ElapsedTime
	}

CollectedDigits 							::= SEQUENCE {
	minimumNbOfDigits		[0] INTEGER (1..30)	DEFAULT 1,
	maximumNbOfDigits		[1] INTEGER (1..30),
	endOfReplyDigit			[2] OCTET STRING (SIZE (1..2))	OPTIONAL,
	cancelDigit				[3] OCTET STRING (SIZE (1..2))	OPTIONAL,
	startDigit				[4] OCTET STRING (SIZE (1..2))	OPTIONAL,
	firstDigitTimeOut		[5] INTEGER (1..127)			OPTIONAL,
	interDigitTimeOut		[6] INTEGER (1..127)			OPTIONAL,
	errorTreatment			[7] ErrorTreatment				DEFAULT stdErrorAndInfo,
	interruptableAnnInd		[8] BOOLEAN						DEFAULT TRUE,
	voiceInformation		[9] BOOLEAN						DEFAULT FALSE,
	voiceBack				[10] BOOLEAN					DEFAULT FALSE
	}
-- The use of voiceBack and the support of voice recognition via voiceInformation
-- is network operator specific.
-- The endOfReplyDigit, cancelDigit, and startDigit parameters have been
-- designated as OCTET STRING, and are to be encoded as BCD, one digit per octet
-- only, contained in the four least significant bits of each OCTET. The following encoding shall
-- be applied for the non-decimal characters:
-- 1011 (*), 1100 (#).
-- The usage is service dependent.
-- firstDigitTimeOut and interDigitTimeOut are measured in seconds.

CollectedInfo 								::= CHOICE {
	collectedDigits			[0] CollectedDigits
	}

ConnectedNumberTreatmentInd					::= ENUMERATED {
	noINImpact						(0),
	presentationRestricted 			(1),
	presentCalledINNumber 			(2),
	presentCallINNumberRestricted 	(3)
}
-- This parameter is used to suppress or to display the connected number.

ControlType									::= ENUMERATED {
	sCPOverloaded					(0),
	manuallyInitiated				(1)
	}

CompoundCriteria {PARAMETERS-BOUND : bound}	::= SEQUENCE {
	basicGapCriteria 			[0] BasicGapCriteria {bound},
	scfID						[1] ScfID {bound}					OPTIONAL
	}

CorrelationID {PARAMETERS-BOUND : bound} 	::= Digits {bound}
-- used by gsmSCF for correlation with a previous operation. 

DateAndTime 								::= OCTET STRING (SIZE(7))
--  DateAndTime is BCD encoded. The year digit indicating millenium occupies bits
--  0-3 of the first octet, and the year digit indicating century occupies bits
--  4-7 of the first octet.
--  The year digit indicating decade occupies bits 0-3 of the second octet,
--  whilst the digit indicating the year within the decade occupies bits 4-7 of
--  the second octet.
--  The most significant month digit occupies bits 0-3 of the third octet,
--  and the least significant month digit occupies bits 4-7 of the third octet.
--  The most significant day digit occupies bits 0-3 of the fourth octet,
--  and the least significant day digit occupies bits 4-7 of the fourth octet. 
--  The most significant hours digit occupies bits 0-3 of the fifth octet,
--  and the least significant digit occupies bits 4-7 of the fifth octet. 
--  The most significant minutes digit occupies bits 0-3 of the sixth octet,
--  and the least significant digit occupies bits 4-7 of the sixth octet. 
--  The most significant seconds digit occupies bits 0-3 of the seventh octet,
--  and the least seconds significant digit occupies bits 4-7 of the seventh octet. 
--  For the encoding of digits in an octet, refer to the timeAndtimezone parameter.

DestinationRoutingAddress {PARAMETERS-BOUND : bound} ::= SEQUENCE SIZE(1) OF
													CalledPartyNumber {bound}
-- Indicates the Called Party Number.

Digits {PARAMETERS-BOUND : bound} 	::= OCTET STRING (SIZE(
	bound.&minDigitsLength .. bound.&maxDigitsLength))
-- Indicates the address signalling digits. 
-- Refer to ETS 300 356-1 [8] Generic Number & Generic Digits parameters for encoding.
-- The coding of the subfields 'NumberQualifier' in Generic Number and 'TypeOfDigits' in
-- Generic Digits are irrelevant to the CAP;
-- the ASN.1 tags are sufficient to identify the parameter.
-- The ISUP format does not allow to exclude these subfields,
-- therefore the value is network operator specific.
-- The following parameters should use Generic Number:
-- AdditionalCallingPartyNumber for InitialDP
-- AssistingSSPIPRoutingAddress for EstablishTemporaryConnection
-- CorrelationID for AssistRequestInstructions
-- CalledAddressValue for all occurrences, CallingAddressValue for all occurrences.
--
-- The following parameters should use Generic Digits:
-- CorrelationID in EstablishTemporaryConnection
-- number in VariablePart
-- digitsResponse in ReceivedInformationArg
-- In the digitsResponse the digits may also include the '*', '#', a, b , c and d digits
-- by using the IA5 character encoding scheme. If the BCD even or BCD odd encoding
-- scheme is used, the following encoding shall be applied for the non-decimal characters:
-- 1011 (*), 1100 (#).

-- Note that when CorrelationID is transported in Generic Digits, then the digits shall 
-- always be BCD encoded.

DpSpecificCriteria {PARAMETERS-BOUND : bound} 		::= CHOICE {
	applicationTimer		[1] ApplicationTimer
	}
--  The gsmSCF may set a timer in the gsmSSF for the No Answer event.
--  If the user does not answer the call within the allotted time,
--  the gsmSSF reports the event to the gsmSCF

ElapsedTime						::= CHOICE {
	timeGPRSIfNoTariffSwitch	[0] INTEGER (0..86400),
	timeGPRSIfTariffSwitch		[1] SEQUENCE {
		timeGPRSSinceLastTariffSwitch	[0] INTEGER (0..86400),
		timeGPRSTariffSwitchInterval	[1] INTEGER (0..86400)	OPTIONAL
		}
	}
--	timeGPRSIfNoTariffSwitch is measured in seconds
--	timeGPRSSinceLastTariffSwitch and timeGPRSTariffSwitchInterval are measured in seconds

ErrorTreatment 						::= ENUMERATED {
	stdErrorAndInfo			(0),
	help				(1),
	repeatPrompt			(2) 
	}
-- stdErrorAndInfomeans returning the "ImproperCallerResponse" error in the event of an error
-- condition during collection of user info.


EventSpecificInformationSMS		::= CHOICE {
	o-smsFailureSpecificInfo	[0] SEQUENCE {
		failureCause			[0] SMSCause		OPTIONAL,
		...
		},
	o-smsSubmittedSpecificInfo	[1] SEQUENCE {
		-- no specific info defined
		...
		}
	}


EventTypeSMS				::= ENUMERATED {
	sms-CollectedInfo			(1),
	o-smsFailure				(2),
	o-smsSubmitted				(3)
	}
-- Value sms-CollectedInfo can only be used for TDPs.

ExtensionField {PARAMETERS-BOUND : bound} ::= SEQUENCE {
	type		EXTENSION.&id ({SupportedExtensions {bound}}),
			-- shall identify the value of an EXTENSION type
	criticality	CriticalityType	DEFAULT ignore,
	value		[1] EXTENSION.&ExtensionType
			({SupportedExtensions {bound}}{@type}),
	...
	}
-- This parameter indicates an extension of an argument data type. 
-- Its content is network operator specific

ForwardServiceInteractionInd						 ::= SEQUENCE {
	conferenceTreatmentIndicator	[1] OCTET STRING (SIZE(1))			OPTIONAL,
	-- acceptConferenceRequest	'xxxx xx01'B
	-- rejectConferenceRequest	'xxxx xx10'B
	-- network default is accept conference request
	callDiversionTreatmentIndicator	[2] OCTET STRING (SIZE(1))		OPTIONAL,
	-- callDiversionAllowed		'xxxx xx01'B
	-- callDiversionNotAllowed	'xxxx xx10'B
	-- network default is Call Diversion allowed
	callingPartyRestrictionIndicator [4] OCTET STRING (SIZE(1))		OPTIONAL,
	-- noINImpact				'xxxx xx01'B
	-- presentationRestricted	'xxxx xx10'B
	-- network default is noINImpact
...
	}

GapCriteria {PARAMETERS-BOUND : bound}::= CHOICE {
	basicGapCriteria			BasicGapCriteria {bound},
	compoundGapCriteria			CompoundCriteria {bound}
	}

GapIndicators 											::= SEQUENCE {
	duration					[0] Duration,
	gapInterval					[1] Interval,
	...
	}
-- Indicates the gapping characteristics. 
-- No gapping when gapInterval equals 0.

GapOnService 											::= SEQUENCE {
	serviceKey					[0] ServiceKey,
	...
	}

GapTreatment {PARAMETERS-BOUND : bound} 				::= CHOICE {
	informationToSend			[0] InformationToSend {bound},
	releaseCause				[1] Cause {bound}
	}
-- The default value for Cause is the same as in ISUP.

GenericNumber {PARAMETERS-BOUND : bound} 			::= OCTET STRING (SIZE(
	bound.&minGenericNumberLength .. bound.&maxGenericNumberLength))
--  Indicates a generic number. Refer to ETS 300 356-1 [8] Generic number for encoding.

GenericNumbers {PARAMETERS-BOUND : bound} 			::= SET SIZE(1..bound.&numOfGenericNumbers) OF GenericNumber {bound}

GPRS-QoS									::=	CHOICE {
	short-QoS-format						[0]	QoS-Subscribed,
	long-QoS-format							[1]	Ext-QoS-Subscribed
	}
-- Short-QoS-format shall be sent for QoS in pre GSM release 99 format.
-- Long-QoS-format shall be sent for QoS in GSM release 99 (and beyond) format.
-- Which of the two QoS formats shall be sent is determined by which QoS
-- format is available in the SGSN at the time of sending.
-- Refer to 3GPP TS 29.002 [13] for encoding details of QoS-Subscribed and
-- Ext-QoS-Subscribed.

GPRSCause {PARAMETERS-BOUND : bound} 			::= OCTET STRING (SIZE
			(bound.&minGPRSCauseLength .. bound.&maxGPRSCauseLength))
-- Shall only include the cause value.

--	00000000   Unspecified
--  All other values shall be interpreted as "Unspecified".
--
-- This parameter indicates the cause for CAP interface related information. 
-- The GPRSCause mapping to/from GTP cause values specified in the 3GPP TS 29.060 and 
-- to/from 3GPP TS 24.008 GMM cause and SM cause values are outside scope of this document.


GPRSChargingID							::= OCTET STRING (SIZE (4))
--	The Charging ID is a unique four octet value generated by the GGSN when 
--- a PDP Context is activated. A Charging ID is generated for each activated context.

GPRSEvent							::= SEQUENCE {
	gPRSEventType						[0] GPRSEventType,
	monitorMode							[1] MonitorMode
	}
--  Indicates the GPRS event information for monitoring.

GPRSEventSpecificInformation {PARAMETERS-BOUND : bound}					::= CHOICE {

	attachChangeOfPositionSpecificInformation 
										[0] SEQUENCE {
			locationInformationGPRS 		[0] LocationInformationGPRS	OPTIONAL,
			...
			},

	pdp-ContextchangeOfPositionSpecificInformation
									 	[1] SEQUENCE {
			accessPointName					[0]	AccessPointName {bound}	OPTIONAL,
			chargingID						[1]	GPRSChargingID			OPTIONAL,
			locationInformationGPRS 		[2] LocationInformationGPRS OPTIONAL,
			pDPType							[3]	PDPType					OPTIONAL,
			qualityOfService				[4]	QualityOfService		OPTIONAL,
			timeAndTimeZone					[5]	TimeAndTimeZone			OPTIONAL,
			...,
			gGSNAddress						[6]	GSN-Address				OPTIONAL
			},

	detachSpecificInformation 			[2] SEQUENCE {
			inititatingEntity 				[0] InitiatingEntity		OPTIONAL,
			...
			},

	disconnectSpecificInformation 		[3] SEQUENCE {
			inititatingEntity 				[0] InitiatingEntity		OPTIONAL,
			...
			},

	pDPContextEstablishmentSpecificInformation
										[4]	SEQUENCE {
			accessPointName					[0]	AccessPointName {bound}	OPTIONAL,
			pDPType							[1]	PDPType					OPTIONAL,
			qualityOfService				[2]	QualityOfService		OPTIONAL,
			locationInformationGPRS 		[3] LocationInformationGPRS OPTIONAL,
			timeAndTimeZone					[4]	TimeAndTimeZone			OPTIONAL,
			pDPInitiationType				[5] PDPInitiationType		OPTIONAL,
			...
			},

	pDPContextEstablishmentAcknowledgementSpecificInformation
										[5]	SEQUENCE {
			accessPointName					[0]	AccessPointName {bound}	OPTIONAL,
			chargingID						[1] GPRSChargingID			OPTIONAL,
			pDPType							[2]	PDPType					OPTIONAL,
			qualityOfService				[3]	QualityOfService		OPTIONAL,
			locationInformationGPRS 		[4] LocationInformationGPRS OPTIONAL,
			timeAndTimeZone					[5]	TimeAndTimeZone			OPTIONAL,
			...,
			gGSNAddress						[6]	GSN-Address				OPTIONAL
			}
		}

PDPinitiationType							::= ENUMERATED {
	mSInitiated								(0),
	networkInitiated						(1)
		}

GPRSEventType 								::= ENUMERATED {
	attach									(1),
	attachChangeOfPosition					(2),
	detached								(3),
	pdp-ContextEstablishment				(11),
	pdp-ContextEstablishmentAcknowledgement	(12),
	disonnect								(13),
	pdp-ContextChangeOfPosition				(14)
	}

GPRSMSClass									::= SEQUENCE {
	mSNetworkCapability					[0]	MSNetworkCapability,
	mSRadioAccessCapability				[1]	MSRadioAccessCapability
	}
-- GPRS MS class mark describes the terminal capabilites.
-- For encoding refer to 3GPP TS 24.008 [12].

InbandInfo {PARAMETERS-BOUND : bound} 				::= SEQUENCE {
	messageID				[0] MessageID {bound},
	numberOfRepetitions		[1] INTEGER (1..127)							OPTIONAL,
	duration				[2] INTEGER (0..32767)							OPTIONAL,
	interval				[3] INTEGER (0.. 32767)							OPTIONAL,
...
	}
-- Interval is the time in seconds between each repeated announcement. Duration is the total
-- amount of time in seconds, including repetitions and intervals.
-- The end of announcement is either the end of duration or numberOfRepetitions, 
-- whatever comes first.
-- duration with value 0 indicates infinite duration

InformationToSend {PARAMETERS-BOUND : bound} 		::= CHOICE {
	inbandInfo				[0] InbandInfo {bound},
	tone					[1] Tone
	}

InitiatingEntity 					::= ENUMERATED {
	mobileStation					(0),
	sgsn							(1),
	hlr								(2),
	ggsn							(3)
	}

-- InvokeID		::= TCInvokeIdSet

IPRoutingAddress {PARAMETERS-BOUND : bound} 			::= CalledPartyNumber {bound}
-- Indicates the routing address for the IP.

IPSSPCapabilities {PARAMETERS-BOUND : bound} 		::= OCTET STRING (SIZE(
	bound.&minIPSSPCapabilitiesLength .. bound.&maxIPSSPCapabilitiesLength))
--  Indicates the gsmSRF resources available. The parameter has two parts, a standard and a 
--  bilateral part. The standard part indicates capabilities defined as optional in CAP V.2 
--  that shall be recognised (but not necessarily supported) by a CAP V.2 gsmSCF. The bilateral 
--  part contains further information that is not specified in this standard, but which is set 
--  according to bilateral agreements between network operators and/or equipment vendors.
--  The last octet of the standard part is indicated by bit 7 being set to 0, otherwise Bit 7 of 
--  a standard part octet is set to 1 indicating that the standard part continues in the following 
--  octet. Coding is as follows:

--  Octet 1					Standard Part for CAP V.3
--  Bit	Value				Meaning
--  0	0					IPRoutingAddress not supported
--		1					IPRoutingAddress supported
--  1	0					VoiceBack not supported
--		1					VoiceBack supported
--  2	0					VoiceInformation not supported, via speech recognition
--  	1					VoiceInformation supported, via speech recognition
--  3	0					VoiceInformation not supported, via voice recognition
--		1					VoiceInformation supported, via voice recognition
--  4	0					Generation of voice announcements from Text not supported
--		1					Generation of voice announcements from Text supported
--  5	-					Reserved
--  6	-					Reserved
--  7	0					End of standard part
--   	1					This value is reserved in CAP V.3
--
--  Octets 2 to 4			Bilateral Part: Network operator / equipment vendor specific


LegType 											::= OCTET STRING (SIZE(1))
leg1 LegType 										::= '01'H
leg2 LegType 										::= '02'H

LocationInformationGPRS		::= SEQUENCE {
	cellGlobalIdOrServiceAreaIdOrLAI	[0] OCTET STRING (SIZE(5..7))	OPTIONAL,
	routeingAreaIdentity				[1] RAIdentity					OPTIONAL,
	geographicalInformation			[2] OCTET STRING (SIZE (8))		OPTIONAL,
	sgsn-Number							[3] ISDN-AddressString			OPTIONAL,
	selectedLSAIdentity					[4] LSAIdentity					OPTIONAL,
	extensionContainer					[5] ExtensionContainer			OPTIONAL,
	...,
	sai-Present							[6] NULL						OPTIONAL 
}
-- CellGlobalIdOrServiceAreaIdOrLAI and LSAIdentity are coded in accordance with
-- 3GPP TS 29.002 [13].
-- GeographicalInformation refers to geographical Information as defined
-- in 3GPP TS 23.032 [44].
-- sai-Present indicates that the cellGlobalIdOrServiceAreaIdOrLAI parameter contains
-- a Service Area Identity.

LocationNumber {PARAMETERS-BOUND : bound} 			::= OCTET STRING (SIZE (
	bound.&minLocationNumberLength .. bound.&maxLocationNumberLength))
-- Indicates the Location Number for the calling party. 
-- Refer to ETS 300 356-1 [8] for encoding.

MessageID {PARAMETERS-BOUND : bound} 				::= CHOICE {
	elementaryMessageID		[0] Integer4,
	text					[1] SEQUENCE {
		messageContent			[0] IA5String (SIZE(
			bound.&minMessageContentLength .. bound.&maxMessageContentLength)),
		attributes				[1] OCTET STRING (SIZE(
			bound.&minAttributesLength .. bound.&maxAttributesLength)) OPTIONAL
	},
	elementaryMessageIDs	[29] SEQUENCE SIZE (1.. bound.&numOfMessageIDs) OF Integer4,
	variableMessage			[30] SEQUENCE {
		elementaryMessageID		[0] Integer4,
		variableParts			[1] SEQUENCE SIZE (1..5) OF VariablePart {bound}
		}
	}
-- Use of the text parameter is network operator/equipment vendor specific.

MonitorMode	 										::= ENUMERATED {
	interrupted					(0),
	notifyAndContinue			(1),
	transparent					(2)
	}
-- Indicates the event is relayed and/or processed by the SSP.
-- Transparent means that the gsmSSF or gprsSSF does not notify the gsmSCF of the event. 
-- For the use of this parameter refer to the procedure descriptions in clause 11.

MSNetworkCapability								::= OCTET STRING (SIZE (3))
--	MS Network Capability describes the GPRS terminal capabilites related to the network, i.e. SMS
--	point to point service over packet data channels. For encoding refer to 3GPP TS 24.008 [12].

MSRadioAccessCapability					::= OCTET STRING (SIZE (3..32))
-- MS Radio Access Capability describes the terminal capabilites relevant for the radio network, 
-- which may affect the way the network handles the mobile.
-- For encoding refer to 3GPP TS 24.008 [12].

NAOliInfo							::= OCTET STRING (SIZE (1))
--  NA Oli information takes the same value as defined in ANSI ISUP T1.113 [53]
--  e.g.	 '3D'H  – Decimal value 61 - Cellular Service (Type 1)
--			 '3E'H  – Decimal value 62 - Cellular Service (Type 2)
--			 '3F'H  – Decimal value 63 - Cellular Service (roaming)

OriginalCalledPartyID {PARAMETERS-BOUND : bound}				::= OCTET STRING (SIZE(
	bound.&minOriginalCalledPartyIDLength .. bound.&maxOriginalCalledPartyIDLength))

--  Indicates the original called number. Refer to ETS 300 356-1 [8] Original Called Number 
--  for encoding.

OCSIApplicable 									::= NULL
--  Indicates that the Originating CAMEL Subscription Information, if present, shall be 
--  applied on the outgoing call leg created with a Connect operation. For the use of this 
--  parameter see 3GPP TS 23.078 [42].

PDPID										::= OCTET STRING (SIZE (1))
--	PDP Identifier is a counter used to identify a specific PDP Context within a control
--	relationship between gprsSSF and gsmSCF.

PDPType	{PARAMETERS-BOUND: bound}			::= SEQUENCE {
	pDPTypeOrganization						[0] OCTET STRING (SIZE(1)),
	pDPTypeNumber							[1] OCTET STRING (SIZE(1)),
	pDPAddress								[2] OCTET STRING (SIZE(
		bound.&minPDPAddressLength .. bound.&maxPDPAddressLength))	OPTIONAL
	}
-- Indicates the PDPType, refer to 3GPP TS 29.060 for the encoding.
-- The pDPTypeOrganization shall use the least significant 4 bits of the octet encoded. 
-- The sender of this parameter shall set the most significant 4 bit of the octet to 0. 
-- The receiver of this parameter shall ignore the most significant 4 bits of this octet.

QualityOfService							::=	SEQUENCE {
	requested-QoS							[0]	GPRS-QoS	OPTIONAL,
	subscribed-QoS							[1]	GPRS-QoS	OPTIONAL,
	negotiated-QoS							[2]	GPRS-QoS	OPTIONAL,
	...
	}
-- The procedure descriptions in chapter 11 indicate which one(s) of the
-- QoS variables shall be transported.

RAIdentity									::= OCTET STRING (SIZE (7))
--	Routing Area Identity coded according to 3GPP TS 29.060 [43].

ReceivingSideID						::= CHOICE {receivingSideID [1] LegType}

-- used to identify LegID in operations sent from gsmSSF to gsmSCF

RedirectingPartyID {PARAMETERS-BOUND : bound} 		::= OCTET STRING (SIZE (
	bound.&minRedirectingPartyIDLength .. bound.&maxRedirectingPartyIDLength))
-- Indicates redirecting number. 
-- Refer to ETS 300 356-1 [8] Redirecting number for encoding.

RequestedInformationList {PARAMETERS-BOUND : bound} 	::= SEQUENCE SIZE (1.. numOfInfoItems) OF RequestedInformation {bound}

RequestedInformationTypeList {PARAMETERS-BOUND : bound}	::= SEQUENCE SIZE (1.. numOfInfoItems) OF RequestedInformationType

RequestedInformation {PARAMETERS-BOUND : bound} 		::= SEQUENCE {
	requestedInformationType	[0] RequestedInformationType,
	requestedInformationValue	[1] RequestedInformationValue {bound},
...
	}

RequestedInformationType 							::= ENUMERATED {
	callAttemptElapsedTime		(0),
	callStopTime				(1),
	callConnectedElapsedTime	(2),
	releaseCause				(30)
	}

RequestedInformationValue {PARAMETERS-BOUND : bound} ::= CHOICE {
	callAttemptElapsedTimeValue		[0] INTEGER (0..255),
	callStopTimeValue				[1] DateAndTime,
	callConnectedElapsedTimeValue	[2] Integer4,
	releaseCauseValue				[30] Cause {bound}
	}
-- The callAttemptElapsedTimeValue is specified in seconds. The unit for the
-- callConnectedElapsedTimeValue is 100 milliseconds

RPCause				::= OCTET STRING (SIZE (1))
-- RP cause according to 3GPP TS 24.011 [45].
-- GsmSCF shall send this cause in the ReleaseSMS operation.
-- The received cause is sent to the originating MS by the VMSC/SGSN.

ScfID {PARAMETERS-BOUND : bound} 					::= OCTET STRING (SIZE(
	bound.&minScfIDLength .. bound.&maxScfIDLength))
-- defined by network operator.
-- Indicates the gsmSCF identity.

SCIBillingChargingCharacteristics {PARAMETERS-BOUND : bound} ::= OCTET STRING (SIZE (
	bound.&minSCIBillingChargingLength .. bound.&maxSCIBillingChargingLength))
	(CONSTRAINED BY {-- shall be the result of the BER-encoded value of type –-
	CAMEL-SCIBillingChargingCharacteristics})
-- Indicates AOC information to be sent to a Mobile Station
-- The violation of the UserDefinedConstraint shall be handled as an ASN.1 syntax error.

SCIGPRSBillingChargingCharacteristics {PARAMETERS-BOUND : bound} ::= OCTET STRING (SIZE (
	bound.&minSCIBillingChargingLength .. bound.&maxSCIBillingChargingLength))
	(CONSTRAINED BY {-- shall be the result of the BER-encoded value of type –
	CAMEL-SCIGPRSBillingChargingCharacteristics})
-- Indicates AOC information to be sent to a Mobile Station
-- The violation of the UserDefinedConstraint shall be handled as an ASN.1 syntax error.

SendingSideID						::= CHOICE {sendingSideID [0] LegType}
-- used to identify LegID in operations sent from gsmSCF to gsmSSF

ServiceInteractionIndicatorsTwo 						::= SEQUENCE {
	forwardServiceInteractionInd		[0]	ForwardServiceInteractionInd		OPTIONAL,
	-- applicable to operations IDP, CON, CWA.
	backwardServiceInteractionInd		[1]	BackwardServiceInteractionInd		OPTIONAL,
	-- applicable to operations IDP, CON, CWA.
	bothwayThroughConnectionInd			[2] BothwayThroughConnectionInd			OPTIONAL,
	connectedNumberTreatmentInd			[4]	ConnectedNumberTreatmentInd			OPTIONAL,
	nonCUGCall							[13] NULL									OPTIONAL,
	-- applicable to CON and CWA
	-- indicates that no parameters for CUG shall be used for the call (i.e. the call shall 
	-- be a non-CUG call). 
	-- If not present, it indicates one of three things:
	--  a) continue with modified CUG information (when one or more of either CUG Interlock Code 
	--     and Outgoing Access Indicator are present), or
	--  b) continue with original CUG information (when neither CUG Interlock Code or Outgoing 
	--     Access Indicator are present), i.e. no IN impact.
	--  c) continue with the original non-CUG call.
	holdTreatmentIndicator				[50] OCTET STRING (SIZE(1))				OPTIONAL,
	-- acceptHoldRequest	'xxxx xx01'B
	-- rejectHoldRequest	'xxxx xx10'B
	-- network default is accept hold request
	cwTreatmentIndicator				[51] OCTET STRING (SIZE(1))			OPTIONAL,
	-- acceptCw	'xxxx xx01'B
	-- rejectCw	'xxxx xx10'B
	-- network default is accept cw
	ectTreatmentIndicator				[52] OCTET STRING (SIZE(1))			OPTIONAL,
	-- acceptEctRequest	'xxxx xx01'B
	-- rejectEctRequest	'xxxx xx10'B
	-- network default is accept ect request
	...
	}

SGSNCapabilities							::= OCTET STRING (SIZE (1))

--  Indicates the SGSN capabilities. The coding of the parameter is as follows:
--  Bit	Value				Meaning
--  0	0					AoC not supported by SGSN
--		1					AoC supported by SGSN 
--  1	-					This bit is reserved in CAP V.3
--  2	-					This bit is reserved in CAP V.3
--  3	-					This bit is reserved in CAP V.3
--  4	-					This bit is reserved in CAP V.3
--  5	-					This bit is reserved in CAP V.3
--  6	-					This bit is reserved in CAP V.3
--  7	-					This bit is reserved in CAP V.3

SMSCause	::= ENUMERATED {
	systemFailure				(0),
	unexpectedDataValue 		(1),
	facilityNotSupported		(2),
	sM-DeliveryFailure 			(3),
	releaseFromRadioInterface	(4)
	}
-- MO SMS error values which are reported to gsmSCF.
-- Most of these values are received from the SMSC as a response to 
-- MO-ForwardSM operation.

SMSEvent							::= SEQUENCE {
	eventTypeSMS						[0] EventTypeSMS,
	monitorMode							[1] MonitorMode
	}

TimeInformation						::= CHOICE {
 	timeIfNoTariffSwitch				[0] TimeIfNoTariffSwitch,
 	timeIfTariffSwitch					[1] TimeIfTariffSwitch
	}
-- Indicates call duration information

TimeIfNoTariffSwitch				::= INTEGER(0..864000)
-- TimeIfNoTariffSwitch is measured in 100 millisecond intervals

TimeIfTariffSwitch					::= SEQUENCE {
 	timeSinceTariffSwitch				[0] INTEGER(0..864000),
 	tariffSwitchInterval				[1] INTEGER(1..864000)						OPTIONAL
	}
-- timeSinceTariffSwitch and tariffSwitchInterval are measured in 100 millisecond intervals

TimerID 							::= ENUMERATED {
	tssf								(0)
	}
-- Indicates the timer to be reset.

TimerValue 							::= Integer4
-- Indicates the timer value (in seconds).

TimeAndTimezone {PARAMETERS-BOUND : bound}::= OCTET STRING (SIZE(
	bound.&minTimeAndTimezoneLength .. bound.&maxTimeAndTimezoneLength))
--  Indicates the time and timezone, relative to GMT. This parameter BCD encoded. 
--  The year digit indicating millenium occupies bits 0-3 of the first octet, and the year 
--  digit indicating century occupies bits 4-7 of the first octet. 
--  The year digit indicating decade occupies bits 0-3 of the second octet, whilst the digit 
--  indicating the year within the decade occupies bits 4-7 of the second octet. 
--  The most significant month digit occupies bits 0-3 of the third octet, and the least 
--  significant month digit occupies bits 4-7 of the third octet. 
--  The most significant day digit occupies bits 0-3 of the fourth octet, and the least 
--  significant day digit occupies bits 4-7 of the fourth octet. 
--  The most significant hours digit occupies bits 0-3 of the fifth octet, and the least 
--  significant hours digit occupies bits 4-7 of the fifth octet. 
--  The most significant minutes digit occupies bits 0-3 of the sixth octet, and the least 
--  significant minutes digit occupies bits 4-7 of the sixth octet. 
--  The most significant seconds digit occupies bits 0-3 of the seventh octet, and the least 
--  significant seconds digit occupies bits 4-7 of the seventh octet.
--
--  The timezone information occupies the eigth octet. For the encoding of Timezone refer to 
--  Reference [29], 3GPP TS 23.040 [46].
--
--  The BCD digits are packed and encoded as follows:
--
--  Bit	 7  6  5   4  |  3  2  1  0 
--       2nd digit    | 1st digit          Octet 1
--       3rd digit    | 4th digit          Octet 2
--             	         ..                   ..
--       nth digit    | n-1th digit        Octet m
--
--       0000       digit 0
--       0001       digit 1
--       0010       digit 2
--       0011       digit 3
--       0100       digit 4
--       0101       digit 5
--       0110       digit 6
--       0111       digit 7
--       1000       digit 8
--       1001       digit 9
--       1010       spare
--       1011       spare
--       1100       spare
--       1101       spare
--       1110       spare
--       1101       spare
--
-- where the leftmost bit of the digit is either bit 7 or bit 3 of the octet.

Tone 										::= SEQUENCE {
	toneID				[0] Integer4,
	duration			[1] Integer4			OPTIONAL,
...
	}
-- The duration specifies the length of the tone in seconds, value 0 indicates infinite duration.

TPDataCodingScheme					::= OCTET STRING (SIZE (1))
-- TP Data Coding Scheme according to 3GPP TS 23.040 [46]

TPProtocolIdentifier				::= OCTET STRING (SIZE (1))
-- indicates the protocol used above SM-Transfer Layer as specified in 3GPP TS 23.040 [46].

TPShortMessageSubmissionInfo		::= OCTET STRING (SIZE (1))
-- contains the 1st octect of the SMS-SUBMIT TPDU as specified in 3GPP TS 23.040 [46].

TPValidityPeriod					::= OCTET STRING (SIZE (1..7))
-- indicates the length of the validity period or the absolute time of the validity 
-- period termination as specified in 3GPP TS 23.040 [46].
-- the length of ValidityPeriod is either 1 octet or 7 octets

TransferredVolume					::= CHOICE {
	volumeIfNoTariffSwitch		[0] INTEGER (0..4294967295),
	volumeIfTariffSwitch [1] SEQUENCE {
		volumeSinceLastTariffSwitch		[0]	INTEGER (0..4294967295),
		volumeTariffSwitchInterval		[1]	INTEGER (0..4294967295)	OPTIONAL
		}
	}
--	volumeIfNoTariffSwitch, volumeSinceLastTariffSwitch and volumeTariffSwitchInterval
--	are measured in bytes.

UnavailableNetworkResource ::= ENUMERATED {
	unavailableResources			(0),
	componentFailure				(1),
	basicCallProcessingException	(2),
	resourceStatusFailure			(3),
	endUserFailure					(4)
	}
-- Indicates the network resource that failed.

VariablePart {PARAMETERS-BOUND : bound} 					::= CHOICE {
	integer				[0] Integer4,
	number				[1] Digits {bound},	-- Generic digits
	time				[2] OCTET STRING (SIZE(2)),	-- HH: MM, BCD coded
	date				[3] OCTET STRING (SIZE(4)),	-- YYYYMMDD, BCD coded
	price				[4] OCTET STRING (SIZE(4))
	}
--  Indicates the variable part of the message. Time is BCD encoded. 
--  The most significant hours digit occupies bits 0-3 of the first octet, and the least 
--  significant digit occupies bits 4-7 of the first octet. The most significant minutes digit 
--  occupies bits 0-3 of the second octet, and the least significant digit occupies bits 4-7 
--  of the second octet. 
--
--  Date is BCD encoded. The year digit indicating millenium occupies bits 0-3 of the first octet, 
--  and the year digit indicating century occupies bits 4-7 of the first octet. The year digit 
--  indicating decade occupies bits 0-3 of the second octet, whilst the digit indicating the year 
--  within the decade occupies bits 4-7 of the second octet.
--  The most significant month digit occupies bits 0-3 of the third octet, and the least 
--  significant month digit occupies bits 4-7 of the third octet. The most significant day digit 
--  occupies bits 0-3 of the fourth octet, and the least significant day digit occupies bits 4-7 
--  of the fourth octet.
--  Price is BCD encoded. The digit indicating hundreds of thousands occupies bits 0-3 of the 
--  first octet, and the digit indicating tens of thousands occupies bits 4-7 of the first octet.
--  The digit indicating thousands occupies bits 0-3 of the second octet, whilst the digit 
--  indicating hundreds occupies bits 4-7 of the second octet. The digit indicating tens occupies 
--  bits 0-3 of the third octet, and the digit indicating 0 to 9 occupies bits 4-7 of the third 
--  octet. The tenths digit occupies bits 0-3 of the fourth octet, and the hundredths digit 
--  occupies bits 4-7 of the fourth octet.
--
--  For the encoding of digits in an octet, refer to the timeAndtimezone parameter

-- The Definition of range of constants follows
numOfInfoItems INTEGER ::= 4

END
