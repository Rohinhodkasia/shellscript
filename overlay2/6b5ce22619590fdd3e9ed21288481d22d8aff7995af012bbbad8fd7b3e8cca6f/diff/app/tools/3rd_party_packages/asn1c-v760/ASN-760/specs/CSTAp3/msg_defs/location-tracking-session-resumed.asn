CSTA-location-tracking-session-resumed
	{ iso( 1) identified-organization( 3) icd-ecma( 12)
		standard( 0) csta3( 285) location-tracking-session-resumed ( 532) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
LocCrossRefID, LocReason FROM CSTA-device-feature-types
	{ iso( 1) identified-organization( 3) icd-ecma( 12)
		standard( 0) csta3( 285) device-feature-types( 127) };

locationTrackingSessionResumed OPERATION ::=
{ 	ARGUMENT		LocationTrackingSessionResumedArgument
	RESULT			LocationTrackingSessionResumedResult
	ERRORS			{universalFailure }
	CODE			local: 532}

LocationTrackingSessionResumedArgument ::= SEQUENCE
{	locCrossRefID			LocCrossRefID,	
	locReason			LocReason				OPTIONAL,
	extensions			CSTACommonArguments			OPTIONAL }

LocationTrackingSessionResumedResult ::= SEQUENCE 
{	extensions			CSTACommonArguments			OPTIONAL }

END -- of CSTA-location-tracking-session-resumed
