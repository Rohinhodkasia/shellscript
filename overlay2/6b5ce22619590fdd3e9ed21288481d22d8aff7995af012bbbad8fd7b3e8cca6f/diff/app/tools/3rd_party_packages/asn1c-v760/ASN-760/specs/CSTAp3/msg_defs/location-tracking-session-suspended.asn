CSTA-location-tracking-session-suspended
	{ iso( 1) identified-organization( 3) icd-ecma( 12)
		standard( 0) csta3( 285) location-tracking-session-suspended( 533) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
LocCrossRefID, LocReason FROM CSTA-device-feature-types
	{ iso( 1) identified-organization( 3) icd-ecma( 12)
		standard( 0) csta3( 285) device-feature-types( 127) }
LocationInfoList FROM CSTA-call-control
	{ iso( 1) identified-organization( 3) icd-ecma( 12)
		standard( 0) csta3( 285) call-control( 130) };

locationTrackingSessionSuspended OPERATION ::=
{ 	ARGUMENT		LocationTrackingSessionSuspendedArgument
	RESULT			LocationTrackingSessionSuspendedResult
	ERRORS			{universalFailure }
	CODE			local: 533}

LocationTrackingSessionSuspendedArgument ::= SEQUENCE
{	locCrossRefID			LocCrossRefID,
	locReason			LocReason				OPTIONAL,
	locationInfoList		LocationInfoList			OPTIONAL,
	extensions			CSTACommonArguments			OPTIONAL }

LocationTrackingSessionSuspendedResult ::= SEQUENCE 
{	extensions			CSTACommonArguments			OPTIONAL }

END -- of CSTA-location-tracking-session-suspended
