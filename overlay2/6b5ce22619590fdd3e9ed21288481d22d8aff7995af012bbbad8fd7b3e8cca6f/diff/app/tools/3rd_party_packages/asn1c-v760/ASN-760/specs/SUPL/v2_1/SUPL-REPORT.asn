-- This file was generated by the Objective Systems ASN1C Compiler
-- (http://www.obj-sys.com).  Version: 6.8.A, Date: 15-Nov-2014.

SUPL-REPORT DEFINITIONS AUTOMATIC TAGS ::= BEGIN

IMPORTS

SETCapabilities
FROM SUPL-START 

Position, PosMethod, SessionID, Ver
FROM ULP-Components 

MultipleLocationIds, GNSSPosTechnology, GANSSSignals
FROM Ver2-ULP-Components 

maxGANSS
FROM ULP-Version-2-parameter-extensions 

Ver3-SUPL-REPORT-extension
FROM ULP-Version-3-message-extensions ;

-- Productions

SessionInformation ::= SEQUENCE {
   sessionID [0] SessionID,
   ...
}

SessionList ::= SEQUENCE (SIZE (1..maxnumSessions)) OF SessionInformation

GANSSSignalsDescription ::= SEQUENCE {
   ganssId [0] INTEGER (0..15),
   gANSSSignals [1] GANSSSignals,
   ...
}

GANSSsignalsInfo ::= SEQUENCE (SIZE (1..maxGANSS)) OF GANSSSignalsDescription

PositionData ::= SEQUENCE {
   position [0] Position,
   posMethod [1] PosMethod OPTIONAL,
   gnssPosTechnology [2] GNSSPosTechnology OPTIONAL,
   ganssSignalsInfo [3] GANSSsignalsInfo OPTIONAL,
   ...
}

ResultCode ::= ENUMERATED { outofradiocoverage(1), noposition(2), 
   nomeasurement(3), nopositionnomeasurement(4), outofmemory(5), 
   outofmemoryintermediatereporting(6), other(7), ... }

TimeStamp ::= CHOICE {
   absoluteTime [0] UTCTime,
   relativeTime [1] INTEGER (0..31536000)
}

ReportData ::= SEQUENCE {
   positionData [0] PositionData OPTIONAL,
   multipleLocationIds [1] MultipleLocationIds OPTIONAL,
   resultCode [2] ResultCode OPTIONAL,
   timestamp [3] TimeStamp OPTIONAL,
   ...
}

ReportDataList ::= SEQUENCE (SIZE (1..1024)) OF ReportData

Ver2-SUPLREPORT ::= SEQUENCE {
   sessionList [0] SessionList OPTIONAL,
   sETCapabilities [1] SETCapabilities OPTIONAL,
   reportDataList [2] ReportDataList OPTIONAL,
   ver [3] Ver OPTIONAL,
   moreComponents [4] NULL OPTIONAL,
   ...,
   ver3-SUPL-REPORT-extension [5] Ver3-SUPL-REPORT-extension OPTIONAL
}

-- Value assignments

maxnumSessions INTEGER ::= 64


END
