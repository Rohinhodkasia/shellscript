-- This file was generated by the Objective Systems ASN1C Compiler
-- (http://www.obj-sys.com).  Version: 6.8.A, Date: 15-Nov-2014.

Ver2-ULP-Components DEFINITIONS AUTOMATIC TAGS ::= BEGIN

IMPORTS

LocationId, PrimaryCPICH-Info, CellParametersID, FQDN
FROM ULP-Components ;

-- Productions

SupportedWLANInfo ::= SEQUENCE {
   apTP [0] BOOLEAN,
   apAG [1] BOOLEAN,
   apSN [2] BOOLEAN,
   apDevType [3] BOOLEAN,
   apRSSI [4] BOOLEAN,
   apChanFreq [5] BOOLEAN,
   apRTD [6] BOOLEAN,
   setTP [7] BOOLEAN,
   setAG [8] BOOLEAN,
   setSN [9] BOOLEAN,
   setRSSI [10] BOOLEAN,
   apRepLoc [11] BOOLEAN,
   ...
}

SupportedWLANApData ::= SEQUENCE {
   apMACAddress [0] BIT STRING  (SIZE (48)),
   apDevType [1] ENUMERATED { wlan802-11a(0), wlan802-11b(1), wlan802-11g(2)
      , ... },
   ...
}

SupportedWLANApsChannel11a ::= SEQUENCE {
   ch34 [0] BOOLEAN,
   ch36 [1] BOOLEAN,
   ch38 [2] BOOLEAN,
   ch40 [3] BOOLEAN,
   ch42 [4] BOOLEAN,
   ch44 [5] BOOLEAN,
   ch46 [6] BOOLEAN,
   ch48 [7] BOOLEAN,
   ch52 [8] BOOLEAN,
   ch56 [9] BOOLEAN,
   ch60 [10] BOOLEAN,
   ch64 [11] BOOLEAN,
   ch149 [12] BOOLEAN,
   ch153 [13] BOOLEAN,
   ch157 [14] BOOLEAN,
   ch161 [15] BOOLEAN
}

SupportedWLANApsChannel11bg ::= SEQUENCE {
   ch1 [0] BOOLEAN,
   ch2 [1] BOOLEAN,
   ch3 [2] BOOLEAN,
   ch4 [3] BOOLEAN,
   ch5 [4] BOOLEAN,
   ch6 [5] BOOLEAN,
   ch7 [6] BOOLEAN,
   ch8 [7] BOOLEAN,
   ch9 [8] BOOLEAN,
   ch10 [9] BOOLEAN,
   ch11 [10] BOOLEAN,
   ch12 [11] BOOLEAN,
   ch13 [12] BOOLEAN,
   ch14 [13] BOOLEAN
}

SupportedWLANApsList ::= SEQUENCE {
   supportedWLANApDataList [0] SEQUENCE (SIZE (1..maxWLANApDataSize)) OF SupportedWLANApData,
   supportedWLANapsChannel11a [1] SupportedWLANApsChannel11a OPTIONAL,
   supportedWLANapsChannel11bg [2] SupportedWLANApsChannel11bg OPTIONAL,
   ...
}

SupportedWCDMAInfo ::= SEQUENCE {
   mRL [0] BOOLEAN,
   ...
}

SupportedNetworkInformation ::= SEQUENCE {
   wLAN [0] BOOLEAN,
   supportedWLANInfo [1] SupportedWLANInfo OPTIONAL,
   supportedWLANApsList [2] SupportedWLANApsList OPTIONAL,
   gSM [3] BOOLEAN,
   wCDMA [4] BOOLEAN,
   supportedWCDMAInfo [5] SupportedWCDMAInfo OPTIONAL,
   cDMA [6] BOOLEAN,
   hRDP [7] BOOLEAN,
   uMB [8] BOOLEAN,
   lTE [9] BOOLEAN,
   wIMAX [10] BOOLEAN,
   historic [11] BOOLEAN,
   nonServing [12] BOOLEAN,
   uTRANGPSReferenceTime [13] BOOLEAN,
   uTRANGANSSReferenceTime [14] BOOLEAN,
   ...
}

GNSSPosTechnology ::= SEQUENCE {
   gps [0] BOOLEAN,
   galileo [1] BOOLEAN,
   sbas [2] BOOLEAN,
   modernized-gps [3] BOOLEAN,
   qzss [4] BOOLEAN,
   glonass [5] BOOLEAN,
   ...,
   bds [6] BOOLEAN OPTIONAL
}

GANSSSignals ::= BIT STRING  { signal1(0), signal2(1), signal3(2), signal4(3), 
   signal5(4), signal6(5), signal7(6), signal8(7) } (SIZE (1..8))

RepMode ::= SEQUENCE {
   realtime [0] BOOLEAN,
   quasirealtime [1] BOOLEAN,
   batch [2] BOOLEAN,
   ...
}

BatchRepCap ::= SEQUENCE {
   report-position [0] BOOLEAN,
   report-measurements [1] BOOLEAN,
   max-num-positions [2] INTEGER (1..1024) OPTIONAL,
   max-num-measurements [3] INTEGER (1..1024) OPTIONAL,
   ...
}

ReportingCap ::= SEQUENCE {
   minInt [0] INTEGER (1..3600),
   maxInt [1] INTEGER (1..1440) OPTIONAL,
   repMode [2] RepMode,
   batchRepCap [3] BatchRepCap OPTIONAL,
   ...
}

HrpdCellInformation ::= SEQUENCE {
   refSECTORID [0] BIT STRING  (SIZE (128)) OPTIONAL,
   refBASELAT [1] INTEGER (0..4194303),
   reBASELONG [2] INTEGER (0..8388607),
   refWeekNumber [3] INTEGER (0..65535),
   refSeconds [4] INTEGER (0..4194303),
   ...
}

UmbCellInformation ::= SEQUENCE {
   refSECTORID [0] BIT STRING  (SIZE (128)),
   refMCC [1] INTEGER (0..999),
   refMNC [2] INTEGER (0..999),
   refBASELAT [3] INTEGER (0..4194303),
   reBASELONG [4] INTEGER (0..8388607),
   refWeekNumber [5] INTEGER (0..65535),
   refSeconds [6] INTEGER (0..4194303),
   ...
}

MCC-MNC-Digit ::= INTEGER (0..9)

MCC ::= SEQUENCE (SIZE (3)) OF MCC-MNC-Digit

MNC ::= SEQUENCE (SIZE (2..3)) OF MCC-MNC-Digit

PLMN-Identity ::= SEQUENCE {
   mcc [0] MCC OPTIONAL,
   mnc [1] MNC
}

CellIdentity ::= BIT STRING  (SIZE (28))

CellGlobalIdEUTRA ::= SEQUENCE {
   plmn-Identity [0] PLMN-Identity,
   cellIdentity [1] CellIdentity,
   ...
}

PhysCellId ::= INTEGER (0..503)

TrackingAreaCode ::= BIT STRING  (SIZE (16))

RSRP-Range ::= INTEGER (0..97)

RSRQ-Range ::= INTEGER (0..34)

MeasResultEUTRA ::= SEQUENCE {
   physCellId [0] PhysCellId,
   cgi-Info [1] SEQUENCE {
      cellGlobalId [0] CellGlobalIdEUTRA,
      trackingAreaCode [1] TrackingAreaCode
   } OPTIONAL,
   measResult [2] SEQUENCE {
      rsrpResult [0] RSRP-Range OPTIONAL,
      rsrqResult [1] RSRQ-Range OPTIONAL,
      ...,
      earfcn [2] INTEGER (0..65535) OPTIONAL,
      earfcn-ext [3] INTEGER (65536..262143) OPTIONAL
   }
}

MeasResultListEUTRA ::= SEQUENCE (SIZE (1..maxCellReport)) OF MeasResultEUTRA

LteCellInformation ::= SEQUENCE {
   cellGlobalIdEUTRA [0] CellGlobalIdEUTRA,
   physCellId [1] PhysCellId,
   trackingAreaCode [2] TrackingAreaCode,
   rsrpResult [3] RSRP-Range OPTIONAL,
   rsrqResult [4] RSRQ-Range OPTIONAL,
   tA [5] INTEGER (0..1282) OPTIONAL,
   measResultListEUTRA [6] MeasResultListEUTRA OPTIONAL,
   ...,
   earfcn [7] INTEGER (0..65535) OPTIONAL,
   earfcn-ext [8] INTEGER (65536..262143) OPTIONAL
}

RTDUnits ::= ENUMERATED { microseconds(0), hundredsofnanoseconds(1), 
   tensofnanoseconds(2), nanoseconds(3), tenthsofnanoseconds(4), ... }

RTD ::= SEQUENCE {
   rTDValue [0] INTEGER (0..16777216),
   rTDUnits [1] RTDUnits,
   rTDAccuracy [2] INTEGER (0..255) OPTIONAL,
   ...
}

LocationEncodingDescriptor ::= ENUMERATED { lCI(0), aSN1(1), ... }

LocationData ::= SEQUENCE {
   locationAccuracy [0] INTEGER (0..4294967295) OPTIONAL,
   locationValue [1] OCTET STRING (SIZE (1..128)),
   ...
}

ReportedLocation ::= SEQUENCE {
   locationEncodingDescriptor [0] LocationEncodingDescriptor,
   locationData [1] LocationData,
   ...
}

LocationDataLCI ::= SEQUENCE {
   latitudeResolution [0] BIT STRING  (SIZE (6)),
   latitude [1] BIT STRING  (SIZE (34)),
   longitudeResolution [2] BIT STRING  (SIZE (6)),
   longitude [3] BIT STRING  (SIZE (34)),
   altitudeType [4] BIT STRING  (SIZE (4)),
   altitudeResolution [5] BIT STRING  (SIZE (6)),
   altitude [6] BIT STRING  (SIZE (30)),
   datum [7] BIT STRING  (SIZE (8)),
   ...
}

LciLocData ::= SEQUENCE {
   locationDataLCI [0] LocationDataLCI OPTIONAL,
   ...
}

RepLocation ::= CHOICE {
   lciLocData [0] LciLocData,
   ...
}

WlanAPInformation ::= SEQUENCE {
   apMACAddress [0] BIT STRING  (SIZE (48)),
   apTransmitPower [1] INTEGER (-127..128) OPTIONAL,
   apAntennaGain [2] INTEGER (-127..128) OPTIONAL,
   apSignaltoNoise [3] INTEGER (-127..128) OPTIONAL,
   apDeviceType [4] ENUMERATED { wlan802-11a(0), wlan802-11b(1), wlan802-11g(2)
      , ..., wlan802-11n(3), wlan802-11ac(4), wlan802-11ad(5) } OPTIONAL,
   apSignalStrength [5] INTEGER (-127..128) OPTIONAL,
   apChannelFrequency [6] INTEGER (0..256) OPTIONAL,
   apRoundTripDelay [7] RTD OPTIONAL,
   setTransmitPower [8] INTEGER (-127..128) OPTIONAL,
   setAntennaGain [9] INTEGER (-127..128) OPTIONAL,
   setSignaltoNoise [10] INTEGER (-127..128) OPTIONAL,
   setSignalStrength [11] INTEGER (-127..128) OPTIONAL,
   apReportedLocation [12] ReportedLocation OPTIONAL,
   ...,
   apRepLocation [13] RepLocation OPTIONAL,
   apSignalStrengthDelta [14] INTEGER (0..1) OPTIONAL,
   apSignaltoNoiseDelta [15] INTEGER (0..1) OPTIONAL,
   setSignalStrengthDelta [16] INTEGER (0..1) OPTIONAL,
   setSignaltoNoiseDelta [17] INTEGER (0..1) OPTIONAL,
   operatingClass [18] INTEGER (0..255) OPTIONAL,
   apSSID [19] OCTET STRING (SIZE (1..32)) OPTIONAL,
   apPHYType [20] ENUMERATED { unknown(0), any(1), fhss(2), dsss(3), 
      irbaseband(4), ofdm(5), hrdsss(6), erp(7), ht(8), ihv(9), ... } OPTIONAL
      ,
   setMACAddress [21] BIT STRING  (SIZE (48)) OPTIONAL
}

WimaxBsID ::= SEQUENCE {
   bsID-MSB [0] BIT STRING  (SIZE (24)) OPTIONAL,
   bsID-LSB [1] BIT STRING  (SIZE (24)),
   ...
}

WimaxRTD ::= SEQUENCE {
   rTD [0] INTEGER (0..65535),
   rTDstd [1] INTEGER (0..1023) OPTIONAL,
   ...
}

WimaxNMR ::= SEQUENCE {
   wimaxBsID [0] WimaxBsID,
   relDelay [1] INTEGER (-32768..32767) OPTIONAL,
   relDelaystd [2] INTEGER (0..1023) OPTIONAL,
   rSSI [3] INTEGER (0..255) OPTIONAL,
   rSSIstd [4] INTEGER (0..63) OPTIONAL,
   bSTxPower [5] INTEGER (0..255) OPTIONAL,
   cINR [6] INTEGER (0..255) OPTIONAL,
   cINRstd [7] INTEGER (0..63) OPTIONAL,
   bSLocation [8] ReportedLocation OPTIONAL,
   ...
}

WimaxNMRList ::= SEQUENCE (SIZE (1..maxWimaxBSMeas)) OF WimaxNMR

WimaxBSInformation ::= SEQUENCE {
   wimaxBsID [0] WimaxBsID,
   wimaxRTD [1] WimaxRTD OPTIONAL,
   wimaxNMRList [2] WimaxNMRList OPTIONAL,
   ...
}

Ver2-CellInfo-extension ::= CHOICE {
   hrpdCell [0] HrpdCellInformation,
   umbCell [1] UmbCellInformation,
   lteCell [2] LteCellInformation,
   wlanAP [3] WlanAPInformation,
   wimaxBS [4] WimaxBSInformation,
   ...
}

RelativeTime ::= INTEGER (0..65535)

LocationIdData ::= SEQUENCE {
   locationId [0] LocationId,
   relativetimestamp [1] RelativeTime OPTIONAL,
   servingFlag [2] BOOLEAN,
   ...
}

MultipleLocationIds ::= SEQUENCE (SIZE (1..maxLidSize)) OF LocationIdData

ThirdPartyID ::= CHOICE {
   logicalName [0] IA5String (SIZE (1..1000)),
   msisdn [1] OCTET STRING (SIZE (8)),
   emailaddr [2] IA5String (SIZE (1..1000)),
   sip-uri [3] VisibleString (FROM ("a".."z" | "A".."Z" | "0".."9" | ":./-_~%#@?") ^ SIZE (1..255)),
   ims-public-identity [4] VisibleString (FROM ("a".."z" | "A".."Z" | "0".."9" | ":./-_~%#@?") ^ SIZE (1..255)),
   min [5] BIT STRING  (SIZE (34)),
   mdn [6] OCTET STRING (SIZE (8)),
   uri [7] VisibleString (FROM ("a".."z" | "A".."Z" | "0".."9" | "./-
_~%#") ^ SIZE (1..255)),
   ...
}

ThirdParty ::= SEQUENCE (SIZE (1..64)) OF ThirdPartyID

ApplicationID ::= SEQUENCE {
   appProvider [0] IA5String (SIZE (1..24)),
   appName [1] IA5String (SIZE (1..32)),
   appVersion [2] IA5String (SIZE (1..8)) OPTIONAL,
   ...
}

SPCSETKey ::= BIT STRING  (SIZE (128))

SPCTID ::= SEQUENCE {
   rAND [0] BIT STRING  (SIZE (128)),
   slpFQDN [1] FQDN,
   ...
}

SPCSETKeylifetime ::= INTEGER (1..24)

UTRAN-GPSReferenceTime ::= SEQUENCE {
   utran-GPSTimingOfCell [0] SEQUENCE {
      ms-part [0] INTEGER (0..1023),
      ls-part [1] INTEGER (0..4294967295)
   },
   modeSpecificInfo [1] CHOICE {
      fdd [0] SEQUENCE {
         referenceIdentity [0] PrimaryCPICH-Info
      },
      tdd [1] SEQUENCE {
         referenceIdentity [0] CellParametersID
      }
   } OPTIONAL,
   sfn [2] INTEGER (0..4095)
}

UTRANGPSDriftRate ::= ENUMERATED { utran-GPSDrift0(0), utran-GPSDrift1(1), 
   utran-GPSDrift2(2), utran-GPSDrift5(3), utran-GPSDrift10(4), 
   utran-GPSDrift15(5), utran-GPSDrift25(6), utran-GPSDrift50(7), 
   utran-GPSDrift-1(8), utran-GPSDrift-2(9), utran-GPSDrift-5(10), 
   utran-GPSDrift-10(11), utran-GPSDrift-15(12), utran-GPSDrift-25(13), 
   utran-GPSDrift-50(14) }

UTRAN-GPSReferenceTimeAssistance ::= SEQUENCE {
   utran-GPSReferenceTime [0] UTRAN-GPSReferenceTime,
   gpsReferenceTimeUncertainty [1] INTEGER (0..127) OPTIONAL,
   utranGPSDriftRate [2] UTRANGPSDriftRate OPTIONAL
}

UTRAN-GPSReferenceTimeResult ::= SEQUENCE {
   set-GPSTimingOfCell [0] SEQUENCE {
      ms-part [0] INTEGER (0..16383),
      ls-part [1] INTEGER (0..4294967295)
   },
   modeSpecificInfo [1] CHOICE {
      fdd [0] SEQUENCE {
         referenceIdentity [0] PrimaryCPICH-Info
      },
      tdd [1] SEQUENCE {
         referenceIdentity [0] CellParametersID
      }
   } OPTIONAL,
   sfn [2] INTEGER (0..4095),
   gpsReferenceTimeUncertainty [3] INTEGER (0..127) OPTIONAL,
   ...
}

UTRAN-GANSSReferenceTime ::= SEQUENCE {
   ganssTOD [0] INTEGER (0..86399),
   utran-GANSSTimingOfCell [1] INTEGER (0..3999999) OPTIONAL,
   modeSpecificInfo [2] CHOICE {
      fdd [0] SEQUENCE {
         referenceIdentity [0] PrimaryCPICH-Info
      },
      tdd [1] SEQUENCE {
         referenceIdentity [0] CellParametersID
      }
   } OPTIONAL,
   sfn [3] INTEGER (0..4095),
   ganss-TODUncertainty [4] INTEGER (0..127) OPTIONAL,
   ...
}

UTRANGANSSDriftRate ::= ENUMERATED { utran-GANSSDrift0(0), utran-GANSSDrift1(1)
   , utran-GANSSDrift2(2), utran-GANSSDrift5(3), utran-GANSSDrift10(4), 
   utran-GANSSDrift15(5), utran-GANSSDrift25(6), utran-GANSSDrift50(7), 
   utran-GANSSDrift-1(8), utran-GANSSDrift-2(9), utran-GANSSDrift-5(10), 
   utran-GANSSDrift-10(11), utran-GANSSDrift-15(12), utran-GANSSDrift-25(13), 
   utran-GANSSDrift-50(14) }

UTRAN-GANSSReferenceTimeAssistance ::= SEQUENCE {
   ganssDay [0] INTEGER (0..8191) OPTIONAL,
   ganssTimeID [1] INTEGER (0..15),
   utran-GANSSReferenceTime [2] UTRAN-GANSSReferenceTime,
   utranGANSSDriftRate [3] UTRANGANSSDriftRate OPTIONAL
}

SET-GANSSReferenceTime ::= SEQUENCE {
   set-GANSSTimingOfCell [0] SEQUENCE {
      ms-part [0] INTEGER (0..80),
      ls-part [1] INTEGER (0..4294967295)
   } OPTIONAL,
   modeSpecificInfo [1] CHOICE {
      fdd [0] SEQUENCE {
         referenceIdentity [0] PrimaryCPICH-Info
      },
      tdd [1] SEQUENCE {
         referenceIdentity [0] CellParametersID
      }
   } OPTIONAL,
   sfn [2] INTEGER (0..4095),
   ganss-TODUncertainty [3] INTEGER (0..127) OPTIONAL,
   ...
}

UTRAN-GANSSReferenceTimeResult ::= SEQUENCE {
   ganssTimeID [0] INTEGER (0..15),
   set-GANSSReferenceTime [1] SET-GANSSReferenceTime,
   ...
}

Coordinate ::= SEQUENCE {
   latitudeSign [0] ENUMERATED { north(0), south(1) },
   latitude [1] INTEGER (0..8388607),
   longitude [2] INTEGER (-8388608..8388607)
}

CircularArea ::= SEQUENCE {
   coordinate [0] Coordinate,
   radius [1] INTEGER (1..1000000),
   radius-min [2] INTEGER (1..1000000) OPTIONAL,
   radius-max [3] INTEGER (1..1500000) OPTIONAL
}

EllipticalArea ::= SEQUENCE {
   coordinate [0] Coordinate,
   semiMajor [1] INTEGER (1..1000000),
   semiMajor-min [2] INTEGER (1..1000000) OPTIONAL,
   semiMajor-max [3] INTEGER (1..1500000) OPTIONAL,
   semiMinor [4] INTEGER (1..1000000),
   semiMinor-min [5] INTEGER (1..1000000) OPTIONAL,
   semiMinor-max [6] INTEGER (1..1500000) OPTIONAL,
   angle [7] INTEGER (0..179)
}

PolygonDescription ::= SEQUENCE (SIZE (3..15)) OF Coordinate

PolygonArea ::= SEQUENCE {
   polygonDescription [0] PolygonDescription,
   polygonHysteresis [1] INTEGER (1..100000) OPTIONAL
}

CauseCode ::= ENUMERATED { servingNetWorkNotInAreaIdList(0), 
   sETCapabilitiesChanged(1), noSUPLCoverage(2), ... }

-- Value assignments

maxLidSize INTEGER ::= 64

maxWLANApDataSize INTEGER ::= 128

maxCellReport INTEGER ::= 8

maxWimaxBSMeas INTEGER ::= 32


END
