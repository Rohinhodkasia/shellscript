CSTA-suspend-location-tracking-session
	{ iso( 1) identified-organization( 3) icd-ecma( 12)
		standard( 0) csta3( 285) suspend-location-tracking-session ( 538) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
DeviceID FROM CSTA-device-identifiers
	{ iso( 1) identified-organization( 3) icd-ecma( 12)
		standard( 0) csta3( 285) device-identifiers( 123) }
LocCrossRefID FROM CSTA-device-feature-types
	{ iso( 1) identified-organization( 3) icd-ecma( 12)
		standard( 0) csta3( 285) device-feature-types( 127) };

suspendLocationTrackingSession OPERATION ::=
{ 	ARGUMENT		SuspendLocationTrackingSessionArgument
	RESULT			SuspendLocationTrackingSessionResult
	ERRORS			{universalFailure }
	CODE			local: 538 }

SuspendLocationTrackingSessionArgument ::= SEQUENCE
{	locCrossRefID			LocCrossRefID,
	extensions			CSTACommonArguments			OPTIONAL }

SuspendLocationTrackingSessionResult ::= SEQUENCE 
{	extensions			CSTACommonArguments			OPTIONAL }

END -- of CSTA-suspend-location-tracking-session
