-- This file was generated by the Objective Systems ASN1C Compiler
-- (http://www.obj-sys.com).  Version: 7.5.1.1, Date: 09-Jul-2021.

NR-UE-Variables DEFINITIONS AUTOMATIC TAGS ::= BEGIN

IMPORTS

CellIdentity, EUTRA-PhysCellId, MeasId, MeasIdToAddModList, 
   MeasObjectToAddModList, PhysCellId, RNTI-Value, ReportConfigToAddModList, 
   RSRP-Range, QuantityConfig, maxNrofCellMeas, maxNrofMeasId
FROM NR-RRC-Definitions ;

-- Productions

-- NR-UE-VARIABLES-STOP
-- TAG-VARPENDINGRNA-UPDATE-START
VarPendingRNA-Update ::= SEQUENCE {
   pendingRNA-Update [0] BOOLEAN OPTIONAL
}

-- TAG-VARPENDINGRNA-UPDATE-STOP
-- TAG-VARMEASCONFIG-START
VarMeasConfig ::= SEQUENCE {
     -- Measurement identities
   measIdList [0] MeasIdToAddModList OPTIONAL,
     -- Measurement objects
   measObjectList [1] MeasObjectToAddModList OPTIONAL,
     -- Reporting configurations
   reportConfigList [2] ReportConfigToAddModList OPTIONAL,
     -- Other parameters
   quantityConfig [3] QuantityConfig OPTIONAL,
   s-MeasureConfig [4] EXPLICIT CHOICE {
      ssb-RSRP [0] RSRP-Range,
      csi-RSRP [1] RSRP-Range
   } OPTIONAL
}

CellsTriggeredList ::= SEQUENCE (SIZE (1..maxNrofCellMeas)) OF CHOICE {
   physCellId [0] PhysCellId,
   physCellIdEUTRA [1] EUTRA-PhysCellId
}

VarMeasReport ::= SEQUENCE {
     -- List of measurement that have been triggered
   measId [0] MeasId,
   cellsTriggeredList [1] CellsTriggeredList OPTIONAL,
   numberOfReportsSent [2] INTEGER
}

-- TAG-VARMEASCONFIG-STOP
-- TAG-VARMEASREPORTLIST-START
VarMeasReportList ::= SEQUENCE (SIZE (1..maxNrofMeasId)) OF VarMeasReport

-- TAG-VARMEASREPORTLIST-STOP
-- TAG-VARRESUMEMAC-INPUT-START
VarResumeMAC-Input ::= SEQUENCE {
   sourcePhysCellId [0] PhysCellId,
   targetCellIdentity [1] CellIdentity,
   source-c-RNTI [2] RNTI-Value
}

-- TAG-VARRESUMEMAC-INPUT-STOP
-- TAG-VARSHORTMAC-INPUT-START
VarShortMAC-Input ::= SEQUENCE {
   sourcePhysCellId [0] PhysCellId,
   targetCellIdentity [1] CellIdentity,
   source-c-RNTI [2] RNTI-Value
}

END
