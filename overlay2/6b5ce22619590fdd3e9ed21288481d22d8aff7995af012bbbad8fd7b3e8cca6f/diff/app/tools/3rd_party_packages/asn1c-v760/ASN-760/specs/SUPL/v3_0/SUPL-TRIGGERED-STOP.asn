-- This file was generated by the Objective Systems ASN1C Compiler
-- (http://www.obj-sys.com).  Version: 6.8.A, Date: 18-Nov-2014.

SUPL-TRIGGERED-STOP DEFINITIONS AUTOMATIC TAGS ::= BEGIN

IMPORTS

StatusCode
FROM ULP-Components 

Ver3-SUPL-TRIGGERED-STOP-extension
FROM ULP-Version-3-message-extensions ;

-- Productions

Ver2-SUPLTRIGGEREDSTOP ::= SEQUENCE {
   statusCode [0] StatusCode OPTIONAL,
   ...,
   ver3-SUPL-TRIGGERED-STOP-extension [1] Ver3-SUPL-TRIGGERED-STOP-extension
       OPTIONAL
}

END
