-- This file was generated by the Objective Systems ASN1C Compiler
-- (http://www.obj-sys.com).  Version: 6.8.A, Date: 18-Nov-2014.

Ver3-ULP-Components DEFINITIONS AUTOMATIC TAGS ::= BEGIN

IMPORTS

OMA-LPPe-HighAccuracy3Dposition, OMA-LPPe-HighAccuracy3Dvelocity
FROM OMA-LPPE ;

-- Productions

Ver3-CellInfo-extension ::= CHOICE {
   noCellInfo [0] NULL,
   ...
}

Ver3-PositionEstimate-extension ::= SEQUENCE {
   highAccuracy3Dposition [0] OMA-LPPe-HighAccuracy3Dposition OPTIONAL,
   ...
}

Ver3-Velocity-extension ::= SEQUENCE {
   highAccuracy3Dvelocity [0] OMA-LPPe-HighAccuracy3Dvelocity OPTIONAL,
   ...
}

END
