-- This file was generated by the Objective Systems ASN1C Compiler
-- (http://www.obj-sys.com).  Version: 7.5.1.1, Date: 09-Jul-2021.

PC5-RRC-Definitions DEFINITIONS AUTOMATIC TAGS ::= BEGIN

IMPORTS

SetupRelease, RRC-TransactionIdentifier, SN-FieldLengthAM, SN-FieldLengthUM, 
   LogicalChannelIdentity, maxNrofSLRB-r16, maxNrofSL-QFIs-r16, 
   maxNrofSL-QFIsPerDest-r16, RSRP-Range, SL-MeasConfig-r16, SL-MeasId-r16, 
   FreqBandList, FreqBandIndicatorNR, maxSimultaneousBands, maxBandComb, 
   maxBands, BandParametersSidelink-r16, RLC-ParametersSidelink-r16
FROM NR-RRC-Definitions ;

-- Productions

SLRB-PC5-ConfigIndex-r16 ::= INTEGER (1..maxNrofSLRB-r16)

SL-PQFI-r16 ::= INTEGER (1..64)

AccessStratumReleaseSidelink-r16 ::= ENUMERATED { rel16(0), spare7(1), 
   spare6(2), spare5(3), spare4(4), spare3(5), spare2(6), spare1(7), ... }

-- TAG-SCCH-MESSAGE-STOP
-- TAG-MASTERINFORMATIONBLOCKSIDELINK-START
MasterInformationBlockSidelink ::= SEQUENCE {
   sl-TDD-Config-r16 [0] BIT STRING  (SIZE (12)),
   inCoverage-r16 [1] BOOLEAN,
   directFrameNumber-r16 [2] BIT STRING  (SIZE (10)),
   slotIndex-r16 [3] BIT STRING  (SIZE (7)),
   reservedBits-r16 [4] BIT STRING  (SIZE (2))
}

SBCCH-SL-BCH-MessageType ::= CHOICE {
   c1 [0] EXPLICIT CHOICE {
      masterInformationBlockSidelink [0] MasterInformationBlockSidelink,
      spare1 [1] NULL
   },
   messageClassExtension [1] SEQUENCE {

   }
}

-- TAG-PC5-RRC-DEFINITIONS-STOP
-- TAG-SBCCH-SL-BCH-MESSAGE-START
SBCCH-SL-BCH-Message ::= SEQUENCE {
   message [0] EXPLICIT SBCCH-SL-BCH-MessageType
}

SL-MeasQuantityResult-r16 ::= SEQUENCE {
   sl-RSRP-r16 [0] RSRP-Range OPTIONAL,
   ...
}

SL-MeasResult-r16 ::= SEQUENCE {
   sl-ResultDMRS-r16 [0] SL-MeasQuantityResult-r16 OPTIONAL,
   ...
}

SL-MeasResults-r16 ::= SEQUENCE {
   sl-MeasId-r16 [0] SL-MeasId-r16,
   sl-MeasResult-r16 [1] SL-MeasResult-r16,
   ...
}

MeasurementReportSidelink-IEs-r16 ::= SEQUENCE {
   sl-measResults-r16 [0] SL-MeasResults-r16,
   lateNonCriticalExtension [1] OCTET STRING OPTIONAL,
   nonCriticalExtension [2] SEQUENCE {

   } OPTIONAL
}

-- TAG-MASTERINFORMATIONBLOCKSIDELINK-STOP
-- TAG-MEASUREMENTREPORTSIDELINK-START
MeasurementReportSidelink ::= SEQUENCE {
   criticalExtensions [0] EXPLICIT CHOICE {
      measurementReportSidelink-r16 [0] MeasurementReportSidelink-IEs-r16,
      criticalExtensionsFuture [1] SEQUENCE {

      }
   }
}

SL-SDAP-ConfigPC5-r16 ::= SEQUENCE {
   sl-MappedQoS-FlowsToAddList-r16 [0] SEQUENCE (SIZE (1..maxNrofSL-QFIsPerDest-r16)) OF SL-PQFI-r16
       OPTIONAL, -- Need N
   sl-MappedQoS-FlowsToReleaseList-r16 [1] SEQUENCE (SIZE (1..maxNrofSL-QFIsPerDest-r16)) OF SL-PQFI-r16
       OPTIONAL, -- Need N
   sl-SDAP-Header-r16 [2] ENUMERATED { present(0), absent(1) },
   ...
}

SL-PDCP-ConfigPC5-r16 ::= SEQUENCE {
   sl-PDCP-SN-Size-r16 [0] ENUMERATED { len12bits(0), len18bits(1) } OPTIONAL, -- Need M
   sl-OutOfOrderDelivery-r16 [1] ENUMERATED { true(0) } OPTIONAL,
   ...
}

SL-RLC-ConfigPC5-r16 ::= CHOICE {
   sl-AM-RLC-r16 [0] SEQUENCE {
      sl-SN-FieldLengthAM-r16 [0] SN-FieldLengthAM OPTIONAL,
      ...
   },
   sl-UM-Bi-Directional-RLC-r16 [1] SEQUENCE {
      sl-SN-FieldLengthUM-r16 [0] SN-FieldLengthUM OPTIONAL,
      ...
   },
   sl-UM-Uni-Directional-RLC-r16 [2] SEQUENCE {
      sl-SN-FieldLengthUM-r16 [0] SN-FieldLengthUM OPTIONAL,
      ...
   }
}

SL-LogicalChannelConfigPC5-r16 ::= SEQUENCE {
   sl-LogicalChannelIdentity-r16 [0] LogicalChannelIdentity,
   ...
}

SLRB-Config-r16 ::= SEQUENCE {
   slrb-PC5-ConfigIndex-r16 [0] SLRB-PC5-ConfigIndex-r16,
   sl-SDAP-ConfigPC5-r16 [1] SL-SDAP-ConfigPC5-r16 OPTIONAL, -- Need M
   sl-PDCP-ConfigPC5-r16 [2] SL-PDCP-ConfigPC5-r16 OPTIONAL, -- Need M
   sl-RLC-ConfigPC5-r16 [3] EXPLICIT SL-RLC-ConfigPC5-r16 OPTIONAL, -- Need M
   sl-MAC-LogicalChannelConfigPC5-r16 [4] SL-LogicalChannelConfigPC5-r16
       OPTIONAL,
   ...
}

SL-CSI-RS-Config-r16 ::= SEQUENCE {
   sl-CSI-RS-FreqAllocation-r16 [0] EXPLICIT CHOICE {
      sl-OneAntennaPort-r16 [0] BIT STRING  (SIZE (12)),
      sl-TwoAntennaPort-r16 [1] BIT STRING  (SIZE (6))
   } OPTIONAL, -- Need M
   sl-CSI-RS-FirstSymbol-r16 [1] INTEGER (3..12) OPTIONAL,
   ...
}

RRCReconfigurationSidelink-IEs-r16 ::= SEQUENCE {
   slrb-ConfigToAddModList-r16 [0] SEQUENCE (SIZE (1..maxNrofSLRB-r16)) OF SLRB-Config-r16
       OPTIONAL, -- Need N
   slrb-ConfigToReleaseList-r16 [1] SEQUENCE (SIZE (1..maxNrofSLRB-r16)) OF 
      SLRB-PC5-ConfigIndex-r16 OPTIONAL, -- Need N
   sl-MeasConfig-r16 [2] EXPLICIT CHOICE {
      release [0] NULL,
      setup [1] EXPLICIT SL-MeasConfig-r16
   } OPTIONAL, -- Need M
   sl-CSI-RS-Config-r16 [3] EXPLICIT CHOICE {
      release [0] NULL,
      setup [1] EXPLICIT SL-CSI-RS-Config-r16
   } OPTIONAL, -- Need M
   sl-ResetConfig-r16 [4] ENUMERATED { true(0) } OPTIONAL, -- Need N
   sl-LatencyBoundCSI-Report-r16 [5] INTEGER (3..160) OPTIONAL, -- Need M
   lateNonCriticalExtension [6] OCTET STRING OPTIONAL,
   nonCriticalExtension [7] SEQUENCE {

   } OPTIONAL
}

-- TAG-MEASUREMENTREPORTSIDELINK-STOP
-- TAG-RRCRECONFIGURATIONSIDELINK-START
RRCReconfigurationSidelink ::= SEQUENCE {
   rrc-TransactionIdentifier-r16 [0] RRC-TransactionIdentifier,
   criticalExtensions [1] EXPLICIT CHOICE {
      rrcReconfigurationSidelink-r16 [0] RRCReconfigurationSidelink-IEs-r16,
      criticalExtensionsFuture [1] SEQUENCE {

      }
   }
}

RRCReconfigurationCompleteSidelink-IEs-r16 ::= SEQUENCE {
   lateNonCriticalExtension [0] OCTET STRING OPTIONAL,
   nonCriticalExtension [1] SEQUENCE {

   } OPTIONAL
}

-- TAG-RRCRECONFIGURATIONSIDELINK-STOP
-- TAG-RRCRECONFIGURATIONCOMPLETESIDELINK-START
RRCReconfigurationCompleteSidelink ::= SEQUENCE {
   rrc-TransactionIdentifier-r16 [0] RRC-TransactionIdentifier,
   criticalExtensions [1] EXPLICIT CHOICE {
      rrcReconfigurationCompleteSidelink-r16 [0] 
         RRCReconfigurationCompleteSidelink-IEs-r16,
      criticalExtensionsFuture [1] SEQUENCE {

      }
   }
}

RRCReconfigurationFailureSidelink-IEs-r16 ::= SEQUENCE {
   lateNonCriticalExtension [0] OCTET STRING OPTIONAL,
   nonCriticalExtension [1] SEQUENCE {

   } OPTIONAL
}

-- TAG-RRCRECONFIGURATIONCOMPLETESIDELINK-STOP
-- TAG-RRCRECONFIGURATIONFAILURESIDELINK-START
RRCReconfigurationFailureSidelink ::= SEQUENCE {
   rrc-TransactionIdentifier-r16 [0] RRC-TransactionIdentifier,
   criticalExtensions [1] EXPLICIT CHOICE {
      rrcReconfigurationFailureSidelink-r16 [0] 
         RRCReconfigurationFailureSidelink-IEs-r16,
      criticalExtensionsFuture [1] SEQUENCE {

      }
   }
}

UECapabilityEnquirySidelink-IEs-r16 ::= SEQUENCE {
   frequencyBandListFilterSidelink-r16 [0] FreqBandList OPTIONAL, -- Need N
   ue-CapabilityInformationSidelink-r16 [1] OCTET STRING OPTIONAL, -- Need N
   lateNonCriticalExtension [2] OCTET STRING OPTIONAL,
   nonCriticalExtension [3] SEQUENCE {

   } OPTIONAL
}

-- TAG-RRCRECONFIGURATIONFAILURESIDELINK-STOP
-- TAG-UECAPABILITYENQUIRYSIDELINK-START
UECapabilityEnquirySidelink ::= SEQUENCE {
   rrc-TransactionIdentifier-r16 [0] RRC-TransactionIdentifier,
   criticalExtensions [1] EXPLICIT CHOICE {
      ueCapabilityEnquirySidelink-r16 [0] UECapabilityEnquirySidelink-IEs-r16,
      criticalExtensionsFuture [1] SEQUENCE {

      }
   }
}

PDCP-ParametersSidelink-r16 ::= SEQUENCE {
   outOfOrderDeliverySidelink-r16 [0] ENUMERATED { supported(0) } OPTIONAL,
   ...
}

BandCombinationParametersSidelinkNR-r16 ::= SEQUENCE (SIZE (1..maxSimultaneousBands)) OF 
   BandParametersSidelink-r16

BandCombinationListSidelinkNR-r16 ::= SEQUENCE (SIZE (1..maxBandComb)) OF 
   BandCombinationParametersSidelinkNR-r16

BandSidelinkPC5-r16 ::= SEQUENCE {
   freqBandSidelink-r16 [0] FreqBandIndicatorNR,
     --15-1
   sl-Reception-r16 [1] SEQUENCE {
      harq-RxProcessSidelink-r16 [0] ENUMERATED { n16(0), n24(1), n32(2), 
         n64(3) },
      pscch-RxSidelink-r16 [1] ENUMERATED { value1(0), value2(1) },
      scs-CP-PatternRxSidelink-r16 [2] EXPLICIT CHOICE {
         fr1-r16 [0] SEQUENCE {
            scs-15kHz-r16 [0] BIT STRING  (SIZE (16)) OPTIONAL,
            scs-30kHz-r16 [1] BIT STRING  (SIZE (16)) OPTIONAL,
            scs-60kHz-r16 [2] BIT STRING  (SIZE (16)) OPTIONAL
         },
         fr2-r16 [1] SEQUENCE {
            scs-60kHz-r16 [0] BIT STRING  (SIZE (16)) OPTIONAL,
            scs-120kHz-r16 [1] BIT STRING  (SIZE (16)) OPTIONAL
         }
      } OPTIONAL,
      extendedCP-RxSidelink-r16 [3] ENUMERATED { supported(0) } OPTIONAL
   } OPTIONAL,
     --15-10
   sl-Tx-256QAM-r16 [2] ENUMERATED { supported(0) } OPTIONAL,
     --15-12
   lowSE-64QAM-MCS-TableSidelink-r16 [3] ENUMERATED { supported(0) } OPTIONAL,
   ...,
   [[
      csi-ReportSidelink-r16 [4] SEQUENCE {
         csi-RS-PortsSidelink-r16 [0] ENUMERATED { p1(0), p2(1) }
      } OPTIONAL,
      rankTwoReception-r16 [5] ENUMERATED { supported(0) } OPTIONAL,
      sl-openLoopPC-RSRP-ReportSidelink-r16 [6] ENUMERATED { supported(0) }
          OPTIONAL,
      sl-Rx-256QAM-r16 [7] ENUMERATED { supported(0) } OPTIONAL
   ]]
}

UECapabilityInformationSidelink-IEs-r16 ::= SEQUENCE {
   accessStratumReleaseSidelink-r16 [0] AccessStratumReleaseSidelink-r16,
   pdcp-ParametersSidelink-r16 [1] PDCP-ParametersSidelink-r16 OPTIONAL,
   rlc-ParametersSidelink-r16 [2] RLC-ParametersSidelink-r16 OPTIONAL,
   supportedBandCombinationListSidelinkNR-r16 [3] 
      BandCombinationListSidelinkNR-r16 OPTIONAL,
   supportedBandListSidelink-r16 [4] SEQUENCE (SIZE (1..maxBands)) OF 
      BandSidelinkPC5-r16 OPTIONAL,
   appliedFreqBandListFilter-r16 [5] FreqBandList OPTIONAL,
   lateNonCriticalExtension [6] OCTET STRING OPTIONAL,
   nonCriticalExtension [7] SEQUENCE {

   } OPTIONAL
}

-- TAG-UECAPABILITYENQUIRYSIDELINK-STOP
-- TAG-UECAPABILITYINFORMATIONSIDELINK-START
UECapabilityInformationSidelink ::= SEQUENCE {
   rrc-TransactionIdentifier-r16 [0] RRC-TransactionIdentifier,
   criticalExtensions [1] EXPLICIT CHOICE {
      ueCapabilityInformationSidelink-r16 [0] 
         UECapabilityInformationSidelink-IEs-r16,
      criticalExtensionsFuture [1] SEQUENCE {

      }
   }
}

SCCH-MessageType ::= CHOICE {
   c1 [0] EXPLICIT CHOICE {
      measurementReportSidelink [0] MeasurementReportSidelink,
      rrcReconfigurationSidelink [1] RRCReconfigurationSidelink,
      rrcReconfigurationCompleteSidelink [2] RRCReconfigurationCompleteSidelink
         ,
      rrcReconfigurationFailureSidelink [3] RRCReconfigurationFailureSidelink,
      ueCapabilityEnquirySidelink [4] UECapabilityEnquirySidelink,
      ueCapabilityInformationSidelink [5] UECapabilityInformationSidelink,
      spare2 [6] NULL,
      spare1 [7] NULL
   },
   messageClassExtension [1] SEQUENCE {

   }
}

-- TAG-SBCCH-SL-BCH-MESSAGE-STOP
-- TAG-SCCH-MESSAGE-START
SCCH-Message ::= SEQUENCE {
   message [0] EXPLICIT SCCH-MessageType
}

END
