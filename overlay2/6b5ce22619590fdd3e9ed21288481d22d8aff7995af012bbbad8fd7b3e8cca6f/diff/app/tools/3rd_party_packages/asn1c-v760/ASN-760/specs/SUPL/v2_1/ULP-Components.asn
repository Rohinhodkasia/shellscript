-- This file was generated by the Objective Systems ASN1C Compiler
-- (http://www.obj-sys.com).  Version: 6.8.A, Date: 15-Nov-2014.

ULP-Components DEFINITIONS AUTOMATIC TAGS ::= BEGIN

IMPORTS

Ver2-CellInfo-extension
FROM Ver2-ULP-Components ;

-- Productions

Version ::= SEQUENCE {
   maj [0] INTEGER (0..255),
   min [1] INTEGER (0..255),
   servind [2] INTEGER (0..255)
}

IPAddress ::= CHOICE {
   ipv4Address [0] OCTET STRING (SIZE (4)),
   ipv6Address [1] OCTET STRING (SIZE (16))
}

SETId ::= CHOICE {
   msisdn [0] OCTET STRING (SIZE (8)),
   mdn [1] OCTET STRING (SIZE (8)),
   min [2] BIT STRING  (SIZE (34)),
   imsi [3] OCTET STRING (SIZE (8)),
   nai [4] IA5String (SIZE (1..1000)),
   iPAddress [5] IPAddress,
   ...
}

SetSessionID ::= SEQUENCE {
   sessionId [0] INTEGER (0..65535),
   setId [1] SETId
}

FQDN ::= VisibleString (FROM ("a".."z" | "A".."Z" | "0".."9" | ". -") ^ SIZE (1..255))

SLPAddress ::= CHOICE {
   iPAddress [0] IPAddress,
   fQDN [1] FQDN,
   ...
}

SlpSessionID ::= SEQUENCE {
   sessionID [0] OCTET STRING (SIZE (4)),
   slpId [1] SLPAddress
}

SessionID ::= SEQUENCE {
   setSessionID [0] SetSessionID OPTIONAL,
   slpSessionID [1] SlpSessionID OPTIONAL
}

PosMethod ::= ENUMERATED { agpsSETassisted(0), agpsSETbased(1), 
   agpsSETassistedpref(2), agpsSETbasedpref(3), autonomousGPS(4), aFLT(5), 
   eCID(6), eOTD(7), oTDOA(8), noPosition(9), ..., 
   ver2-historicalDataRetrieval(10), ver2-agnssSETassisted(11), 
   ver2-agnssSETbased(12), ver2-agnssSETassistedpref(13), 
   ver2-agnssSETbasedpref(14), ver2-autonomousGNSS(15), 
   ver2-sessioninfoquery(16) }

QoP ::= SEQUENCE {
   horacc [0] INTEGER (0..127),
   veracc [1] INTEGER (0..127) OPTIONAL,
   maxLocAge [2] INTEGER (0..65535) OPTIONAL,
   delay [3] INTEGER (0..7) OPTIONAL,
   ...
}

NMRelement ::= SEQUENCE {
   aRFCN [0] INTEGER (0..1023),
   bSIC [1] INTEGER (0..63),
   rxLev [2] INTEGER (0..63),
   ...
}

NMR ::= SEQUENCE (SIZE (1..15)) OF NMRelement

GsmCellInformation ::= SEQUENCE {
   refMCC [0] INTEGER (0..999),
   refMNC [1] INTEGER (0..999),
   refLAC [2] INTEGER (0..65535),
   refCI [3] INTEGER (0..65535),
   nMR [4] NMR OPTIONAL,
   tA [5] INTEGER (0..255) OPTIONAL,
   ...
}

UARFCN ::= INTEGER (0..16383)

FrequencyInfoFDD ::= SEQUENCE {
   uarfcn-UL [0] UARFCN OPTIONAL,
   uarfcn-DL [1] UARFCN,
   ...
}

FrequencyInfoTDD ::= SEQUENCE {
   uarfcn-Nt [0] UARFCN,
   ...
}

FrequencyInfo ::= SEQUENCE {
   modeSpecificInfo [0] CHOICE {
      fdd [0] FrequencyInfoFDD,
      tdd [1] FrequencyInfoTDD,
      ...
   },
   ...
}

UTRA-CarrierRSSI ::= INTEGER (0..127)

PrimaryCPICH-Info ::= SEQUENCE {
   primaryScramblingCode [0] INTEGER (0..511)
}

CPICH-Ec-N0 ::= INTEGER (0..63)

CPICH-RSCP ::= INTEGER (0..127)

Pathloss ::= INTEGER (46..173)

CellParametersID ::= INTEGER (0..127)

TGSN ::= INTEGER (0..14)

PrimaryCCPCH-RSCP ::= INTEGER (0..127)

TimeslotISCP ::= INTEGER (0..127)

TimeslotISCP-List ::= SEQUENCE (SIZE (1..maxTS)) OF TimeslotISCP

CellMeasuredResults ::= SEQUENCE {
   cellIdentity [0] INTEGER (0..268435455) OPTIONAL,
   modeSpecificInfo [1] CHOICE {
      fdd [0] SEQUENCE {
         primaryCPICH-Info [0] PrimaryCPICH-Info,
         cpich-Ec-N0 [1] CPICH-Ec-N0 OPTIONAL,
         cpich-RSCP [2] CPICH-RSCP OPTIONAL,
         pathloss [3] Pathloss OPTIONAL
      },
      tdd [1] SEQUENCE {
         cellParametersID [0] CellParametersID,
         proposedTGSN [1] TGSN OPTIONAL,
         primaryCCPCH-RSCP [2] PrimaryCCPCH-RSCP OPTIONAL,
         pathloss [3] Pathloss OPTIONAL,
         timeslotISCP-List [4] TimeslotISCP-List OPTIONAL
      }
   }
}

CellMeasuredResultsList ::= SEQUENCE (SIZE (1..maxCellMeas)) OF CellMeasuredResults

MeasuredResults ::= SEQUENCE {
   frequencyInfo [0] FrequencyInfo OPTIONAL,
   utra-CarrierRSSI [1] UTRA-CarrierRSSI OPTIONAL,
   cellMeasuredResultsList [2] CellMeasuredResultsList OPTIONAL
}

MeasuredResultsList ::= SEQUENCE (SIZE (1..maxFreq)) OF MeasuredResults

TAResolution ::= ENUMERATED { res10chip(0), res05chip(1), res0125chip(2), ... }
   

ChipRate ::= ENUMERATED { tdd128(0), tdd384(1), tdd768(2), ... }

TimingAdvance ::= SEQUENCE {
   tA [0] INTEGER (0..8191),
   tAResolution [1] TAResolution OPTIONAL,
   chipRate [2] ChipRate OPTIONAL,
   ...
}

WcdmaCellInformation ::= SEQUENCE {
   refMCC [0] INTEGER (0..999),
   refMNC [1] INTEGER (0..999),
   refUC [2] INTEGER (0..268435455),
   frequencyInfo [3] FrequencyInfo OPTIONAL,
   primaryScramblingCode [4] INTEGER (0..511) OPTIONAL,
   measuredResultsList [5] MeasuredResultsList OPTIONAL,
   ...,
   cellParametersId [6] INTEGER (0..127) OPTIONAL,
   timingAdvance [7] TimingAdvance OPTIONAL
}

CdmaCellInformation ::= SEQUENCE {
   refNID [0] INTEGER (0..65535),
   refSID [1] INTEGER (0..32767),
   refBASEID [2] INTEGER (0..65535),
   refBASELAT [3] INTEGER (0..4194303),
   reBASELONG [4] INTEGER (0..8388607),
   refREFPN [5] INTEGER (0..511),
   refWeekNumber [6] INTEGER (0..65535),
   refSeconds [7] INTEGER (0..4194303),
   ...
}

CellInfo ::= CHOICE {
   gsmCell [0] GsmCellInformation,
   wcdmaCell [1] WcdmaCellInformation,
   cdmaCell [2] CdmaCellInformation,
   ...,
   ver2-CellInfo-extension [3] Ver2-CellInfo-extension
}

Status ::= ENUMERATED { stale(0), current(1), unknown(2), ... }

LocationId ::= SEQUENCE {
   cellInfo [0] CellInfo,
   status [1] Status,
   ...
}

AltitudeInfo ::= SEQUENCE {
   altitudeDirection [0] ENUMERATED { height(0), depth(1) },
   altitude [1] INTEGER (0..32767),
   altUncertainty [2] INTEGER (0..127),
   ...
}

PositionEstimate ::= SEQUENCE {
   latitudeSign [0] ENUMERATED { north(0), south(1) },
   latitude [1] INTEGER (0..8388607),
   longitude [2] INTEGER (-8388608..8388607),
   uncertainty [3] SEQUENCE {
      uncertaintySemiMajor [0] INTEGER (0..127),
      uncertaintySemiMinor [1] INTEGER (0..127),
      orientationMajorAxis [2] INTEGER (0..180)
   } OPTIONAL,
   confidence [4] INTEGER (0..100) OPTIONAL,
   altitudeInfo [5] AltitudeInfo OPTIONAL,
   ...
}

Horvel ::= SEQUENCE {
   bearing [0] BIT STRING  (SIZE (9)),
   horspeed [1] BIT STRING  (SIZE (16)),
   ...
}

Horandvervel ::= SEQUENCE {
   verdirect [0] BIT STRING  (SIZE (1)),
   bearing [1] BIT STRING  (SIZE (9)),
   horspeed [2] BIT STRING  (SIZE (16)),
   verspeed [3] BIT STRING  (SIZE (8)),
   ...
}

Horveluncert ::= SEQUENCE {
   bearing [0] BIT STRING  (SIZE (9)),
   horspeed [1] BIT STRING  (SIZE (16)),
   uncertspeed [2] BIT STRING  (SIZE (8)),
   ...
}

Horandveruncert ::= SEQUENCE {
   verdirect [0] BIT STRING  (SIZE (1)),
   bearing [1] BIT STRING  (SIZE (9)),
   horspeed [2] BIT STRING  (SIZE (16)),
   verspeed [3] BIT STRING  (SIZE (8)),
   horuncertspeed [4] BIT STRING  (SIZE (8)),
   veruncertspeed [5] BIT STRING  (SIZE (8)),
   ...
}

Velocity ::= CHOICE {
   horvel [0] Horvel,
   horandvervel [1] Horandvervel,
   horveluncert [2] Horveluncert,
   horandveruncert [3] Horandveruncert,
   ...
}

Position ::= SEQUENCE {
   timestamp [0] UTCTime,
   positionEstimate [1] PositionEstimate,
   velocity [2] Velocity OPTIONAL,
   ...
}

Ver ::= BIT STRING  (SIZE (64))

StatusCode ::= ENUMERATED { unspecified(0), systemFailure(1), 
   unexpectedMessage(2), protocolError(3), dataMissing(4), 
   unexpectedDataValue(5), posMethodFailure(6), posMethodMismatch(7), 
   posProtocolMismatch(8), targetSETnotReachable(9), versionNotSupported(10), 
   resourceShortage(11), invalidSessionId(12), nonProxyModeNotSupported(13), 
   proxyModeNotSupported(14), positioningNotPermitted(15), authNetFailure(16), 
   authSuplinitFailure(17), ..., ver2-incompatibleProtectionLevel(18), 
   ver2-serviceNotSupported(19), ver2-insufficientInterval(20), 
   ver2-noSUPLCoverage(21), consentDeniedByUser(100), consentGrantedByUser(101)
   , ver2-sessionStopped(102), ver2-appIdDenied(103), 
   ver3-locationURIUnavailable(130), ver3-locationURINotSupported(131), 
   ver3-locationURINotAuthorized(132), ver3-gssCapabilityMismatch(133), 
   ver3-unauthorizedAccessToSLP(134), ver3-invalidAccessToSLP(135), 
   ver3-RelativeLocationNotSupported(136), ver3-ReferencePointNotSupported(137)
    }

-- Value assignments

maxCellMeas INTEGER ::= 32

maxFreq INTEGER ::= 8

maxTS INTEGER ::= 14


END
