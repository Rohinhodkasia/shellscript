-- QSIG-MCM.asn
--
-- Taken from Ecma International
-- Standard ECMA-347, (June 2003)
-- http://www.ecma-international.org/publications/standards/Ecma-347.htm
--
-- $Id: QSIG-MCM.asn 22361 2007-07-20 09:54:47Z kukosa $
--

SS-MCM-Operations-asn1-97 
{iso (1) identified-organization (3) icd-ecma (12) standard (0)  
qsig-message-centre-monitoring (347)  
message-centre-monitoring-operations-asn1-97 (1)} 
 
DEFINITIONS EXPLICIT TAGS ::= 
 
BEGIN 
 
IMPORTS           OPERATION, ERROR FROM 
                       Remote-Operations-Information-Objects 
                       {joint-iso-itu-t remote-operations (4) informationObjects (5) 
                       version1 (0)} 
 
                  EXTENSION, Extension{} FROM  
                       Manufacturer-specific-service-extension-class-asn1-97 
                       {iso standard pss1-generic-procedures (11582)   
                       msi-class-asn1-97 (11)} 
 
                  basicServiceNotProvided, userNotSubscribed, invalidServedUserNr 
                       FROM General-Error-List 
                       {itu-t (0) recommendation (0) q (17) 950 
                       general-error-list (1)} 
 
                  PresentedAddressUnscreened, PartyNumber  FROM  
                       Addressing-Data-Elements-asn1-97  
                       {iso standard pss1-generic-procedures (11582)  
                       addressing-data-elements-asn1-97 (20)} 
               Name FROM Name-Operations-asn1-97 
                    {iso standard pss1-name (13868) name-operations-asn1-97 (1)} 
               ; 
 
 
MCM-Operations   OPERATION ::= { 
                               mCMNewMsg |  
                               mCMNoNewMsg | 
                               mCMUpdate |  
                               mCMUpdateReq |  
                               mCMService |  
                               mCMInterrogate |  
                               mCMailboxFull } 
 
 
mCMNewMsg        OPERATION ::= { 
                 ARGUMENT      MCMNewMsgArg 
                 RESULT        MCMDummyRes 
                 ERRORS        {userNotSubscribed | 
                               invalidServedUserNr | 
                               basicServiceNotProvided | 
                               unspecified} 
                 CODE          local: 80}  -- same code as for mWIActivate in SS-MWI 
 
 
mCMNoNewMsg      OPERATION ::= { 
                 ARGUMENT      MCMNoNewMsgArg 
                 RESULT        MCMDummyRes 
                 ERRORS        {userNotSubscribed | 
                               invalidServedUserNr | 
                               basicServiceNotProvided | 
                               unspecified} 
                 CODE          local: 81} -- same code as for mWIDeactivate in SS-MWI 
 
 
mCMUpdate        OPERATION ::= { 
                 ARGUMENT      MCMUpdateArg 
                 RESULT        MCMDummyRes 
                 ERRORS        {userNotSubscribed |  
                               invalidServedUserNr | 
                               unspecified} 
                 CODE          local: 115} 
 
 
mCMUpdateReq     OPERATION ::= { 
                 ARGUMENT      MCMUpdateReqArg 
                 RESULT        MCMUpdateReqRes 
                 ERRORS        {userNotSubscribed | 
                               invalidServedUserNr | 
                               basicServiceNotProvided | 
                               unspecified} 
                 CODE          local: 82} 
                               -- same code as for mWIInterrogate in SS-MWI

mCMService          OPERATION   ::= { 
                    ARGUMENT        MCMServiceArg 
                    RESULT          MCMDummyRes 
                    ERRORS          {userNotSubscribed | 
                                    invalidServedUserNr | 
                                    basicServiceNotProvided | 
                                    mCMModeNotProvided | 
                                    unspecified} 
                    CODE            local: 116} 
 
 
mCMInterrogate      OPERATION   ::= { 
                    ARGUMENT        MCMInterrogateArg 
                    RESULT          MCMInterrogateRes 
                    ERRORS          {userNotSubscribed | 
                                    invalidServedUserNr | 
                                    basicServiceNotProvided | 
                                    mCMModeNotProvided | 
                                    unspecified} 
                    CODE            local: 117} 
 
 
mCMailboxFull       OPERATION   ::= { 
                    ARGUMENT        MCMailboxFullArg 
                    RETURN RESULT   FALSE 
                    ALWAYS RESPONDS FALSE 
                    CODE            local: 118} 
 
 
MCMailboxFullArg  ::= SEQUENCE  
                             { 
                             partyInfo           PartyInfo, 
                             mailboxFullFor      MailboxFullFor, 
                             extensions          MCMExtensions    OPTIONAL, 
                             ... 
                             } 
 
MailboxFullFor    ::= SEQUENCE OF MailboxFullPar 
 
MailboxFullPar    ::= SEQUENCE 
                             { 
                             messageType         MessageType, 
                             capacityReached     INTEGER (0..100) OPTIONAL 
                             -- percentage of storage capacity already used 
                             } 
 
MCMServiceArg     ::= SEQUENCE 
                      { 
 
                      partyInfo         PartyInfo, 
                      mCMChange         MCMChange, 
                      extensions        MCMExtensions    OPTIONAL, 
                      ... 
                       } 

MCMChange          ::= CHOICE 
                       { 
                       activateMCM         [1] IMPLICIT SEQUENCE OF MCMServiceInfo, 
                       deactivateMCM       [2] IMPLICIT SEQUENCE OF MessageType, 
                       setToDefaultValues  NULL 
                       } 
 
MCMServiceInfo     ::= SEQUENCE 
                       { 
                       messageType         MessageType, 
                       mCMModeNew          [1] IMPLICIT MCMMode    OPTIONAL, 
                       mCMModeRetrieved    [2] IMPLICIT MCMMode    OPTIONAL 
                       } 
 
MCMInterrogateArg  ::= SEQUENCE 
                       { 
                       partyInfo           PartyInfo, 
                       interrogateInfo     SEQUENCE OF MessageType, 
                       extensions          MCMExtensions    OPTIONAL, 
                       ... 
                       } 
 
MCMInterrogateRes  ::= SEQUENCE 
                       { 
                       interrogateResult   SEQUENCE OF MCMServiceInfo, 
                       extensions          MCMExtensions    OPTIONAL, 
                       ... 
                       } 
 
MCMNewMsgArg       ::= SEQUENCE 
                       { 
                       servedUserNr         PartyNumber, 
                       specificMessageType  MessageType, 
                       msgCentreId          MsgCentreId                  OPTIONAL, 
                       nrOfMessages         [3] IMPLICIT NrOfMessages    OPTIONAL, 
                       originatingNr        [4] PartyNumber              OPTIONAL, 
                       timestamp            TimeStamp                    OPTIONAL, 
                       priority             [5] IMPLICIT INTEGER (0..9)  OPTIONAL, 
                       argumentExt   CHOICE { 
                             extension           [6] IMPLICIT Extension{{MCMExtSet}}, 
                             multipleExtension   [7] IMPLICIT SEQUENCE OF  
                                                     Extension{{MCMExtSet}} 
                             } OPTIONAL 
                       } 
 
 
MCMNoNewMsgArg     ::= SEQUENCE 
                       { 
                       servedUserNr           PartyNumber, 
                       specificMessageType    MessageType, 
                       msgCentreId            MsgCentreId          OPTIONAL, 
                       argumentExt            CHOICE { 
                            extension           [3] IMPLICIT Extension{{MCMExtSet}}, 
                            multipleExtension   [4] IMPLICIT SEQUENCE OF 
                                                 Extension{{MCMExtSet}} 
                            } OPTIONAL 
                       } 

MCMUpdateArg     ::= SEQUENCE 
                     { 
                     partyInfo              PartyInfo, 
                     messageType            MessageType, 
                     updateInfo             UpdateInfo, 
                     moreInfoFollows        BOOLEAN DEFAULT FALSE, 
                     extensions             MCMExtensions        OPTIONAL, 
                     ... 
                     } 
 
 
MCMUpdateReqArg  ::= SEQUENCE 
                     { 
                     servedUserNr          PartyNumber, 
                     specificMessageType   MessageType, 
                     msgCentreId           MsgCentreId         OPTIONAL, 
                     argumentExt           CHOICE { 
                        extension             [3] IMPLICIT Extension{{MCMExtSet}}, 
                        multipleExtension     [4] IMPLICIT SEQUENCE OF  
                                              Extension{{MCMExtSet}} 
                        } OPTIONAL 
                     }     
 
 
MCMUpdateReqRes  ::= SEQUENCE SIZE (1..10) OF MCMUpdateReqResElt 
 
 
MCMUpdateReqResElt  ::= SEQUENCE 
                        { 
                        specificMessageType    MessageType, 
                        msgCentreId            MsgCentreId                 OPTIONAL, 
                        nrOfMessages           [3] IMPLICIT NrOfMessages   OPTIONAL, 
                        originatingNr          [4] PartyNumber             OPTIONAL, 
                        timestamp              TimeStamp                   OPTIONAL, 
                        priority               [5] IMPLICIT INTEGER (0..9) OPTIONAL, 
                        argumentExt            CHOICE { 
                            extension            [6] IMPLICIT Extension{{MCMExtSet}}, 
                            multipleExtension    [7] IMPLICIT SEQUENCE OF  
                                                 Extension{{MCMExtSet}} 
                            } OPTIONAL 
                        } 
 
 
MCMMode        ::= INTEGER 
                   { 
                   compressed      (0), 
                   complete        (1) 
                   } 
 
MCMDummyRes    ::= MCMExtensions 
 
 
PartyInfo  ::= SEQUENCE   
                   { 
                   servedUserNr        PartyNumber, 
                   messageCentreID     MsgCentreId 
                   } 

UpdateInfo     ::= CHOICE 
                   { 
                   newMsgInfoOnly          [1] MessageInfo, 
                   retrievedMsgInfoOnly    [2] MessageInfo, 
                   allMsgInfo              AllMsgInfo 
                   } 
 
 
AllMsgInfo     ::= SEQUENCE 
                   { 
                   newMsgInfo          MessageInfo, 
                   retrievedMsgInfo    MessageInfo 
                   } 
 
 
MessageInfo    ::= CHOICE  
                   { 
                   completeInfo        [1] IMPLICIT CompleteInfo, 
                   compressedInfo      [2] IMPLICIT CompressedInfo, 
                   noMsgsOfMsgType     NULL 
                   } 
 
 
CompleteInfo   ::= SEQUENCE OF AddressHeader 
 
 
AddressHeader  ::= SEQUENCE 
                   { 
                   originatorNr        PartyNumber, 
                   timeStamp           [1] IMPLICIT TimeStamp       OPTIONAL, 
                   priority            [2] IMPLICIT Priority        OPTIONAL 
                   } 
 
 
CompressedInfo    ::= SEQUENCE 
                      { 
                      nrOfMessages        NrOfMessages, 
                      lastTimeStamp       TimeStamp         OPTIONAL, 
                      highestPriority     Priority          OPTIONAL 
                      } 
 
 
NrOfMessages      ::= INTEGER (0..65535) 
 
 
Priority          ::= INTEGER (0..9)      -- the value 0 means the highest priority 
                                          -- and 9 the lowest 
 
MsgCentreId       ::= CHOICE  
                      { 
                      integer          [0] IMPLICIT INTEGER (0..65535), 
                      partyNumber      [1] PartyNumber, 
                      numericString    [2] IMPLICIT NumericString (SIZE(1..10)) 
                      } 

TimeStamp         ::= GeneralizedTime
              --  a VisibleString containing: 
              --    - the (local) date in 8 digits (YYYYMMDD), 
              --    - followed by (local) time of day in 4 or 6 digits (HHMM[SS]), 
              --    - optionally followed by the letter "Z" or  
              --      by a local time differential in 5 digits ("+"HHMM or "-"HHMM); 
              --      this date and time representation follows ISO 8601 
              --  Examples:      1) 19970621194530, meaning 21 June 1997, 19:45:30; 
              --                 2) 19970621194530Z, meaning the same as 1); 
              --                 3) 19970621194530-0500, meaning the same as 1), 
              --                    5 hours retarded in relation to UTC time 
 
 
MessageType       ::= ENUMERATED 
                      { 
                   -- Note: for the following message type see also Annex D.4 
                      allServices                    (0), 
                   -- Note: for the following message types see also Annex D.1 
                   -- For compatibility among vendors, speech is recommended for 
                   -- voice mail indications 
                      speech                          (1), 
                      unrestrictedDigitalInformation  (2), 
                      audio3100Hz                     (3), 
                      telephony                      (32), 
                      teletex                        (33), 
                      telefaxGroup4Class1            (34), 
                      videotextSyntaxBased           (35), 
                      videotelephony                 (36), 
                      telefaxGroup2-3                (37), 
                      reservedNotUsed1               (38), 
                      reservedNotUsed2               (39), 
                      reservedNotUsed3               (40), 
                      reservedNotUsed4               (41), 
                      reservedNotUsed5               (42), 
                   -- Note: for the following message types see also annex D.2 
                      email                          (51), 
                      video                          (52), 
                      fileTransfer                   (53), 
                      shortMessageService            (54), 
                   -- Note: for the following message types see also annex D.3 
                      speechAndVideo                 (55), 
                      speechAndFax                   (56), 
                      speechAndEmail                 (57), 
                      videoAndFax                    (58), 
                      videoAndEmail                  (59), 
                      faxAndEmail                    (60), 
                      speechVideoAndFax              (61), 
                      speechVideoAndEmail            (62), 
                      speechFaxAndEmail              (63), 
                      videoFaxAndEmail               (64), 
                      speechVideoFaxAndEmail         (65), 
                   -- Note: for the following message types see also annex D.4 
                      multimediaUnknown              (66), 
                      serviceUnknown                 (67), 
                    futureReserve1               (68), 
                    futureReserve2               (69), 
                    futureReserve3               (70), 
                    futureReserve4               (71), 
                    futureReserve5               (72), 
                    futureReserve6               (73), 
                    futureReserve7               (74), 
                    futureReserve8               (75) 
                    } 
 
MCMExtensions   ::= CHOICE 
                    { 
                    none               NULL, 
                    extension          [1] IMPLICIT Extension {{MCMExtSet}}, 
                    multipleExtension  [2] IMPLICIT SEQUENCE OF  
                                            Extension {{ MCMExtSet }} 
                    } 
 
mCMModeNotProvided      ERROR   ::= { 
                        CODE       local:1037} 
 
unspecified            ERROR ::= { 
                       PARAMETER    Extension{{MCMExtSet}} 
                       CODE        local:1008} 
 
MCMExtSet     EXTENSION ::= {...} 
 
 
END        -- of SS-MCM-Operations-asn1-97
