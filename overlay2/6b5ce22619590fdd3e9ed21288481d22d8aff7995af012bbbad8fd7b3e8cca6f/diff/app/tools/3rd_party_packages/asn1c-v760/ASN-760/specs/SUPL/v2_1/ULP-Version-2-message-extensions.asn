-- This file was generated by the Objective Systems ASN1C Compiler
-- (http://www.obj-sys.com).  Version: 6.8.A, Date: 15-Nov-2014.

ULP-Version-2-message-extensions DEFINITIONS AUTOMATIC TAGS ::= BEGIN

IMPORTS

SLPAddress, Position, Ver
FROM ULP-Components 

SETCapabilities
FROM SUPL-START 

SupportedNetworkInformation, GNSSPosTechnology, MultipleLocationIds, 
   UTRAN-GPSReferenceTimeResult, UTRAN-GANSSReferenceTimeResult, 
   UTRANGPSReferenceTimeAssistance, UTRAN-GANSSReferenceTimeAssistance, 
   SPCSETKey, SPCTID, SPCSETKeylifetime, ThirdParty, ApplicationID, 
   UTRAN-GPSReferenceTimeAssistance
FROM Ver2-ULP-Components 

TriggerType
FROM SUPL-TRIGGERED-START ;

-- Productions

NotificationMode ::= ENUMERATED { normal(0), basedOnLocation(1), ... }

AllowedReportingType ::= ENUMERATED { positionsOnly(0), measurementsOnly(1), 
   positionsAndMeasurements(2), ... }

TimeWindow ::= SEQUENCE {
   startTime [0] INTEGER (-525600..-1),
   stopTime [1] INTEGER (-525599..0)
}

ReportingCriteria ::= SEQUENCE {
   timeWindow [0] TimeWindow OPTIONAL,
   maxNumberofReports [1] INTEGER (1..65536) OPTIONAL,
   minTimeInterval [2] INTEGER (1..86400) OPTIONAL,
   ...
}

HistoricReporting ::= SEQUENCE {
   allowedReportingType [0] AllowedReportingType,
   reportingCriteria [1] ReportingCriteria OPTIONAL,
   ...
}

ProtLevel ::= ENUMERATED { nullProtection(0), basicProtection(1), ... }

BasicProtectionParams ::= SEQUENCE {
   keyIdentifier [0] OCTET STRING (SIZE (8)),
   basicReplayCounter [1] INTEGER (0..65535),
   basicMAC [2] BIT STRING  (SIZE (32)),
   ...
}

ProtectionLevel ::= SEQUENCE {
   protlevel [0] ProtLevel,
   basicProtectionParams [1] BasicProtectionParams OPTIONAL,
   ...
}

Ver2-SUPL-INIT-extension ::= SEQUENCE {
   notificationMode [0] NotificationMode OPTIONAL,
   supportedNetworkInformation [1] SupportedNetworkInformation OPTIONAL,
   triggerType [2] TriggerType OPTIONAL,
   e-SLPAddress [3] SLPAddress OPTIONAL,
   historicReporting [4] HistoricReporting OPTIONAL,
   protectionLevel [5] ProtectionLevel OPTIONAL,
   gnssPosTechnology [6] GNSSPosTechnology OPTIONAL,
   minimumMajorVersion [7] INTEGER (0..255) OPTIONAL,
   ...
}

Ver2-SUPL-START-extension ::= SEQUENCE {
   multipleLocationIds [0] MultipleLocationIds OPTIONAL,
   thirdParty [1] ThirdParty OPTIONAL,
   applicationID [2] ApplicationID OPTIONAL,
   position [3] Position OPTIONAL,
   ...
}

Ver2-SUPL-RESPONSE-extension ::= SEQUENCE {
   supportedNetworkInformation [0] SupportedNetworkInformation OPTIONAL,
   sPCSETKey [1] SPCSETKey OPTIONAL,
   sPCTID [2] SPCTID OPTIONAL,
   sPCSETKeylifetime [3] SPCSETKeylifetime OPTIONAL,
   initialApproximateposition [4] Position OPTIONAL,
   gnssPosTechnology [5] GNSSPosTechnology OPTIONAL,
   ...
}

Ver2-SUPL-POS-extension ::= SEQUENCE {
   utran-GPSReferenceTimeAssistance [0] UTRAN-GPSReferenceTimeAssistance
       OPTIONAL,
   utran-GPSReferenceTimeResult [1] UTRAN-GPSReferenceTimeResult OPTIONAL,
   utran-GANSSReferenceTimeAssistance [2] UTRAN-GANSSReferenceTimeAssistance
       OPTIONAL,
   utran-GANSSReferenceTimeResult [3] UTRAN-GANSSReferenceTimeResult OPTIONAL,
   ...
}

Ver2-SUPL-POS-INIT-extension ::= SEQUENCE {
   multipleLocationIds [0] MultipleLocationIds OPTIONAL,
   utran-GPSReferenceTimeResult [1] UTRAN-GPSReferenceTimeResult OPTIONAL,
   utran-GANSSReferenceTimeResult [2] UTRAN-GANSSReferenceTimeResult OPTIONAL,
   ...
}

Ver2-SUPL-END-extension ::= SEQUENCE {
   sETCapabilities [0] SETCapabilities OPTIONAL,
   ...
}

END
