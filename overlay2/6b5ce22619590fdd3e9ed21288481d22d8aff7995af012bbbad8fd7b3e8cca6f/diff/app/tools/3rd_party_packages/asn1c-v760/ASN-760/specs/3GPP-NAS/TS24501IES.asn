TS24501IES DEFINITIONS AUTOMATIC TAGS ::=
BEGIN

IMPORTS
ExtQualityOfService, MCCMNCPair, IMEI, IMEISV, TFT, TimeZoneAndTime
FROM TS24008IES

IMPORTS
APNAggMaxBitRate, EPSQualityOfService, ExtAPNAggMaxBitRate, NASMessageContainer
FROM TS24301IES
;


/* -- TYPE DEFINITIONS --- */

/* OpaqueData can be used for any case where the specification has
   some number of octets preceded by a 2-octet length. */
OpaqueData ::= SEQUENCE {
   --<is3GLength bitFieldSize="16"/>
   length INTEGER (1..65535),
   --<length fixed-size="0"/>
   contents OCTET STRING  
}

/* 9.11.2.1 - Additional information */
AdditionalInfo ::= OCTET STRING

/* 9.11.2.1A - Access type */
AccessType ::= SEQUENCE {
   spare INTEGER (0..3) DEFAULT 0,
   typeOfAccess ENUMERATED {
      access3gpp(1), accessNon3gpp(2)
   }
}

/* 9.11.2.1B - DNN */
DNNList ::= SEQUENCE {
   --<is3GLength/>
   length INTEGER (1..255),
   --<length fixed-size="0"/>
   apn SEQUENCE OF IA5String
}

/* 9.11.2.2 - EAP message */
EAPMessage ::= SEQUENCE {
   --<is3GLength bitFieldSize="16"/>
   length INTEGER (1..65535),
   --<asn1typename>EAPPacketFormat</asn1typename>
   packetFormat SEQUENCE {
      code EAPFormatCode,
      id INTEGER (0..255),
      length INTEGER (4..65535),
      --<length expr="@.length - 4"/>
      data OCTET STRING
   }
}

EAPFormatCode ::= ENUMERATED {
   request(1), response(2), success(3), failure(4),
   codeMax(255)
}

/* 9.11.2.6 - Intra N1 mode NAS transparent container */
IntraN1NASContainer ::= SEQUENCE {
   --<is3GLength/>
   length INTEGER (1..255),
   authCode OCTET STRING (SIZE (4)),
   cipherType INTEGER (0..15),
   integrityType INTEGER (0..15),
   spare1 INTEGER (0..7) DEFAULT 0,
   kacf BOOLEAN,
   tsc BOOLEAN,
   keysetId INTEGER (0..7),
   seqNumber INTEGER (1..255)
}

/* 9.11.2.7 - N1 mode to S1 mode NAS transparent container */
N1ToS1NASContainer ::= INTEGER (1..255)

/* 9.11.2.8 - S-NSSAI */
SNSSAI ::= SEQUENCE {
   --<is3GLength/>
   length INTEGER (1..255),
   sst SST,
   --<noPresentBit/>
   sd SD OPTIONAL,
   --<noPresentBit/>
   mappedSST OCTET STRING (SIZE (1)) OPTIONAL,
   --<noPresentBit/>
   mappedSD OCTET STRING (SIZE (3)) OPTIONAL
}

/* 9.11.2.9 - S1 mode to N1 mode NAS transparent container */
S1ToN1NASContainer ::= SEQUENCE {   
   --<is3GLength/>
   length INTEGER (1..255),
   authCode OCTET STRING (SIZE (4)),
   cipherType INTEGER (0..15),
   integrityType INTEGER (0..15),
   spare1 BOOLEAN DEFAULT FALSE,
   ncc INTEGER (0..7),
   tsc BOOLEAN,
   keysetId INTEGER (0..7),
   spare2 INTEGER (1..65535) DEFAULT 0
}

SST ::= INTEGER (1..255)

SD ::= INTEGER (1..16777215)

/* 9.11.2.10 - Service-level-AA container - added in 17.3 */
SLAAContainer ::= SEQUENCE {
   --<is3GLength bitFieldSize="16"/>
   length INTEGER (0..65535),
   --<is3GVarLenList lengthElem="length"/>
   contents SEQUENCE (SIZE (1..256)) OF SLAAParameter
}

SLAAParameter ::= SEQUENCE {
   type SLAAParamTypes,
   --<inline/>
   param CHOICE {
      --<selector element="type" value="16"/>
      deviceId SLDeviceId,
      --<selector element="type" value="32"/>
      serverAddr SLAAServerAddr,
      --<selector element="type" value="48"/>
      payload SLAAPayload,
      --<selector element="type" value="112"/>
      response SLAAResponse
   }
}

SLAAParamTypes ::= ENUMERATED {
   ptDeviceId(16), ptServerAddr(32), ptPayload(48), ptResponse(112),
   ptMax(255)
}

/* 9.11.2.11 - Service-level device ID - added in 17.3 */
SLDeviceId ::= SEQUENCE {
   --<is3GLength/>
   length INTEGER (1..255),
   id OCTET STRING (SIZE (1..255))
}

/* 9.11.2.12 - Service-level-AA server address - added in 17.3 */
SLAAServerAddr ::= SEQUENCE {
   --<is3GLength/>
   length INTEGER (1..255),
   addrType INTEGER (1..255),
   addr OCTET STRING (SIZE (1..255))
}

/* 9.11.2.13 - Service-level-AA payload - added in 17.3 */
SLAAPayload ::= SEQUENCE {
   --<is3GLength bitFieldSize="16"/>
   length INTEGER (0..65535),
   payload OCTET STRING (SIZE (1..65532))
}

/* 9.11.2.14 - Service-level-AA response - added in 17.3 */
SLAAResponse ::= SEQUENCE {
   --<is3GLength/>
   length INTEGER (1..255),
   spare INTEGER (0..127) DEFAULT 0,
   slar BOOLEAN
}


/* 9.11.3.1 - MM capability */
MMCapability ::= SEQUENCE {
   --<is3GLength/>
   length INTEGER (1..255) DEFAULT 1,

   /* octet 3 */
   sgc BOOLEAN,
   hcCpCIoT BOOLEAN,
   n3Data BOOLEAN,
   cpCIoT BOOLEAN,
   restrictedEC BOOLEAN,
   lppSupported BOOLEAN,
   handoverSupported BOOLEAN,
   s1Supported BOOLEAN,
   --<noPresentBit/>
   octet4 SEQUENCE {
      racs BOOLEAN,
      nssaa BOOLEAN,
      lcs BOOLEAN,
      v2xcnpc5 BOOLEAN,
      v2xcepc5 BOOLEAN,
      v2x BOOLEAN,
      upCIoT BOOLEAN,
      srvcc BOOLEAN
   } OPTIONAL,
   --<noPresentBit/>
   octet5 SEQUENCE {
      proSel2relay BOOLEAN, -- Added in v17.3
      proSedc BOOLEAN, -- Added in v17.3
      proSedd BOOLEAN, -- Added in v17.3
      erNssai BOOLEAN,  -- Added in v17.0
      ehcCpCIoT BOOLEAN,  -- Added in v16.5
      multipleUp BOOLEAN, -- Added in v16.5
      wusa BOOLEAN,
      cag BOOLEAN
   } OPTIONAL,
   --<noPresentBit/>
   octet6 SEQUENCE { -- Added in v17.3
      spare INTEGER (0..31) DEFAULT 0,
      proSel3rmt BOOLEAN,
      proSel2rmt BOOLEAN,
      proSel3relay BOOLEAN
   } OPTIONAL,
   --<noPresentBit/>
   --<length fixed-size="0"/>
   spare OCTET STRING OPTIONAL
}

/* 9.11.3.2 - MM cause */
MMCause ::= INTEGER (0..255)

/* 9.11.3.2A - DRX parameters */
DRXParams ::= SEQUENCE {
   --<is3GLength/>
   length INTEGER (1), 
   spare INTEGER (0..15) DEFAULT 0, 
   drxValue INTEGER (0..15)
}

/* 9.11.3.3 - Identity type */
IdentityType ::= SEQUENCE {
   spare BOOLEAN DEFAULT FALSE,
   typeOfIdent TypeOfIdentity
}

TypeOfIdentity ::= ENUMERATED {
   none(0), suci(1), guti(2), imei(3), stmsi(4), imeisv(5), macAddr(6),
   eui64(7) }

/* 9.11.3.4 - 5G mobile identity */
MobileIdentity ::= CHOICE {
   none NULL,   
   suci CHOICE {
      -- The supiFormat bit in the MobileIdentity determines which of these
      -- choices is present in an encoding.
      supiImsi MobileIdentity_SUCI_IMSI,
      supiNetSpecificId MobileIdentity_SUCI_NetId
   },
   guti MobileIdentity_GUTI,
   imei IMEI,
   stmsi MobileIdentity_STMSI,
   imeisv IMEISV,
   mac MobileIdentity_MAC,
   eui-64 OCTET STRING (SIZE(8))
}

MobileIdentity_GUTI ::= SEQUENCE {
   mcc-mnc MCCMNCPair,
   amfRegionID INTEGER (0..255),
   amfSetID INTEGER (0..1023),
   amfPointer INTEGER (0..63),
   tmsi OCTET STRING (SIZE (4))
}

MobileIdentity_STMSI ::= SEQUENCE {
   amfSetID INTEGER (0..1023),
   amfPointer INTEGER (0..63),
   tmsi OCTET STRING (SIZE (4))
}

MobileIdentity_SUCI_IMSI ::= SEQUENCE {
   mcc-mnc MCCMNCPair,
   routingInd2 INTEGER (0..15),
   routingInd1 INTEGER (0..15),
   routingInd4 INTEGER (0..15),
   routingInd3 INTEGER (0..15),
   spare INTEGER (0..15) DEFAULT 0,
   protSchemeId INTEGER (0..15),
   homeNetId INTEGER (0..255),
   --<length fixed-size="0"/>
   schemeOutput OCTET STRING
}

MobileIdentity_SUCI_NetId ::= SEQUENCE {
   --<length fixed-size="0">
   nai OCTET STRING
}

MobileIdentity_MAC ::= SEQUENCE {
   mauri BOOLEAN,
   macaddr OCTET STRING (SIZE(6))
}

/* 9.11.3.5 - 5GS network feature support */
NetworkFeatureSupport ::= SEQUENCE {
   --<is3GLength/>
   length INTEGER (1..255),

   /* octet 3 */
   mpsInd BOOLEAN, 
   interNetworkWithoutN26Ind BOOLEAN,
   emfInd INTEGER (0..3), 
   emcInd INTEGER (0..3), 
   imsVoPSN3GPPInd BOOLEAN,
   imsVoPS3GPPInd BOOLEAN,

   --<noPresentBit/>
   /* octet 4 */
   octet4 SEQUENCE {
      upCIoT BOOLEAN,
      hcCpCIoT BOOLEAN,
      n3Data BOOLEAN,
      cpCIoT BOOLEAN,
      restrictedEC INTEGER (0..3),
      mcsi BOOLEAN,
      emcn3 BOOLEAN
   } OPTIONAL,

   --<noPresentBit/>
   /* octet 5 */
   octet5 SEQUENCE {
      spare BOOLEAN DEFAULT FALSE,
      pr BOOLEAN, -- Added in v17.3
      rpr BOOLEAN, -- Added in v17.3
      piv BOOLEAN, -- Added in v17.3
      ncr BOOLEAN, -- Added in v17.3
      ehcCpCIoT BOOLEAN, -- Added in v16.5
      atsInd BOOLEAN,
      lcs BOOLEAN        -- Added in v16.5
   } OPTIONAL
}

/* 9.11.3.6 - Registration result */
RegistrationResult ::= SEQUENCE {
   --<is3GLength/>
   length INTEGER (1..255),
   spare INTEGER (0..3) DEFAULT 0,
   emergencyRegistered BOOLEAN,
   nssaa BOOLEAN,
   smsAllowed BOOLEAN,
   regResult RegistrationResultValue
}

RegistrationResultValue ::= ENUMERATED {
   access(1), nonAccess(2), accessAndNonAccess(3), regResultMAX(7)
} 

/* 9.11.3.7 - Registration type */
RegistrationType ::= SEQUENCE {
   forBit BOOLEAN,
   regisType RegistrationTypeValue
}

RegistrationTypeValue ::= ENUMERATED {
   initial(1), mobilityUpdate(2), periodicUpdate(3), emergency(4),
   snpnOnboard(5), regisTypeMAX(7)
} 

/* 9.11.3.8 - Tracking area identity */
/* Mostly the same as 24.301 except the TAC is 3 octets instead of 2... */
TrackingAreaIdent ::= SEQUENCE {
   mcc-mnc MCCMNCPair,
   tac TrackingAreaCode
}

TrackingAreaCode ::= OCTET STRING (SIZE (3))

/* 9.11.3.9 - Tracking area identity list */
/* Mostly the same as 24.301 except the TAC is 3 octets instead of 2... */
/* Also used for Service Area List type (9.11.3.49)... */
TrackingAreaIdentList ::= SEQUENCE {
   --<is3GLength/>
   length INTEGER (1..255), 
   --<is3GVarLenList lengthElem="length"/>
   idents SEQUENCE (SIZE (1..16)) OF TrackingAreaIdentListItem
}

TrackingAreaIdentListItem ::= SEQUENCE {
   spare BOOLEAN DEFAULT FALSE,
   typeOfList INTEGER (0..3),
   numElements INTEGER (0..31),  -- number of elements - 1
   --<inline/>
   elements CHOICE {
      --<selector element="typeOfList" value="0"/>
      --<asn1typename>PartialTrkAreaIdent0</asn1typename>
      partTrkIdentList0 SEQUENCE {
         mcc-mnc MCCMNCPair,
         --<inline/>
         --<length expr="@...numElements + 1"/>
         tacs SEQUENCE (SIZE (1..32)) OF TrackingAreaCode
      },      
      --<selector element="typeOfList" value="1"/>
      --<asn1typename>PartialTrkAreaIdent1</asn1typename>
      partTrkIdentList1 SEQUENCE {
         mcc-mnc MCCMNCPair,
         tac TrackingAreaCode
      },
      --<selector element="typeOfList" value="2"/>
      --<length expr="@.numElements + 1"/>
      --<asn1typename>PartialTrkAreaIdent2</asn1typename>
      partTrkIdentList2 SEQUENCE (SIZE (1..32)) OF TrackingAreaIdent,
      --<selector element="typeOfList" value="3"/>
      partTrkIdentList3 MCCMNCPair
   }
}


/* 9.11.3.9A - Update type */
UpdateType  ::= SEQUENCE {
   --<is3GLength/>
   length INTEGER (1..255),
   spare INTEGER (0..3) DEFAULT 0,
   epsPnbCIoT INTEGER (0..3),
   pnbCIoT INTEGER (0..3),
   ngranUpd BOOLEAN,
   smsReq BOOLEAN
}

/* 9.11.3.10 - ABBA */
ABBA ::= OCTET STRING  -- (preceeded by 1 octet length)

/* 9.11.3.12 - Additional security information */
AddlSecurityInfo ::= SEQUENCE {
   --<is3GLength/>
   length INTEGER (1..255),
   spare INTEGER (0..63) DEFAULT 0,
   rinmr BOOLEAN,
   hdp BOOLEAN
}

/* 9.11.3.12A - Additional information requested */
AdditionalInfoRequested ::= SEQUENCE {
   --<is3GLength/>
   length INTEGER (1..255),
   spare INTEGER (0..127) DEFAULT 0,
   cipherKey BOOLEAN
}

/* 9.11.3.13 - Allowed PDU session status */
AllowedPDUSessionStatus ::= SEQUENCE {
   --<is3GLength/>
   length INTEGER (1..255),
   psi SEQUENCE (SIZE (16)) OF BOOLEAN,
   --<noPresentBit/>
   spare OCTET STRING OPTIONAL
}

/* 9.11.3.18 - Configuration update indication */
ConfigUpdateIndication ::= SEQUENCE {
   spare INTEGER (0..3) DEFAULT 0,
   regRequested BOOLEAN,
   ack BOOLEAN
}

/* 9.11.3.18A - CAG information list */
CAGInfoList ::= SEQUENCE {
   --<is3GLength bitFieldSize="16"/>
   length INTEGER (0..65535),
   --<is3GVarLenList lengthElem="length"/>
   --<noPresentBit/>
   entries SEQUENCE OF CAGEntry OPTIONAL
}

CAGEntry ::= SEQUENCE {
   length INTEGER (1..255),
   mcc-mnc MCCMNCPair,
   spare INTEGER (0..127) DEFAULT 0,
   cagOnly BOOLEAN,
   --<noPresentBit/>
   --<length fixed-size="0"/>
   cagID OCTET STRING OPTIONAL
}

/* 9.11.3.18B - CIoT small data container */
CIoTSmallDataContainer ::= SEQUENCE {
   --<is3GLength/>
   length INTEGER (1..255),
   --<is3GVarLenList lengthElem="length"/>
   --<storage>array</storage>
   dataType CIoTDataTypes,
   --<inline/>
   containerContents CHOICE {
      --<selector element="dataType" value="0"/>
      ctrlPlaneUserData SEQUENCE {
         ddx INTEGER (0..3),
         pduSessionId INTEGER (0..7)
      },
      --<selector element="dataType" value="1"/>
      sms SEQUENCE {
         spare INTEGER (0..31) DEFAULT 0
      },
      --<selector element="dataType" value="2"/>
      locSvcsMsgContainer SEQUENCE {
         ddx INTEGER (0..3),
         spare INTEGER (0..7) DEFAULT 0,
         addlInfoLen INTEGER (0..255),
         --<noPresentBit/>
         --<length expr="@.addlInfoLen"/>
         addlInfo OCTET STRING OPTIONAL
      }
   },
   --<length fixed-size="0"/>
   contents OCTET STRING
}

CIoTDataTypes ::= ENUMERATED {
   ciotCtrlPlaneUserData(0), ciotSMS(1), ciotLocSvcsMsg(2), ciotMAX(7)
} 

/* 9.11.3.18C - Ciphering key data */
CipheringKeyData ::= SEQUENCE {
   --<is3GLength bitFieldSize="16"/>
   length INTEGER (1..65535),
   --<is3GVarLenList lengthElem="length"/>
   --<storage>array</storage>
   dataSet SEQUENCE (SIZE (1..16)) OF CipherDataSet
}

CipherDataSet ::= SEQUENCE {
   cipherKey OCTET STRING (SIZE (16)),
   spare1 INTEGER (0..7) DEFAULT 0,
   c0Len INTEGER (0..31),
   --<length expr="@c0Len"/>
   c0 OCTET STRING,
   spare2 INTEGER (0..15) DEFAULT 0,
   eutraPosSIBLen INTEGER (0..15),
   eutraPosSIBType SEQUENCE (SIZE (32)) OF BOOLEAN,
   spare3 INTEGER (0..15) DEFAULT 0,
   nrPosSIBLen INTEGER (0..15),
   nrPosSIBType SEQUENCE (SIZE (37)) OF BOOLEAN,
   spare4 INTEGER (0..7) DEFAULT 0,
   validityStartTime TimeZoneAndTime,
   validityDuration INTEGER (0..65535),
   taiList TrackingAreaIdentList
}

/* 9.11.3.18D - Control plane service type */
ControlPlaneServiceType ::= SEQUENCE {
   spare BOOLEAN DEFAULT FALSE,
   value INTEGER (0..7)
}

/* 9.11.3.20 - Deregistration type */
DeregistrationType ::= SEQUENCE {
   switchOff BOOLEAN,
   reregReqd BOOLEAN,
   accessType INTEGER (0..3)
}

/* 9.11.3.24 - EPS NAS message container */
EPSMessageContainer ::= SEQUENCE {
   --<is3GLength bitFieldSize="16"/>
   length INTEGER (1..65535),
   --<is3GVarLenList lengthElem="length"/>
   contents SEQUENCE OF NASMessageContainer
}

/* 9.11.3.29 - LADN Indication */
LADNIndication ::= SEQUENCE {
   --<is3GLength bitFieldSize="16"/>
   length INTEGER (0..65535),
   --<is3GVarLenList lengthElem="length"/>
   --<noPresentBit/>
   contents SEQUENCE (SIZE (0..8)) OF DNNList OPTIONAL
}

/* 9.11.3.30 - LADN */
LADNList ::= SEQUENCE {
   --<is3GLength bitFieldSize="16"/>
   length INTEGER (1..1715),
   --<is3GVarLenList lengthElem="length"/>
   contents SEQUENCE (SIZE (0..8)) OF LADN
}

LADN ::= SEQUENCE {
   dnn DNNList,
   tai TrackingAreaIdent
}

/* 9.11.3.31 - MICO indication */
MICOIndication ::= SEQUENCE {
   spare INTEGER (0..3) DEFAULT 0,
   sprti BOOLEAN,
   raai BOOLEAN
}

/* 9.11.3.31A - MA PDU session information */
MAPDUSessionInfo ::= ENUMERATED {   
   networkUpgAllowed(1), mapduMAX(15)
}

/* 9.11.3.31B - Mapped NSSAI */
MappedNSSAI ::= SEQUENCE {
   --<is3GLength/>
   length INTEGER (1..255),
   --<is3GVarLenList lengthElem="length"/>
   contents SEQUENCE (SIZE (1..8)) OF MappedSNSSAIContent
}

MappedSNSSAIContent ::= SEQUENCE {
   length INTEGER (1..255),
   mappedSST OCTET STRING (SIZE (1)),
   --<noPresentBit/>
   mappedSD OCTET STRING OPTIONAL
}

/* 9.11.3.32 - NAS key set identifier */
/* Defined in TS24301IEs.asn */

/* 9.11.3.33 - NAS message container */
/* Different from NASMessageContainer defined in 24.301... */
NASMessageContainer2 ::= SEQUENCE {
   --<is3GLength bitFieldSize="16"/>
   length INTEGER (1..65535),
   --<length fixed-size="0"/>
   contents OCTET STRING (SIZE (1..65535))
} 

/* 9.11.3.34 - NAS security algorithms */
NASSecurityAlgorithm ::= SEQUENCE {
   cipherType CipherTypes,
   protectionType ProtectionTypes
}

CipherTypes ::= ENUMERATED {
   ia0(0), ia1(1), ia2(2), ia3(3), ia4(4), ia5(5), ia6(6), ia7(7),
   cipherTypeMAX(15)
}

ProtectionTypes ::= ENUMERATED {
   ea0(0), ea1(1), ea2(2), ea3(3), ea4(4), ea5(5), ea6(6), ea7(7),
   protectionTypeMAX(15)
}

/* 9.11.3.36 - Network slicing indication */
NetSliceIndication ::= SEQUENCE {
   spare INTEGER (0..3) DEFAULT 0,
   dcni BOOLEAN,
   nssci BOOLEAN
}

/* 9.11.3.37 - NSSAI */
NSSAI ::= SEQUENCE {
   --<is3GLength/>
   length INTEGER (1..255),
   --<is3GVarLenList lengthElem="length"/>
   contents SEQUENCE (SIZE (1..16)) OF SNSSAI
}

/* 9.11.3.37A - NSSAI inclusion mode */
NSSAIInclusionMode ::= SEQUENCE {
   spare INTEGER (0..3) DEFAULT 0,
   inclusionMode ENUMERATED {
      modeA(0), modeB(1), modeC(2), modeD(3)
   }
}

/* 9.11.3.38 - Operator defined access category definitions */
AccessCategoryDefinitions ::= SEQUENCE {
   --<is3GLength bitFieldSize="16"/>
   length INTEGER (1..65535),
   --<is3GVarLenList lengthElem="length"/>
   --<noPresentBit/>
   contents SEQUENCE OF AccessCategoryDefinition OPTIONAL
}

AccessCategoryDefinition ::= SEQUENCE {
   precedence INTEGER (1..255),
   psac BOOLEAN,
   spare INTEGER (0..3) DEFAULT 0,
   categoryNum INTEGER (0..31),
   --<is3GLength/>
   length INTEGER (1..255),
   --<is3GVarLenList lengthElem="length"/>
   criteria SEQUENCE OF OCTET STRING,
   --<noPresentBit/>
   categories SEQUENCE {
      spare2 INTEGER (0..7) DEFAULT 0,
      accessCategory AccessCategories
   } OPTIONAL
}

AccessCategories ::= ENUMERATED {
   category0(0), category1(1), category2(2), category3(3), category4(4),
   category5(5), category6(6), category7(7), categoryMAX(31)
}

/* 9.11.3.39 - Payload container
   Warning: this type covers the specific case where the payload container
   type is 15 (Multiple payloads).
*/
MultiPayloadContainer ::= SEQUENCE {
   --<is3GLength bitFieldSize="16"/>
   length INTEGER (1..65535),
   contents PayloadContainerContents
} 

PayloadContainerContents ::= SEQUENCE {
   numEntries INTEGER (0..255),
   --<inline/>
   --<length expr="@numEntries"/>
   entries SEQUENCE (SIZE (0..255)) OF PayloadContainerEntry
}

PayloadContainerEntry ::= SEQUENCE {
   entryLength INTEGER (1..255),
   numOptIEs INTEGER (1..15),
   type PayloadContainerType,
   --<inline/>
   --<length expr="@numOptIEs"/>
   optionalIEs SEQUENCE (SIZE (1..15)) OF OptionalIE,
   contents OCTET STRING (SIZE (0..65535))
}

OptionalIE ::= SEQUENCE {
   type INTEGER (0..255),
   value OCTET STRING   -- (preceeded by 1 octet length)
}

/* 9.11.3.40 - Payload container type */
PayloadContainerType ::= ENUMERATED {
   n1SmInfo(1), sms(2), lppMessage(3), transparent(4), uePolicy(5),
   ueParams(6), locSvcs(7), ciotUserData(8), multPayloads(15)
} 

/* 9.11.3.41 - PDU session identity 2 */
PDUSessionId2 ::= INTEGER (0..255)

/* 9.11.3.42 - PDU session reactivation result */
SessionReactivateRslt ::= SEQUENCE {
   --<is3GLength/>
   length INTEGER (1..255),
   psi SEQUENCE (SIZE (16)) OF BOOLEAN,
   --<length fixed-size="0"/>
   --<noPresentBit/>
   spare OCTET STRING OPTIONAL
}

/* 9.11.3.43 - PDU session reactivation result error cause */
SessionReactivateCause ::= SEQUENCE {
   --<is3GLength bitFieldSize="16"/>
   length INTEGER (1..512),
   --<is3GVarLenList lengthElem="length"/>
   reactivateCause SEQUENCE (SIZE (1..255)) OF ReactivateCause
}

ReactivateCause ::= SEQUENCE {
   sessionId INTEGER (0..255),
   cause MMCause
}

/* 9.11.3.44 - PDU session status */
PDUSessionStatus ::= SessionReactivateRslt

/* 9.11.3.46 - Rejected NSSAI */
RejectedNSSAIList ::= SEQUENCE {
   --<is3GLength/>
   length INTEGER (1..255),
   --<is3GVarLenList lengthElem="length"/>
   rejectedNSSAI SEQUENCE (SIZE (1..8)) OF RejectedNSSAI
}

RejectedNSSAI ::= SEQUENCE {
   length INTEGER (1..15),
   cause  ENUMERATED { unavailInCurrPlmn(0), unavailInCurrRegisArea(1),
                       authPending(2), causeMAX(15) },
   sst SST,
   --<noPresentBit/>
   sd SD OPTIONAL
}

/* 9.11.3.47 - Request type */
RequestType ::= SEQUENCE {
   spare BOOLEAN DEFAULT FALSE,
   reqType RequestTypes
}

RequestTypes ::= ENUMERATED {
 initialReq(1), existPduSession(2), initialEmerReq(3), emerPduSession(4),
 modifyReq(5), maPduReq(6), reqTypeMAX(7)
}

/* 9.11.3.50 - Service type */
ServiceType ::= ENUMERATED {
   signaling(0), data(1), mobTermSvc(2), emerSvc(3), emerSvcFallback(4),
   hiPriAccess(5), elevSignal(6), serviceTypeMAX(15)
}

/* 9.11.3.50A - SMS indication */
SMSIndication ::= SEQUENCE {
   spare INTEGER (0..7) DEFAULT 0,
   sai BOOLEAN
}

/* 9.11.3.51 - SOR transparent container */

/* This IE requires custom decoding due to the lowest bit in the header octet
   determining whether the IE contains steering or ack of steering information.
*/
SORTransparentContainer ::= SEQUENCE {
   --<is3GLength bitFieldSize="16"/>
   length INTEGER (0..65535),
   steeringOrAck CHOICE {
      steering SORSteering,
      ack SORAck
   }
}

/* SOR for data type = 0 (steering of roaming information) */
SORSteering ::= SEQUENCE {
   spare INTEGER (0..7) DEFAULT 0,
   ap BOOLEAN,
   ack BOOLEAN,
   listType INTEGER(0..1),
   listInd BOOLEAN,
   dataType INTEGER(0..1) DEFAULT 0,   /* always 0 */
   sorMAC OCTET STRING (SIZE (16)),
   counter OCTET STRING (SIZE (2)),
   --<inline/>
   --<noPresentBit/>
   content CHOICE {
      --<selector element="listType" value="0"/>      
      --<length fixed-size="0"/>
      securedPacket OCTET STRING,
      --<selector element="listType" value="1"/>    
      --<length fixed-size="0"/>
      plmnAccess SEQUENCE OF PLMNTechList
   } OPTIONAL
}

/* SOR for data type = 1 (ack of steering of roaming information) */
SORAck ::= SEQUENCE {
   spare INTEGER (0..63) DEFAULT 0,
   mssi BOOLEAN,
   dataType INTEGER(0..1) DEFAULT 1,   /* always 1 */
   sorMAC OCTET STRING(SIZE(16))
}

PLMNTechList ::= SEQUENCE {
    id OCTET STRING (SIZE(3)),
    techId OCTET STRING (SIZE(2))
}

/* 9.11.3.53A - UE Parameters Update Transparent Container */

/* This IE requires custom decoding due to the lowest bit in the header octet
   determining whether the IE contains an update list or ack of an update list.
*/   
UEParamUpdateContainer ::= SEQUENCE {
   --<is3GLength bitFieldSize="16"/>
   length INTEGER (0..65535),
   updateOrAck CHOICE {
      update UEParamUpdate,
      ack UEParamUpdateAck
   }
}

/* UE Param Update for data type = 0 (UE parameters update list) */
UEParamUpdate ::= SEQUENCE {
   spare INTEGER (0..31) DEFAULT 0,
   reg BOOLEAN,
   ack BOOLEAN,
   dataType INTEGER(0..1) DEFAULT 0, /* always 0 */
   mac OCTET STRING (SIZE(16)),
   counter OCTET STRING (SIZE(2)),
   --<length fixed-size="0"/>
   updateList SEQUENCE OF UEParamUpdateDataSet
}

UEParamUpdateDataSet ::= SEQUENCE {
   spare INTEGER (0..15),
   dataSetType INTEGER(0..15),
   dataSetLen INTEGER(0..65535),
   --<inline/>
   dataSet CHOICE {
      --<selector element="dataSetType" value="1"/>      
      --<length expr="@dataSetLen"/>
      securedPacket OCTET STRING,
      --<selector element="dataSetType" value="2"/>      
      --<length expr="@dataSetLen"/>
      defCfgNSSAI OCTET STRING
   }
}

/* UE Param Update for data type = 1 (UE parameters update list acknowledgement)
*/
UEParamUpdateAck ::= SEQUENCE {
   spare INTEGER (0..127) DEFAULT 0,
   dataType INTEGER(0..1) DEFAULT 1, /* always 1 */
   mac OCTET STRING (SIZE(16))
}

/* 9.11.3.54 - UE security capability */
UESecurityCapability ::= SEQUENCE {
   --<is3GLength/>
   length INTEGER (0..255),

   /* octet 3 */
   ea0 BOOLEAN,
   ea1 BOOLEAN,
   ea2 BOOLEAN,
   ea3 BOOLEAN,
   ea4 BOOLEAN,
   ea5 BOOLEAN,
   ea6 BOOLEAN,
   ea7 BOOLEAN,

   /* octet 4 */
   ia0 BOOLEAN,
   ia1 BOOLEAN,
   ia2 BOOLEAN,
   ia3 BOOLEAN,
   ia4 BOOLEAN,
   ia5 BOOLEAN,
   ia6 BOOLEAN,
   ia7 BOOLEAN,

   /* octet 5 */
   --<noPresentBit/>
   octet5 SEQUENCE {
      eea0 BOOLEAN,
      eea1 BOOLEAN,
      eea2 BOOLEAN,
      eea3 BOOLEAN,
      eea4 BOOLEAN,
      eea5 BOOLEAN,
      eea6 BOOLEAN,
      eea7 BOOLEAN
   } OPTIONAL,

   /* octet 6 */
   --<noPresentBit/>
   octet6 SEQUENCE {
      eia0 BOOLEAN,
      eia1 BOOLEAN,
      eia2 BOOLEAN,
      eia3 BOOLEAN,
      eia4 BOOLEAN,
      eia5 BOOLEAN,
      eia6 BOOLEAN,
      eia7 BOOLEAN
   } OPTIONAL,

   --<noPresentBit/>
   spare OCTET STRING OPTIONAL
}

/* 9.11.3.55 - UE usage setting */
UEUsageSetting ::= SEQUENCE {
   --<is3GLength/>
   length INTEGER (0..255) DEFAULT 3, 
   spare INTEGER (0..127) DEFAULT 0, 
   usage BOOLEAN
}

/* 9.11.3.56 - UE status */
/* Defined in TS24301IEs.asn */

/* 9.11.3.57 - Uplink data status */
UplinkDataStatus ::= SEQUENCE {
   --<is3GLength/>
   length INTEGER (2..255),
   spare1 BOOLEAN DEFAULT FALSE,
   psi SEQUENCE (SIZE (15)) OF BOOLEAN,
   --<noPresentBit/>
   spare2 OCTET STRING OPTIONAL
}

/* 9.11.3.68 - UE radio capability ID */
/* Defined in TS24301IEs.asn */

/* 9.11.3.69 - UE radio capability ID deletion indication */
/* Defined in TS24301IEs.asn */

/* 9.11.3.70 - Truncated 5G-S-TMSI configuration */
TruncatedTMSIConfig ::= SEQUENCE {
   --<is3GLength/>
   length INTEGER (0..255),
   truncatedAMFId INTEGER (0..15),
   truncatedAMFPtr INTEGER (0..15)
}

/* 9.11.3.72 - N5GC indication - added in v16.6 */
N5GCIndication ::= SEQUENCE {
   spare INTEGER (0..7) DEFAULT 0,
   n5gcReg BOOLEAN
}

/* 9.11.3.73 - NB-N1 mode DRX parameters - added in v16.5 */
NBN1ModeDRXParams ::= SEQUENCE {
   --<is3GLength/>
   length INTEGER (0..255),
   spare INTEGER (0..15) DEFAULT 0,
   drxValue INTEGER (0..15)
}

/* 9.11.3.74 - Additional configuration indication - added in v16.5 */
AddlConfigIndication ::= SEQUENCE {
   spare INTEGER (0..7) DEFAULT 0,
   scmr BOOLEAN
}

/* 9.11.3.75 - Extended rejected NSSAI - added in v17.0 */
ExtRejectedNSSAIList ::= SEQUENCE {
   --<is3GLength/>
   length INTEGER (1..255),
   --<is3GVarLenList lengthElem="length"/>
   rejectedNSSAI SEQUENCE (SIZE (1..8)) OF PartialExtRejectedNSSAI
}

PartialExtRejectedNSSAI ::= SEQUENCE {  -- Added in v17.3
   spare BOOLEAN DEFAULT FALSE,
   listType PERNTypes,
   numElems INTEGER (1..15),
   --<inline/>
   backoffTimer CHOICE {
      --<selector element="listType" value="0"/>
      withoutTimer NULL,
      --<selector element="listType" value="1"/>
      timerValue INTEGER (1..255)
   },
   --<inline/>
   --<length expr="@numElems"/>
   rejectedSNSSAI SEQUENCE (SIZE (1..8)) OF ExtRejectedNSSAI
}

PERNTypes ::= ENUMERATED {
   pernWithoutTimer(0), pernWithTimer(1), pernTypeMAX(7)
}

ExtRejectedNSSAI ::= SEQUENCE {
   length INTEGER (1..15),
   cause  ENUMERATED { unavailInCurrPlmn(0), unavailInCurrRegisArea(1),
                       authPending(2), maxUEsReached(3), causeMAX(15) },
   sst SST,
   --<noPresentBit/>
   sd SD OPTIONAL,
   --<noPresentBit/>
   mappedSST OCTET STRING (SIZE (1)) OPTIONAL,
   --<noPresentBit/>
   mappedSD OCTET STRING (SIZE (3)) OPTIONAL
}

/* 9.11.3.77 - Paging restriction - added in v17.3 */
/* Defined in TS24301IEs.asn */

/* 9.11.3.78 - MCC list - added in v17.3 */
MCCList ::= SEQUENCE {
   --<is3GLength/>
   length INTEGER (0..255),
   --<is3GVarLenList lengthElem="length"/>
   mccElements SEQUENCE OF MCCElement
}

MCCElement ::= SEQUENCE {
   mccDigit2 INTEGER (0..15),
   mccDigit1 INTEGER (0..15),
   mccInd BOOLEAN,
   spare INTEGER (0..7) DEFAULT 0,
   mccDigit3 INTEGER (0..15)
}

/* 9.11.3.79 - NID - added in v17.3 */
NetworkId ::= SEQUENCE {
   --<is3GLength/>
   length INTEGER (0..255),
   nidDigit1 INTEGER (0..15),
   assignMode INTEGER (0..15),
   nidDigit3 INTEGER (0..15),
   nidDigit2 INTEGER (0..15),
   nidDigit5 INTEGER (0..15),
   nidDigit4 INTEGER (0..15),
   nidDigit7 INTEGER (0..15),
   nidDigit6 INTEGER (0..15),
   nidDigit9 INTEGER (0..15),
   nidDigit8 INTEGER (0..15),
   spare INTEGER (0..15) DEFAULT 0,
   nidDigit10 INTEGER (0..15)
}


/* 9.11.4.1 - SM capability */
SMCapability ::= SEQUENCE {
   --<is3GLength/>
   length INTEGER (0..255),

   /* octet 3 */
   tpmic BOOLEAN,
   atsll ATSSSModes,
   epts1 BOOLEAN,
   mh6Pdu BOOLEAN,
   rqos BOOLEAN,

   --<noPresentBit/>
   /* octet 4 */
   octet4 SEQUENCE { -- Added in v17.3
      spare INTEGER (0..127) DEFAULT 0,
      nonDefQosRule BOOLEAN       
   } OPTIONAL,

   --<noPresentBit/>
   spare OCTET STRING OPTIONAL
}

ATSSSModes ::= ENUMERATED {
   unsupported(0), lowLayer(1), activeOnly(2), anyMode(3), atsssModeMAX(15)
}

/* 9.11.4.2 - SM cause */
SMCause ::= INTEGER (0..255)

/* 9.11.4.3 - Always-on PDU session indication */
AlwaysOnPDUSessionInd ::= SEQUENCE {
   spare INTEGER (0..7) DEFAULT 0,
   apsi BOOLEAN
}

/* 9.11.4.4 - Always-on PDU session requested */
AlwaysOnPDUSessionReq ::= SEQUENCE {
   spare INTEGER (0..7) DEFAULT 0,
   apsr BOOLEAN
}

/* 9.11.4.5 - Allowed SSC mode */
AllowedSSCMode ::= SEQUENCE {
   spare BOOLEAN DEFAULT FALSE,
   ssc3 BOOLEAN,
   ssc2 BOOLEAN,
   ssc1 BOOLEAN
}

/* 9.11.4.7 - Integrity protection maximum data rate */
IntegrityProtMaxDataRate ::= SEQUENCE {
   maxUEDataRateUplink INTEGER (0..255),
   maxUEDataRateDownlink INTEGER (0..255)
}

/* 9.11.4.8 - Mapped EPS bearer contexts */
EPSBearerCtxts ::= SEQUENCE {
   --<is3GLength bitFieldSize="16"/>
   length INTEGER (7..65535),
   --<is3GVarLenList lengthElem="length"/>
   epsBearerCtxts SEQUENCE OF EPSBearerCtxt
}

EPSBearerCtxt ::= SEQUENCE {
   bearerId INTEGER (0..255),
   bearerCtxtLen INTEGER (0..65535),
   opCode INTEGER (0..3),
   spare BOOLEAN DEFAULT FALSE,
   eBit BOOLEAN,
   numParams INTEGER (0..15),
   --<inline/>
   --<length expr="@numParams"/>
   --<noPresentBit/>
   paramsList SEQUENCE (SIZE (0..15)) OF EPSParam OPTIONAL
}

EPSParamId ::= ENUMERATED {
   epsQoS(1), extEpsQoS(2), tft(3),
   apnAmbr(4), extApnAmbr(5), epsParamMax(255), ...
}

EPSParam ::= SEQUENCE {
   id EPSParamId,
   --<inline/>
   content CHOICE {
      --<selector element="id" value="1"/>
      epsQoS EPSQualityOfService,
      --<selector element="id" value="2"/>
      extEpsQos ExtQualityOfService,
      --<selector element="id" value="3"/>
      tft TFT,
      --<selector element="id" value="4"/>
      apnAmbr APNAggMaxBitRate,
      --<selector element="id" value="5"/>
      extApnAmbr ExtAPNAggMaxBitRate,
      unknown OCTET STRING
   }
}

/* 9.11.4.9 - Maximum number of supported packet filters */
MaxSupportedPacketFilters ::= SEQUENCE {
   maxFilters INTEGER (1..2047),
   spare INTEGER (0..31) DEFAULT 0
}

/* 9.11.4.10 - PDU address */
PDUAddress ::= SEQUENCE {
   --<is3GLength/>
   length INTEGER (1..255),
   spare INTEGER (0..15) DEFAULT 0,
   s16LLA INTEGER (0..1),  -- Added in v16.6
   sessionType PDUAddressValues,
   --<inline/>
   addressInfo CHOICE {
      --<selector element="sessionType" value="1"/>
      addressInfoIpv4 OCTET STRING (SIZE (4)),
      --<selector element="sessionType" value="2"/>
      addressInfoIpv6 OCTET STRING (SIZE (8)),
      --<selector element="sessionType" value="3"/>
      --<inline/>
      addressInfoIpv4v6 SEQUENCE {
         ipv6 OCTET STRING (SIZE (8)),
         ipv4 OCTET STRING (SIZE (4))
      }
   },
   --<inline/>
   smfIp6Addr CHOICE {  -- Added in v16.6
      --<selector element="s16LLA" value="0"/>
      absent NULL,
      --<selector element="s16LLA" value="1"/>
      present OCTET STRING (SIZE (8))
   }
}

PDUAddressValues ::= ENUMERATED {
   ipv4(1), ipv6(2), ipv4v6(3), pduAddrValMAX(7)
}

/* 9.11.4.11 - PDU session type */
PDUSessionType ::= SEQUENCE {
   spare BOOLEAN DEFAULT FALSE,
   sessionType SessionType
}

SessionType ::= ENUMERATED {
   st_ipv4(1), st_ipv6(2), st_ipv4v6(3), st_unstructured(4), st_eth(5),
   st_MAX(7)
}

/* 9.11.4.12 - QoS flow descriptions */
QOSFlowDescriptions ::= SEQUENCE {
   --<is3GLength bitFieldSize="16"/>
   length INTEGER (6..65535),
   --<is3GVarLenList lengthElem="length"/>
   qosFlowDesr SEQUENCE OF QOSFlowDescription
}

QOSFlowDescription ::= SEQUENCE {
   spare INTEGER (0..3) DEFAULT 0,
   qfi INTEGER (0..63),
   opCode FlowOpCodes,
   spare2 INTEGER (0..31) DEFAULT 0,
   spare3 BOOLEAN DEFAULT FALSE,
   eBit BOOLEAN,
   numParams INTEGER (0..63),
   --<inline/>
   --<length expr="@numParams"/>
   --<noPresentBit/>
   paramsList SEQUENCE (SIZE (0..63)) OF Parameter OPTIONAL
}

ParameterId ::= ENUMERATED {
   fiveQI(1), gfbrUL(2), gfbrDL(3), mfbrUL(4), mfbrDL(5),
   avgWindow(6), epsBearerIdent(7), paramIdMax(255), ...
}

FlowRateUnit ::= INTEGER {
   notUsed(0), kbps-1(1), kbps-4(2), kbps-16(3), kbps-64(4),
   kbps-256(5), mbps-1(6), mbps-4(7), mbps-16(8), mbps-64(9),
   mbps-256(10), gbps-1(11), gbps-4(12), gbps-16(13), gbps-64(14),
   gbps-256(15), tbps-1(16), tbps-4(17), tbps-16(18), tbps-64(19),
   tbps-256(20), pbps-1(21), pbps-4(22), pbps-16(23), pbps-64(24),
   pbps-256(25) } (0..255)

Parameter ::= SEQUENCE {
   id ParameterId,
   --<is3GLength/>
   length INTEGER(0..255),
   --<inline/>
   content CHOICE {
      --<selector element="id" value="1"/>
      fiveQI INTEGER(0..255),
      --<selector element="id" value="2"/>
      gfbrUL SEQUENCE {
         unit FlowRateUnit,
         guarFlow INTEGER(0..65535)
      },
      --<selector element="id" value="3"/>
      gfbrDL SEQUENCE {
         unit FlowRateUnit,
         guarFlow INTEGER(0..65535)
      },
      --<selector element="id" value="4"/>
      mfbrUL  SEQUENCE {
         unit FlowRateUnit,
         guarFlow INTEGER(0..65535)
      },
      --<selector element="id" value="5"/>
      mfbrDL  SEQUENCE {
         unit FlowRateUnit,
         guarFlow INTEGER(0..65535)
      },
      --<selector element="id" value="6"/>
      avgWindow INTEGER(0..65535),
      --<selector element="id" value="7"/>
      epsBearerIdent SEQUENCE {
         value INTEGER(0..15),
         spare INTEGER(0..15)
      },
      --<length fixed-size="0"/>
      unknown OCTET STRING
   }
}

FlowOpCodes ::= ENUMERATED {
   flowCreate(1), flowDelete(2), flowModify(3), ruleOpMax(7)
}

/* 9.11.4.13 - QoS rules */
QoSRules ::= SEQUENCE {
   --<is3GLength bitFieldSize="16"/>
   length INTEGER (0..65535),
   --<is3GVarLenList lengthElem="length"/>
   rules SEQUENCE OF QoSRule
}

QoSRule ::= SEQUENCE {
   ruleId INTEGER (0..255),
   ruleLen INTEGER (0..65535),
   ruleOpCode RuleOpCodes,
   dqr BOOLEAN,
   numPacketFilters INTEGER (0..15),
   --<inline/>
   packetFilterList CHOICE {
      --<selector element="ruleOpCode" value="1"/>
      --<length expr="@numPacketFilters"/>
      createNew SEQUENCE (SIZE (0..15)) OF PFCreateNew,
      --<selector element="ruleOpCode" value="2"/>
      delete NULL,
      --<selector element="ruleOpCode" value="3"/>
      --<length expr="@numPacketFilters"/>
      modifyAndAdd SEQUENCE (SIZE (1..15)) OF PFCreateNew,
      --<selector element="ruleOpCode" value="4"/>
      --<length expr="@numPacketFilters"/>
      modifyAndReplace SEQUENCE (SIZE (0..15)) OF PFCreateNew,
      --<selector element="ruleOpCode" value="5"/>
      --<length expr="@numPacketFilters"/>
      modifyAndDelete SEQUENCE (SIZE (1..15)) OF PFModifyAndDelete,
      --<selector element="ruleOpCode" value="6"/>
      modifyNoModify NULL
   },
   precedence INTEGER (0..255),
   spare1 BOOLEAN DEFAULT FALSE,
   segregation BOOLEAN,
   flowId INTEGER (0..63)
}

RuleOpCodes ::= ENUMERATED {
   createNew(1), delete(2), modifyAndAdd(3), modifyAndReplace(4), 
   modifyAndDelete(5), modifyNoModify(6), ruleOpMax(7)
}

PFModifyAndDelete ::= SEQUENCE {
   spare INTEGER (0..15) DEFAULT 0,
   filterId INTEGER (0..15)
}

PFCreateNew ::= SEQUENCE {
   spare INTEGER (0..3) DEFAULT 0,
   filterDirection INTEGER (0..3),
   filterId INTEGER (0..15),
   --<is3GLength/>
   filterContentLen INTEGER (0..255),
   --<is3GVarLenList lengthElem="filterContentLen"/>
   filterContent SEQUENCE OF PFComponent
}

PFComponent ::= SEQUENCE {
   typeId PacketFilterTypeId,
   --<inline/>
   value CHOICE {
      --<selector element="typeId" value="1"/>
      matchAll NULL,
      --<selector element="typeId" value="16"/>
      ipv4Remote OCTET STRING (SIZE (8)),
      --<selector element="typeId" value="17"/>
      ipv4Local OCTET STRING (SIZE (8)),
      --<selector element="typeId" value="33"/>
      ipv6Remote OCTET STRING (SIZE (17)),
      --<selector element="typeId" value="35"/>
      ipv6Local OCTET STRING (SIZE (17)),
      --<selector element="typeId" value="48"/>
      protId OCTET STRING (SIZE (1)),
      --<selector element="typeId" value="64"/>
      singleLocalPort OCTET STRING (SIZE (2)),
      --<selector element="typeId" value="65"/>
      localPortRange OCTET STRING (SIZE (4)),
      --<selector element="typeId" value="80"/>
      singleRemPort OCTET STRING (SIZE (2)),
      --<selector element="typeId" value="81"/>
      remPortRange OCTET STRING (SIZE (4)),
      --<selector element="typeId" value="96"/>
      secParam OCTET STRING (SIZE (4)),
      --<selector element="typeId" value="112"/>
      typeOfSvc OCTET STRING (SIZE (2)),
      --<selector element="typeId" value="128"/>
      flowLabel OCTET STRING (SIZE (3)),
      --<selector element="typeId" value="129"/>
      destMacAddr OCTET STRING (SIZE (6)),
      --<selector element="typeId" value="130"/>
      srcMacAddr OCTET STRING (SIZE (6)),
      --<selector element="typeId" value="131"/>
      ctagVid OCTET STRING (SIZE (2)),
      --<selector element="typeId" value="132"/>
      stagVid OCTET STRING (SIZE (2)),
      --<selector element="typeId" value="133"/>
      ctagPcp OCTET STRING (SIZE (1)),
      --<selector element="typeId" value="134"/>
      stagPcp OCTET STRING (SIZE (1)),
      --<selector element="typeId" value="135"/>
      ethernet OCTET STRING (SIZE (2))
   }
}

PacketFilterTypeId ::= ENUMERATED {
   matchAll(1), ipv4Remote(16), ipv4Local(17), ipv6Remote(33), ipv6Local(35),
   protId(48), singleLocalPort(64), localPortRange(65), singleRemPort(80),
   remPortRange(81), secParam(96), typeOfSvc(112), flowLabel(128),
   destMacAddr(129), srcMacAddr(130), ctagVid(131), stagVid(132),
   ctagPcp(133), stagPcp(134), ethernet(135), typeIdMax(255)
}

/* 9.11.4.14 - Session AMBR */
SessionAMBR ::= SEQUENCE {
   --<is3GLength/>
   length INTEGER (0..255) DEFAULT 8,
   unitAmbrDL INTEGER (0..255),
   sessionAmbrDL INTEGER (0..65535),
   unitAmbrUL INTEGER (0..255),
   sessionAmbrUL INTEGER (0..65535)
}

/* 9.11.4.15 - SM PDU DN request container */
SmPduDnReqContainer ::= SEQUENCE {
   --<is3GLength/>
   length INTEGER (3..255),
   --<is3GVarLenList lengthElem="length"/>
   --<noPresentBit/>
   dnSpecificId OCTET STRING OPTIONAL
}

/* 9.11.4.16 - SSC mode */
SSCMode ::= SEQUENCE {
   spare BOOLEAN DEFAULT FALSE,
   sscMode SSCModeValue
}

SSCModeValue ::= ENUMERATED {
   ssc_mode1(1), ssc_mode2(2), ssc_mode3(3), ssc_MAX(7)
}

/* 9.11.4.17 - Re-attempt indicator */
ReattemptIndicator ::= SEQUENCE {
   --<is3GLength/>
   length INTEGER (1),
   spare INTEGER (0..63) DEFAULT 0,
   eplmnc BOOLEAN,
   ratc BOOLEAN
}

/* 9.11.4.18 - 5GSM network feature support */
SMNetworkFeatureSupport ::= SEQUENCE {
   --<is3GLength/>
   length INTEGER (1..255), 
   spare INTEGER (0..127) DEFAULT 0, 
   eptS1 BOOLEAN,
   --<noPresentBit/>
   --<length fixed-size="0"/>
   spare2 OCTET STRING OPTIONAL
}

/* 9.11.4.19 - Session TMBR - removed in 16.3 */
--SessionTMBR ::= SEQUENCE {
--   length INTEGER (0..255) DEFAULT 8,
--   unitTmbrDL INTEGER (0..255),
--   sessionTmbrDL INTEGER (0..65535),
--   unitTmbrUL INTEGER (0..255),
--   sessionTmbrUL INTEGER (0..65535)
--}

/* 9.11.4.21 - 5GSM congestion re-attempt indicator */
CongestionReattemptIndicator ::= SEQUENCE {
   --<is3GLength/>
   length INTEGER (1..255),
   spare INTEGER (0..127) DEFAULT 0,
   abo BOOLEAN
}

/* 9.11.4.22 - ATSSS container */
ATSSSContainer ::= SEQUENCE {
   --<is3GLength bitFieldSize="16"/>
   length INTEGER (3..65535),
   --<is3GVarLenList lengthElem="length"/>
   --<noPresentBit/>
   contents OCTET STRING OPTIONAL
}

/* 9.11.4.23 - Control plane only indication */
ControlPlaneIndication ::= SEQUENCE {
   spare INTEGER (0..7) DEFAULT 0,
   cpoi BOOLEAN
}

/* 9.11.4.24 - Header compression configuration */
HeaderCompressionConfig ::= SEQUENCE {
   --<is3GLength/>
   length INTEGER (3..255),
   spare BOOLEAN DEFAULT FALSE,
   p0x0104 BOOLEAN,
   p0x0103 BOOLEAN,
   p0x0102 BOOLEAN,
   p0x0006 BOOLEAN,
   p0x0004 BOOLEAN,
   p0x0003 BOOLEAN,
   p0x0002 BOOLEAN,
   maxCID OCTET STRING (SIZE(2)),
   --<noPresentBit/>
   addlCompressParamsType INTEGER (0..255) OPTIONAL,
   --<noPresentBit/>
   addlCompressParamsContainer OCTET STRING OPTIONAL
}

/* 9.11.4.25 - DS-TT Ethernet port MAC address */
DSTTEthMACAddr ::= SEQUENCE {
   --<is3GLength/>
   length INTEGER (1..255),
   contents OCTET STRING (SIZE(6))
}

/* 9.11.4.26 - DS-TT residence time */
DSTTResidenceTime ::= SEQUENCE {
   --<is3GLength/>
   length INTEGER (1..255),
   contents OCTET STRING (SIZE(8))
}

/* 9.11.4.27 - Port management information container */
PortMgmtInfoContainer ::= SEQUENCE {
   --<is3GLength bitFieldSize="16"/>
   length INTEGER (0..65535),
   --<is3GVarLenList lengthElem="length"/>
   container OCTET STRING (SIZE (1..65535))
}

/* 9.11.4.28 - Ethernet header compression configuration - added in v16.5 */
EthHdrCompressConfig ::= SEQUENCE {
   --<is3GLength/>
   length INTEGER (1..255),
   spare INTEGER (0..63) DEFAULT 0,
   cidLength INTEGER (0..3)
}

END
