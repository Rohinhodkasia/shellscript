CSTA-single-step-conference
	{ iso( 1) identified-organization( 3) icd-ecma( 12)
		standard( 0) csta3( 285) single-step-conference( 20) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
AccountInfo, AuthCode, CorrelatorData, ParticipationType, UserData
FROM CSTA-device-feature-types
	{ iso( 1) identified-organization( 3) icd-ecma( 12)
		standard( 0) csta3( 285) device-feature-types( 127) }
CallLinkageDataList FROM CSTA-call-control
	{ iso( 1) identified-organization( 3) icd-ecma( 12)
		standard( 0) csta3( 285) call-control( 130) }
CSTACommonArguments FROM CSTA-extension-types
	{ iso( 1) identified-organization( 3) icd-ecma( 12)
		standard( 0) csta3( 285) extension-types( 129) }
SubjectOfCall,LanguagePreferences FROM CSTA-device-feature-types
	{ iso( 1) identified-organization( 3) icd-ecma( 12)
		standard( 0) csta3( 285) device-feature-types( 127) }
ConnectionInformation FROM CSTA-media-services
	{ iso( 1) identified-organization( 3) icd-ecma( 12)
		standard( 0) csta3( 285) media-services( 136) };

singleStepConf OPERATION ::=
{ 	ARGUMENT 		SingleStepConfArgument
	RESULT 			SingleStepConfResult
	ERRORS 			{universalFailure }
	CODE 			local: 20 }

SingleStepConfArgument ::= SEQUENCE
{	activeCall 			ConnectionID,
	deviceToJoin 			DeviceID,
	participationType 		ParticipationType 			DEFAULT active,
	accountCode 			[0] IMPLICIT AccountInfo 		OPTIONAL,
	authCode 			[1] IMPLICIT AuthCode 			OPTIONAL,
	correlatorData 			[2] IMPLICIT CorrelatorData 		OPTIONAL,
	userData 			UserData 				OPTIONAL,
	subjectOfCall			[3] IMPLICIT SubjectOfCall		OPTIONAL,
	languagePreferences		[4] IMPLICIT LanguagePreferences	OPTIONAL,
	extensions 			CSTACommonArguments 			OPTIONAL }

SingleStepConfResult ::= SEQUENCE
{ 	conferencedCall 		ConnectionID,
	conferencedCallInfo 		ConnectionInformation 			OPTIONAL,
	callLinkageDataList		[1] IMPLICIT CallLinkageDataList	OPTIONAL,
	extensions 			CSTACommonArguments 			OPTIONAL }

END -- of CSTA-single-step-conference
