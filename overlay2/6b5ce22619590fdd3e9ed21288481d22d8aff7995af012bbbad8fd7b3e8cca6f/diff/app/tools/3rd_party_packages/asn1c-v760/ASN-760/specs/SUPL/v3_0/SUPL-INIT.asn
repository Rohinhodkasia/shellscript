-- This file was generated by the Objective Systems ASN1C Compiler
-- (http://www.obj-sys.com).  Version: 6.8.A, Date: 18-Nov-2014.

SUPL-INIT DEFINITIONS AUTOMATIC TAGS ::= BEGIN

IMPORTS

SLPAddress, QoP, PosMethod
FROM ULP-Components 

Ver2-SUPL-INIT-extension
FROM ULP-Version-2-message-extensions 

Ver2-Notification-extension
FROM ULP-Version-2-parameter-extensions 

Ver3-SUPL-INIT-extension
FROM ULP-Version-3-message-extensions ;

-- Productions

NotificationType ::= ENUMERATED { noNotificationNoVerification(0), 
   notificationOnly(1), notificationAndVerficationAllowedNA(2), 
   notificationAndVerficationDeniedNA(3), privacyOverride(4), ... }

EncodingType ::= ENUMERATED { ucs2(0), gsmDefault(1), utf8(2), ... }

FormatIndicator ::= ENUMERATED { logicalName(0), e-mailAddress(1), msisdn(2), 
   url(3), sipUrl(4), min(5), mdn(6), iMSPublicidentity(7), ... }

Notification ::= SEQUENCE {
   notificationType [0] NotificationType,
   encodingType [1] EncodingType OPTIONAL,
   requestorId [2] OCTET STRING (SIZE (1..maxReqLength)) OPTIONAL,
   requestorIdType [3] FormatIndicator OPTIONAL,
   clientName [4] OCTET STRING (SIZE (1..maxClientLength)) OPTIONAL,
   clientNameType [5] FormatIndicator OPTIONAL,
   ...,
   ver2-Notification-extension [6] Ver2-Notification-extension OPTIONAL
}

SLPMode ::= ENUMERATED { proxy(0), nonProxy(1) }

MAC ::= BIT STRING  (SIZE (64))

KeyIdentity ::= BIT STRING  (SIZE (128))

SUPLINIT ::= SEQUENCE {
   posMethod [0] PosMethod,
   notification [1] Notification OPTIONAL,
   sLPAddress [2] SLPAddress OPTIONAL,
   qoP [3] QoP OPTIONAL,
   sLPMode [4] SLPMode,
   mAC [5] MAC OPTIONAL,
   keyIdentity [6] KeyIdentity OPTIONAL,
   ...,
   ver2-SUPL-INIT-extension [7] Ver2-SUPL-INIT-extension OPTIONAL,
   ver3-SUPL-INIT-extension [8] Ver3-SUPL-INIT-extension OPTIONAL
}

-- Value assignments

maxReqLength INTEGER ::= 50

maxClientLength INTEGER ::= 50


END
