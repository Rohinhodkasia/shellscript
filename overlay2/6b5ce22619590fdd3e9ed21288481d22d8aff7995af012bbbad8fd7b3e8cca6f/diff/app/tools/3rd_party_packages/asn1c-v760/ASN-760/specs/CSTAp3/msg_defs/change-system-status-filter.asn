CSTA-change-system-status-filter
	{ iso( 1) identified-organization( 3) icd-ecma( 12)
		standard( 0) csta3( 285) change-system-status-filter( 206) }

DEFINITIONS ::=
BEGIN

IMPORTS
OPERATION, ERROR FROM Remote-Operations-Information-Objects
	{joint-iso-itu-t remote-operations(4) informationObjects(5) version1(0) }

-- Data Types --
universalFailure FROM CSTA-error-definition
	{ iso( 1) identified-organization( 3) icd-ecma( 12)
		standard( 0) csta3( 285) error-definition( 120) }
SysStatRegisterID, SystemStatus FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

changeSysStatFilter OPERATION ::=
{ 	ARGUMENT 		ChangeSysStatFilterArg
	RESULT 			ChangeSysStatFilterRes
	ERRORS 			{universalFailure }
	CODE 			local: 206 }

ChangeSysStatFilterArg ::= SEQUENCE
{ 	sysStatRegisterID 		SysStatRegisterID,
	requestedStatusFilter 		SystemStatus,
	extensions 			CSTACommonArguments 		OPTIONAL }

ChangeSysStatFilterRes ::= SEQUENCE
{ 	actualStatusFilter 		SystemStatus,
	extensions 			CSTACommonArguments 		OPTIONAL }

END -- of CSTA-change-system-status-filter
