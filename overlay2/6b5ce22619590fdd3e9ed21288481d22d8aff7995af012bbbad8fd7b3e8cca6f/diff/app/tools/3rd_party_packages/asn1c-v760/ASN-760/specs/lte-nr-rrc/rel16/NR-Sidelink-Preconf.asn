-- This file was generated by the Objective Systems ASN1C Compiler
-- (http://www.obj-sys.com).  Version: 7.5.1.1, Date: 09-Jul-2021.

NR-Sidelink-Preconf DEFINITIONS AUTOMATIC TAGS ::= BEGIN

IMPORTS

SL-FreqConfigCommon-r16, SL-RadioBearerConfig-r16, SL-RLC-BearerConfig-r16, 
   SL-EUTRA-AnchorCarrierFreqList-r16, SL-NR-AnchorCarrierFreqList-r16, 
   SL-MeasConfigCommon-r16, SL-UE-SelectedConfig-r16, TDD-UL-DL-ConfigCommon, 
   maxNrofFreqSL-r16, maxNrofSLRB-r16, maxSL-LCID-r16
FROM NR-RRC-Definitions ;

-- Productions

SL-PreconfigGeneral-r16 ::= SEQUENCE {
   sl-TDD-Configuration-r16 [0] TDD-UL-DL-ConfigCommon OPTIONAL,
   reservedBits-r16 [1] BIT STRING  (SIZE (2)) OPTIONAL,
   ...
}

SL-RoHC-Profiles-r16 ::= SEQUENCE {
   profile0x0001-r16 [0] BOOLEAN,
   profile0x0002-r16 [1] BOOLEAN,
   profile0x0003-r16 [2] BOOLEAN,
   profile0x0004-r16 [3] BOOLEAN,
   profile0x0006-r16 [4] BOOLEAN,
   profile0x0101-r16 [5] BOOLEAN,
   profile0x0102-r16 [6] BOOLEAN,
   profile0x0103-r16 [7] BOOLEAN,
   profile0x0104-r16 [8] BOOLEAN
}

SidelinkPreconfigNR-r16 ::= SEQUENCE {
   sl-PreconfigFreqInfoList-r16 [0] SEQUENCE (SIZE (1..maxNrofFreqSL-r16)) OF 
      SL-FreqConfigCommon-r16 OPTIONAL,
   sl-PreconfigNR-AnchorCarrierFreqList-r16 [1] SL-NR-AnchorCarrierFreqList-r16
       OPTIONAL,
   sl-PreconfigEUTRA-AnchorCarrierFreqList-r16 [2] 
      SL-EUTRA-AnchorCarrierFreqList-r16 OPTIONAL,
   sl-RadioBearerPreConfigList-r16 [3] SEQUENCE (SIZE (1..maxNrofSLRB-r16)) OF 
      SL-RadioBearerConfig-r16 OPTIONAL,
   sl-RLC-BearerPreConfigList-r16 [4] SEQUENCE (SIZE (1..maxSL-LCID-r16)) OF 
      SL-RLC-BearerConfig-r16 OPTIONAL,
   sl-MeasPreConfig-r16 [5] SL-MeasConfigCommon-r16 OPTIONAL,
   sl-OffsetDFN-r16 [6] INTEGER (1..1000) OPTIONAL,
   t400-r16 [7] ENUMERATED { ms100(0), ms200(1), ms300(2), ms400(3), ms600(4), 
      ms1000(5), ms1500(6), ms2000(7) } OPTIONAL,
   sl-MaxNumConsecutiveDTX-r16 [8] ENUMERATED { n1(0), n2(1), n3(2), n4(3), 
      n6(4), n8(5), n16(6), n32(7) } OPTIONAL,
   sl-SSB-PriorityNR-r16 [9] INTEGER (1..8) OPTIONAL,
   sl-PreconfigGeneral-r16 [10] SL-PreconfigGeneral-r16 OPTIONAL,
   sl-UE-SelectedPreConfig-r16 [11] SL-UE-SelectedConfig-r16 OPTIONAL,
   sl-CSI-Acquisition-r16 [12] ENUMERATED { enabled(0) } OPTIONAL,
   sl-RoHC-Profiles-r16 [13] SL-RoHC-Profiles-r16 OPTIONAL,
   sl-MaxCID-r16 [14] INTEGER (1..16383) DEFAULT 15,
   ...
}

-- TAG-NR-SIDELINK-PRECONF-DEFINITIONS-STOP
-- TAG-SL-PRECONFIGURATIONNR-START
SL-PreconfigurationNR-r16 ::= SEQUENCE {
   sidelinkPreconfigNR-r16 [0] SidelinkPreconfigNR-r16,
   ...
}

END
