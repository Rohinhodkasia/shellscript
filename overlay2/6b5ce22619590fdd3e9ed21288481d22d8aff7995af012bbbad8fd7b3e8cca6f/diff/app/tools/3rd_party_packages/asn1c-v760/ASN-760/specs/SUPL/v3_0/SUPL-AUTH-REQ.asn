-- This file was generated by the Objective Systems ASN1C Compiler
-- (http://www.obj-sys.com).  Version: 6.8.A, Date: 18-Nov-2014.

SUPL-AUTH-REQ DEFINITIONS AUTOMATIC TAGS ::= BEGIN

IMPORTS

Ver
FROM ULP-Components 

SETCapabilities
FROM SUPL-START ;

-- Productions

SUPLAUTHREQ ::= SEQUENCE {
   ver [0] Ver OPTIONAL,
   sETCapabilities [1] SETCapabilities OPTIONAL,
   ...
}

END
