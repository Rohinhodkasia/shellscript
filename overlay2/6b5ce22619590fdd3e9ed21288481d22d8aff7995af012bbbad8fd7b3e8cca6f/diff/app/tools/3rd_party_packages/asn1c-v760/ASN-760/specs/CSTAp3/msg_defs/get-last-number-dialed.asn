CSTA-get-last-number-dialed
	{ iso( 1) identified-organization( 3) icd-ecma( 12)
		standard( 0) csta3( 285) get-last-number-dialed( 310) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

getLastNumberDialed OPERATION ::=
{	ARGUMENT 		GetLastNumberDialedArgument
	RESULT 			GetLastNumberDialedResult
	ERRORS 			{universalFailure }
	CODE			local: 310 }

GetLastNumberDialedArgument ::= SEQUENCE
{	device 				DeviceID,
	extensions			CSTACommonArguments 			OPTIONAL }

GetLastNumberDialedResult ::= SEQUENCE
{	numberDialed			DeviceID,
	extensions			CSTACommonArguments			OPTIONAL }

END -- of CSTA-get-last-number-dialed
