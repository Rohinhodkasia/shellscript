CSTA-stop-data-path
	{ iso( 1) identified-organization( 3) icd-ecma( 12)
		standard( 0) csta3( 285) stop-data-path( 111) }
DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IOCrossRefID, IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };
	
stopDataPath	OPERATION ::=
{	ARGUMENT		StopDataPathArgument
	RESULT			StopDataPathResult
	ERRORS			{universalFailure }
	CODE			local: 111
}

StopDataPathArgument ::= SEQUENCE
{	ioCrossRefID			IOCrossRefID,
	ioRegisterReqID			IORegisterReqID				OPTIONAL,
	extensions 			CSTACommonArguments			OPTIONAL }

StopDataPathResult ::= CHOICE
{	extensions			CSTACommonArguments,
	noData				NULL }

END  -- of CSTA-stop-data-path
