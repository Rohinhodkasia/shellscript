-- This file was generated by the Objective Systems ASN1C Compiler
-- (http://www.obj-sys.com).  Version: 6.8.A, Date: 18-Nov-2014.

SUPL-POS DEFINITIONS AUTOMATIC TAGS ::= BEGIN

IMPORTS

Velocity
FROM ULP-Components 

Ver2-SUPL-POS-extension
FROM ULP-Version-2-message-extensions 

Ver2-PosPayLoad-extension
FROM ULP-Version-2-parameter-extensions 

Ver3-SUPL-POS-extension
FROM ULP-Version-3-message-extensions ;

-- Productions

PosPayLoad ::= CHOICE {
   tia801payload [0] OCTET STRING (SIZE (1..8192)),
   rrcPayload [1] OCTET STRING (SIZE (1..8192)),
   rrlpPayload [2] OCTET STRING (SIZE (1..8192)),
   ...,
   ver2-PosPayLoad-extension [3] Ver2-PosPayLoad-extension
}

SUPLPOS ::= SEQUENCE {
   posPayLoad [0] PosPayLoad,
   velocity [1] Velocity OPTIONAL,
   ...,
   ver2-SUPL-POS-extension [2] Ver2-SUPL-POS-extension OPTIONAL,
   ver3-SUPL-POS-extension [3] Ver3-SUPL-POS-extension OPTIONAL
}

END
