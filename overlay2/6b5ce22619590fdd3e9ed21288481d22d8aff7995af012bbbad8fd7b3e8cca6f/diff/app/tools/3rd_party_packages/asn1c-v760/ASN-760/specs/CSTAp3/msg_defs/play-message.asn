CSTA-play-message
	{ iso( 1) identified-organization( 3) icd-ecma( 12)
		standard( 0) csta3( 285) play-message( 502) }
DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
MessageID, TerminatingConditions FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

playMessage OPERATION ::=
{	ARGUMENT		PlayMessageArgument
	RESULT			PlayMessageResult
	ERRORS			{universalFailure }
	CODE			local: 502 }

PlayMessageArgument ::= SEQUENCE
{	messageToBePlayed		MessageID,
	overConnection			ConnectionID,
	duration			INTEGER					OPTIONAL,
	termination			TerminatingConditions			OPTIONAL,
	extensions			CSTACommonArguments			OPTIONAL }

PlayMessageResult ::= CHOICE
{	extensions			CSTACommonArguments,
	noData				NULL }

END  -- of CSTA-play-message
