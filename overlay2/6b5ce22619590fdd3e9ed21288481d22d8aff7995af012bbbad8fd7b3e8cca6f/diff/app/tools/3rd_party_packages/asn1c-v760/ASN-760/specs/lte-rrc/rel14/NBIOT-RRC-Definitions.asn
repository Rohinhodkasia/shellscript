-- This file was generated by the Objective Systems ASN1C Compiler
-- (http://www.obj-sys.com).  Version: 7.5.0, Date: 01-Mar-2021.

NBIOT-RRC-Definitions DEFINITIONS AUTOMATIC TAGS ::= BEGIN

IMPORTS

RRCConnectionReestablishmentReject, SecurityModeCommand, SecurityModeComplete, 
   SecurityModeFailure, AdditionalSpectrumEmission, ARFCN-ValueEUTRA-r9, 
   CellIdentity, DedicatedInfoNAS, DRB-Identity, InitialUE-Identity, 
   IntraFreqBlackCellList, IntraFreqNeighCellList, maxBands, maxCellBlack, 
   maxCellInter, maxFBI2, maxFreq, maxMultiBands, maxPageRec, maxPLMN-r11, 
   maxSAI-MBMS-r11, maxSIB, maxSIB-1, MBMS-SAI-r11, MBMS-SAI-List-r11, 
   MBMSSessionInfo-r13, NextHopChainingCount, PagingUE-Identity, PLMN-Identity
   , P-Max, PowerRampingParameters, PreambleTransMax, PhysCellId, Q-OffsetRange
   , Q-QualMin-r9, Q-RxLevMin, ReestabUE-Identity, RegisteredMME, 
   ReselectionThreshold, ResumeIdentity-r13, RRC-TransactionIdentifier, 
   RSRP-Range, ShortMAC-I, S-TMSI, SystemInformationBlockType16-r11, 
   SystemInfoValueTagSI-r13, T-Reordering, TimeAlignmentTimer, TMGI-r9, 
   TrackingAreaCode, DataInactivityTimer-r14
FROM EUTRA-RRC-Definitions ;

-- Productions

Inband-SamePCI-NB-r13 ::= SEQUENCE {
   eutra-CRS-SequenceInfo-r13 [0] INTEGER (0..31)
}

ChannelRasterOffset-NB-r13 ::= ENUMERATED { khz-7dot5(0), khz-2dot5(1), 
   khz2dot5(2), khz7dot5(3) }

Inband-DifferentPCI-NB-r13 ::= SEQUENCE {
   eutra-NumCRS-Ports-r13 [0] ENUMERATED { same(0), four(1) },
   rasterOffset-r13 [1] ChannelRasterOffset-NB-r13,
   spare [2] BIT STRING  (SIZE (2))
}

Guardband-NB-r13 ::= SEQUENCE {
   rasterOffset-r13 [0] ChannelRasterOffset-NB-r13,
   spare [1] BIT STRING  (SIZE (3))
}

Standalone-NB-r13 ::= SEQUENCE {
   spare [0] BIT STRING  (SIZE (5))
}

MasterInformationBlock-NB ::= SEQUENCE {
   systemFrameNumber-MSB-r13 [0] BIT STRING  (SIZE (4)),
   hyperSFN-LSB-r13 [1] BIT STRING  (SIZE (2)),
   schedulingInfoSIB1-r13 [2] INTEGER (0..15),
   systemInfoValueTag-r13 [3] INTEGER (0..31),
   ab-Enabled-r13 [4] BOOLEAN,
   operationModeInfo-r13 [5] EXPLICIT CHOICE {
      inband-SamePCI-r13 [0] Inband-SamePCI-NB-r13,
      inband-DifferentPCI-r13 [1] Inband-DifferentPCI-NB-r13,
      guardband-r13 [2] Guardband-NB-r13,
      standalone-r13 [3] Standalone-NB-r13
   },
   spare [6] BIT STRING  (SIZE (11))
}

BCCH-BCH-MessageType-NB ::= MasterInformationBlock-NB

ReestablishmentCause-NB-r13 ::= ENUMERATED { reconfigurationFailure(0), 
   otherFailure(1), spare2(2), spare1(3) }

ReleaseCause-NB-r13 ::= ENUMERATED { loadBalancingTAUrequired(0), other(1), 
   rrc-Suspend(2), spare1(3) }

CarrierFreq-NB-r13 ::= SEQUENCE {
   carrierFreq-r13 [0] ARFCN-ValueEUTRA-r9,
   carrierFreqOffset-r13 [1] ENUMERATED { v-10(0), v-9(1), v-8(2), v-7(3), 
      v-6(4), v-5(5), v-4(6), v-3(7), v-2(8), v-1(9), v-0dot5(10), v0(11), 
      v1(12), v2(13), v3(14), v4(15), v5(16), v6(17), v7(18), v8(19), v9(20) }
       OPTIONAL -- Need ON
}

RedirectedCarrierInfo-NB-r13 ::= CarrierFreq-NB-r13

SIB-Type-NB-r13 ::= ENUMERATED { sibType3-NB-r13(0), sibType4-NB-r13(1), 
   sibType5-NB-r13(2), sibType14-NB-r13(3), sibType16-NB-r13(4), 
   sibType15-NB-r14(5), sibType20-NB-r14(6), sibType22-NB-r14(7) }

SystemInformationBlockType16-NB-r13 ::= SystemInformationBlockType16-r11

PagingWeight-NB-r14 ::= ENUMERATED { w1(0), w2(1), w3(2), w4(3), w5(4), w6(5), 
   w7(6), w8(7), w9(8), w10(9), w11(10), w12(11), w13(12), w14(13), w15(14), 
   w16(15) }

PeriodicBSR-Timer-NB-r13 ::= ENUMERATED { pp2(0), pp4(1), pp8(2), pp16(3), 
   pp64(4), pp128(5), infinity(6), spare(7) }

RetxBSR-Timer-NB-r13 ::= ENUMERATED { pp4(0), pp16(1), pp64(2), pp128(3), 
   pp256(4), pp512(5), infinity(6), spare(7) }

ACK-NACK-NumRepetitions-NB-r13 ::= ENUMERATED { r1(0), r2(1), r4(2), r8(3), 
   r16(4), r32(5), r64(6), r128(7) }

T-PollRetransmit-NB-r13 ::= ENUMERATED { ms250(0), ms500(1), ms1000(2), 
   ms2000(3), ms3000(4), ms4000(5), ms6000(6), ms10000(7), ms15000(8), 
   ms25000(9), ms40000(10), ms60000(11), ms90000(12), ms120000(13), 
   ms180000(14), spare1(15) }

FreqBandIndicator-NB-r13 ::= INTEGER (1..maxFBI2)

ReselectionThreshold-NB-v1360 ::= INTEGER (32..63)

T-Reselection-NB-r13 ::= ENUMERATED { s0(0), s3(1), s6(2), s9(3), s12(4), 
   s15(5), s18(6), s21(7) }

CQI-NPDCCH-NB-r14 ::= ENUMERATED { noMeasurements(0), candidateRep-A(1), 
   candidateRep-B(2), candidateRep-C(3), candidateRep-D(4), candidateRep-E(5), 
   candidateRep-F(6), candidateRep-G(7), candidateRep-H(8), candidateRep-I(9), 
   candidateRep-J(10), candidateRep-K(11), candidateRep-L(12) }

CQI-NPDCCH-Short-NB-r14 ::= ENUMERATED { noMeasurements(0), candidateRep-1(1), 
   candidateRep-2(2), candidateRep-3(3) }

NRSRP-Range-NB-r14 ::= INTEGER (0..113)

NRSRQ-Range-NB-r14 ::= INTEGER (-30..46)

EstablishmentCause-NB-r13 ::= ENUMERATED { mt-Access(0), mo-Signalling(1), 
   mo-Data(2), mo-ExceptionData(3), delayTolerantAccess-v1330(4), spare3(5), 
   spare2(6), spare1(7) }

AccessStratumRelease-NB-r13 ::= ENUMERATED { rel13(0), rel14(1), spare6(2), 
   spare5(3), spare4(4), spare3(5), spare2(6), spare1(7), ... }

BCCH-BCH-Message-NB ::= SEQUENCE {
   message [0] BCCH-BCH-MessageType-NB
}

RACH-Info-NB-r13 ::= SEQUENCE {
   ra-ResponseWindowSize-r13 [0] ENUMERATED { pp2(0), pp3(1), pp4(2), pp5(3), 
      pp6(4), pp7(5), pp8(6), pp10(7) },
   mac-ContentionResolutionTimer-r13 [1] ENUMERATED { pp1(0), pp2(1), pp3(2), 
      pp4(3), pp8(4), pp16(5), pp32(6), pp64(7) }
}

RACH-InfoList-NB-r13 ::= SEQUENCE (SIZE (1..maxNPRACH-Resources-NB-r13)) OF RACH-Info-NB-r13

PowerRampingParameters-NB-v1450 ::= SEQUENCE {
   preambleInitialReceivedTargetPower-v1450 [0] ENUMERATED { dBm-130(0), 
      dBm-128(1), dBm-126(2), dBm-124(3), dBm-122(4), dBm-88(5), dBm-86(6), 
      dBm-84(7), dBm-82(8), dBm-80(9) } OPTIONAL,
                     -- Need OR
   powerRampingParametersCE1-r14 [1] SEQUENCE {
      powerRampingStepCE1-r14 [0] ENUMERATED { dB0(0), dB2(1), dB4(2), dB6(3) }
         ,
      preambleInitialReceivedTargetPowerCE1-r14 [1] ENUMERATED { dBm-130(0), 
         dBm-128(1), dBm-126(2), dBm-124(3), dBm-122(4), dBm-120(5), dBm-118(6)
         , dBm-116(7), dBm-114(8), dBm-112(9), dBm-110(10), dBm-108(11), 
         dBm-106(12), dBm-104(13), dBm-102(14), dBm-100(15), dBm-98(16), 
         dBm-96(17), dBm-94(18), dBm-92(19), dBm-90(20), dBm-88(21), dBm-86(22)
         , dBm-84(23), dBm-82(24), dBm-80(25) }
   } OPTIONAL -- Need OR
}

RACH-ConfigCommon-NB-r13 ::= SEQUENCE {
   preambleTransMax-CE-r13 [0] PreambleTransMax,
   powerRampingParameters-r13 [1] PowerRampingParameters,
   rach-InfoList-r13 [2] RACH-InfoList-NB-r13,
   connEstFailOffset-r13 [3] INTEGER (0..15) OPTIONAL,
   ...,
   [[
      powerRampingParameters-v1450 [4] PowerRampingParameters-NB-v1450 OPTIONAL
   ]]
}

BCCH-Config-NB-r13 ::= SEQUENCE {
   modificationPeriodCoeff-r13 [0] ENUMERATED { n16(0), n32(1), n64(2), n128(3)
       }
}

PCCH-Config-NB-r13 ::= SEQUENCE {
   defaultPagingCycle-r13 [0] ENUMERATED { rf128(0), rf256(1), rf512(2), 
      rf1024(3) },
   nB-r13 [1] ENUMERATED { fourT(0), twoT(1), oneT(2), halfT(3), quarterT(4), 
      one8thT(5), one16thT(6), one32ndT(7), one64thT(8), one128thT(9), 
      one256thT(10), one512thT(11), one1024thT(12), spare3(13), spare2(14), 
      spare1(15) },
   npdcch-NumRepetitionPaging-r13 [2] ENUMERATED { r1(0), r2(1), r4(2), r8(3), 
      r16(4), r32(5), r64(6), r128(7), r256(8), r512(9), r1024(10), r2048(11), 
      spare4(12), spare3(13), spare2(14), spare1(15) }
}

RSRP-ThresholdsNPRACH-InfoList-NB-r13 ::= SEQUENCE (SIZE (1..2)) OF RSRP-Range

NPRACH-Parameters-NB-r13 ::= SEQUENCE {
   nprach-Periodicity-r13 [0] ENUMERATED { ms40(0), ms80(1), ms160(2), ms240(3)
      , ms320(4), ms640(5), ms1280(6), ms2560(7) },
   nprach-StartTime-r13 [1] ENUMERATED { ms8(0), ms16(1), ms32(2), ms64(3), 
      ms128(4), ms256(5), ms512(6), ms1024(7) },
   nprach-SubcarrierOffset-r13 [2] ENUMERATED { n0(0), n12(1), n24(2), n36(3), 
      n2(4), n18(5), n34(6), spare1(7) },
   nprach-NumSubcarriers-r13 [3] ENUMERATED { n12(0), n24(1), n36(2), n48(3) },
   nprach-SubcarrierMSG3-RangeStart-r13 [4] ENUMERATED { zero(0), oneThird(1), 
      twoThird(2), one(3) },
   maxNumPreambleAttemptCE-r13 [5] ENUMERATED { n3(0), n4(1), n5(2), n6(3), 
      n7(4), n8(5), n10(6), spare1(7) },
   numRepetitionsPerPreambleAttempt-r13 [6] ENUMERATED { n1(0), n2(1), n4(2), 
      n8(3), n16(4), n32(5), n64(6), n128(7) },
   npdcch-NumRepetitions-RA-r13 [7] ENUMERATED { r1(0), r2(1), r4(2), r8(3), 
      r16(4), r32(5), r64(6), r128(7), r256(8), r512(9), r1024(10), r2048(11), 
      spare4(12), spare3(13), spare2(14), spare1(15) },
   npdcch-StartSF-CSS-RA-r13 [8] ENUMERATED { v1dot5(0), v2(1), v4(2), v8(3), 
      v16(4), v32(5), v48(6), v64(7) },
   npdcch-Offset-RA-r13 [9] ENUMERATED { zero(0), oneEighth(1), oneFourth(2), 
      threeEighth(3) }
}

NPRACH-ParametersList-NB-r13 ::= SEQUENCE (SIZE (1..maxNPRACH-Resources-NB-r13)) OF 
   NPRACH-Parameters-NB-r13

NPRACH-ConfigSIB-NB-r13 ::= SEQUENCE {
   nprach-CP-Length-r13 [0] ENUMERATED { us66dot7(0), us266dot7(1) },
   rsrp-ThresholdsPrachInfoList-r13 [1] RSRP-ThresholdsNPRACH-InfoList-NB-r13
       OPTIONAL, -- need OR
   nprach-ParametersList-r13 [2] NPRACH-ParametersList-NB-r13
}

NPDSCH-ConfigCommon-NB-r13 ::= SEQUENCE {
   nrs-Power-r13 [0] INTEGER (-60..50)
}

UL-ReferenceSignalsNPUSCH-NB-r13 ::= SEQUENCE {
   groupHoppingEnabled-r13 [0] BOOLEAN,
   groupAssignmentNPUSCH-r13 [1] INTEGER (0..29)
}

NPUSCH-ConfigCommon-NB-r13 ::= SEQUENCE {
   ack-NACK-NumRepetitions-Msg4-r13 [0] SEQUENCE (SIZE (1..maxNPRACH-Resources-NB-r13)) OF 
      ACK-NACK-NumRepetitions-NB-r13,
   srs-SubframeConfig-r13 [1] ENUMERATED { sc0(0), sc1(1), sc2(2), sc3(3), 
      sc4(4), sc5(5), sc6(6), sc7(7), sc8(8), sc9(9), sc10(10), sc11(11), 
      sc12(12), sc13(13), sc14(14), sc15(15) } OPTIONAL, -- Need OR
   dmrs-Config-r13 [2] SEQUENCE {
      threeTone-BaseSequence-r13 [0] INTEGER (0..12) OPTIONAL, -- Need OP
      threeTone-CyclicShift-r13 [1] INTEGER (0..2),
      sixTone-BaseSequence-r13 [2] INTEGER (0..14) OPTIONAL, -- Need OP
      sixTone-CyclicShift-r13 [3] INTEGER (0..3),
      twelveTone-BaseSequence-r13 [4] INTEGER (0..30) OPTIONAL -- Need OP
   } OPTIONAL, -- Need OR
   ul-ReferenceSignalsNPUSCH-r13 [3] UL-ReferenceSignalsNPUSCH-NB-r13
}

DL-GapConfig-NB-r13 ::= SEQUENCE {
   dl-GapThreshold-r13 [0] ENUMERATED { n32(0), n64(1), n128(2), n256(3) },
   dl-GapPeriodicity-r13 [1] ENUMERATED { sf64(0), sf128(1), sf256(2), sf512(3)
       },
   dl-GapDurationCoeff-r13 [2] ENUMERATED { oneEighth(0), oneFourth(1), 
      threeEighth(2), oneHalf(3) }
}

UplinkPowerControlCommon-NB-r13 ::= SEQUENCE {
   p0-NominalNPUSCH-r13 [0] INTEGER (-126..24),
   alpha-r13 [1] ENUMERATED { al0(0), al04(1), al05(2), al06(3), al07(4), 
      al08(5), al09(6), al1(7) },
   deltaPreambleMsg3-r13 [2] INTEGER (-1..6)
}

NPRACH-Parameters-NB-v1330 ::= SEQUENCE {
   nprach-NumCBRA-StartSubcarriers-r13 [0] ENUMERATED { n8(0), n10(1), n11(2), 
      n12(3), n20(4), n22(5), n23(6), n24(7), n32(8), n34(9), n35(10), n36(11)
      , n40(12), n44(13), n46(14), n48(15) }
}

NPRACH-ParametersList-NB-v1330 ::= SEQUENCE (SIZE (1..maxNPRACH-Resources-NB-r13)) OF 
   NPRACH-Parameters-NB-v1330

NPRACH-ConfigSIB-NB-v1330 ::= SEQUENCE {
   nprach-ParametersList-v1330 [0] NPRACH-ParametersList-NB-v1330
}

NPRACH-ConfigSIB-NB-v1450 ::= SEQUENCE {
   maxNumPreambleAttemptCE-r14 [0] ENUMERATED { n3(0), n4(1), n5(2), n6(3), 
      n7(4), n8(5), n10(6), spare1(7) }
}

RadioResourceConfigCommonSIB-NB-r13 ::= SEQUENCE {
   rach-ConfigCommon-r13 [0] RACH-ConfigCommon-NB-r13,
   bcch-Config-r13 [1] BCCH-Config-NB-r13,
   pcch-Config-r13 [2] PCCH-Config-NB-r13,
   nprach-Config-r13 [3] NPRACH-ConfigSIB-NB-r13,
   npdsch-ConfigCommon-r13 [4] NPDSCH-ConfigCommon-NB-r13,
   npusch-ConfigCommon-r13 [5] NPUSCH-ConfigCommon-NB-r13,
   dl-Gap-r13 [6] DL-GapConfig-NB-r13 OPTIONAL, -- Need OP
   uplinkPowerControlCommon-r13 [7] UplinkPowerControlCommon-NB-r13,
   ...,
   [[
      nprach-Config-v1330 [8] NPRACH-ConfigSIB-NB-v1330 OPTIONAL
   ]],
   [[
      nprach-Config-v1450 [9] NPRACH-ConfigSIB-NB-v1450 OPTIONAL
   ]]
}

UE-TimersAndConstants-NB-r13 ::= SEQUENCE {
   t300-r13 [0] ENUMERATED { ms2500(0), ms4000(1), ms6000(2), ms10000(3), 
      ms15000(4), ms25000(5), ms40000(6), ms60000(7) },
   t301-r13 [1] ENUMERATED { ms2500(0), ms4000(1), ms6000(2), ms10000(3), 
      ms15000(4), ms25000(5), ms40000(6), ms60000(7) },
   t310-r13 [2] ENUMERATED { ms0(0), ms200(1), ms500(2), ms1000(3), ms2000(4), 
      ms4000(5), ms8000(6) },
   n310-r13 [3] ENUMERATED { n1(0), n2(1), n3(2), n4(3), n6(4), n8(5), n10(6), 
      n20(7) },
   t311-r13 [4] ENUMERATED { ms1000(0), ms3000(1), ms5000(2), ms10000(3), 
      ms15000(4), ms20000(5), ms30000(6) },
   n311-r13 [5] ENUMERATED { n1(0), n2(1), n3(2), n4(3), n5(4), n6(5), n8(6), 
      n10(7) },
   ...,
   [[
      t311-v1350 [6] ENUMERATED { ms40000(0), ms60000(1), ms90000(2), 
         ms120000(3) } OPTIONAL
   ]]
}

SystemInformationBlockType2-NB-r13 ::= SEQUENCE {
   radioResourceConfigCommon-r13 [0] RadioResourceConfigCommonSIB-NB-r13,
   ue-TimersAndConstants-r13 [1] UE-TimersAndConstants-NB-r13,
   freqInfo-r13 [2] SEQUENCE {
      ul-CarrierFreq-r13 [0] CarrierFreq-NB-r13 OPTIONAL, -- Need OP
      additionalSpectrumEmission-r13 [1] AdditionalSpectrumEmission
   },
   timeAlignmentTimerCommon-r13 [3] TimeAlignmentTimer,
   multiBandInfoList-r13 [4] SEQUENCE (SIZE (1..maxMultiBands)) OF AdditionalSpectrumEmission
       OPTIONAL, -- Need OR
   lateNonCriticalExtension [5] OCTET STRING OPTIONAL,
   ...,
   [[
      cp-Reestablishment-r14 [6] ENUMERATED { true(0) } OPTIONAL
   ]],
   [[
      servingCellMeasInfo-r14 [7] ENUMERATED { true(0) } OPTIONAL,
      cqi-Reporting-r14 [8] ENUMERATED { true(0) } OPTIONAL
   ]]
}

NS-PmaxValue-NB-r13 ::= SEQUENCE {
   additionalPmax-r13 [0] P-Max OPTIONAL, -- Need OR
   additionalSpectrumEmission-r13 [1] AdditionalSpectrumEmission
}

NS-PmaxList-NB-r13 ::= SEQUENCE (SIZE (1..maxNS-Pmax-NB-r13)) OF NS-PmaxValue-NB-r13

IntraFreqCellReselectionInfo-NB-v1350 ::= SEQUENCE {
   delta-RxLevMin-v1350 [0] INTEGER (-8..-1)
}

IntraFreqCellReselectionInfo-NB-v1360 ::= SEQUENCE {
   s-IntraSearchP-v1360 [0] ReselectionThreshold-NB-v1360
}

IntraFreqCellReselectionInfo-NB-v1430 ::= SEQUENCE {
   powerClass14dBm-Offset-r14 [0] ENUMERATED { dB-6(0), dB-3(1), dB3(2), dB6(3)
      , dB9(4), dB12(5) } OPTIONAL, -- Need OP
   ce-AuthorisationOffset-r14 [1] ENUMERATED { dB5(0), dB10(1), dB15(2), 
      dB20(3), dB25(4), dB30(5), dB35(6) } OPTIONAL -- Need OP
}

CellReselectionInfoCommon-NB-v1450 ::= SEQUENCE {
   s-SearchDeltaP-r14 [0] ENUMERATED { dB6(0), dB9(1), dB12(2), dB15(3) }
}

SystemInformationBlockType3-NB-r13 ::= SEQUENCE {
   cellReselectionInfoCommon-r13 [0] SEQUENCE {
      q-Hyst-r13 [0] ENUMERATED { dB0(0), dB1(1), dB2(2), dB3(3), dB4(4), 
         dB5(5), dB6(6), dB8(7), dB10(8), dB12(9), dB14(10), dB16(11), dB18(12)
         , dB20(13), dB22(14), dB24(15) }
   },
   cellReselectionServingFreqInfo-r13 [1] SEQUENCE {
      s-NonIntraSearch-r13 [0] ReselectionThreshold
   },
   intraFreqCellReselectionInfo-r13 [2] SEQUENCE {
      q-RxLevMin-r13 [0] Q-RxLevMin,
      q-QualMin-r13 [1] Q-QualMin-r9 OPTIONAL, -- Need OP
      p-Max-r13 [2] P-Max OPTIONAL, -- Need OP
      s-IntraSearchP-r13 [3] ReselectionThreshold,
      t-Reselection-r13 [4] T-Reselection-NB-r13
   },
   freqBandInfo-r13 [3] NS-PmaxList-NB-r13 OPTIONAL, -- Need OR
   multiBandInfoList-r13 [4] SEQUENCE (SIZE (1..maxMultiBands)) OF NS-PmaxList-NB-r13
       OPTIONAL, -- Need OR
   lateNonCriticalExtension [5] OCTET STRING OPTIONAL,
   ...,
   [[
      intraFreqCellReselectionInfo-v1350 [6] 
         IntraFreqCellReselectionInfo-NB-v1350 OPTIONAL
   ]],
   [[
      intraFreqCellReselectionInfo-v1360 [7] 
         IntraFreqCellReselectionInfo-NB-v1360 OPTIONAL
   ]],
   [[
      intraFreqCellReselectionInfo-v1430 [8] 
         IntraFreqCellReselectionInfo-NB-v1430 OPTIONAL
   ]],
   [[
      cellReselectionInfoCommon-v1450 [9] CellReselectionInfoCommon-NB-v1450
          OPTIONAL
   ]]
}

SystemInformationBlockType4-NB-r13 ::= SEQUENCE {
   intraFreqNeighCellList-r13 [0] IntraFreqNeighCellList OPTIONAL, -- Need OR
   intraFreqBlackCellList-r13 [1] IntraFreqBlackCellList OPTIONAL, -- Need OR
   lateNonCriticalExtension [2] OCTET STRING OPTIONAL,
   ...
}

InterFreqNeighCellList-NB-r13 ::= SEQUENCE (SIZE (1..maxCellInter)) OF PhysCellId

InterFreqBlackCellList-NB-r13 ::= SEQUENCE (SIZE (1..maxCellBlack)) OF PhysCellId

MultiBandInfo-NB-r13 ::= SEQUENCE {
   freqBandIndicator-r13 [0] FreqBandIndicator-NB-r13 OPTIONAL, -- Need OR
   freqBandInfo-r13 [1] NS-PmaxList-NB-r13 OPTIONAL -- Need OR
}

MultiBandInfoList-NB-r13 ::= SEQUENCE (SIZE (1..maxMultiBands)) OF MultiBandInfo-NB-r13

InterFreqCarrierFreqInfo-NB-r13 ::= SEQUENCE {
   dl-CarrierFreq-r13 [0] CarrierFreq-NB-r13,
   q-RxLevMin-r13 [1] Q-RxLevMin,
   q-QualMin-r13 [2] Q-QualMin-r9 OPTIONAL, -- Need OP
   p-Max-r13 [3] P-Max OPTIONAL, -- Need OP
   q-OffsetFreq-r13 [4] Q-OffsetRange DEFAULT dB0,
   interFreqNeighCellList-r13 [5] InterFreqNeighCellList-NB-r13 OPTIONAL, -- Need OR
   interFreqBlackCellList-r13 [6] InterFreqBlackCellList-NB-r13 OPTIONAL, -- Need OR
   multiBandInfoList-r13 [7] MultiBandInfoList-NB-r13 OPTIONAL,
   ...,
   [[
      delta-RxLevMin-v1350 [8] INTEGER (-8..-1) OPTIONAL
   ]],
   [[
      powerClass14dBm-Offset-r14 [9] ENUMERATED { dB-6(0), dB-3(1), dB3(2), 
         dB6(3), dB9(4), dB12(5) } OPTIONAL,
      ce-AuthorisationOffset-r14 [10] ENUMERATED { dB5(0), dB10(1), dB15(2), 
         dB20(3), dB25(4), dB30(5), dB35(6) } OPTIONAL
   ]]
}

InterFreqCarrierFreqList-NB-r13 ::= SEQUENCE (SIZE (1..maxFreq)) OF 
   InterFreqCarrierFreqInfo-NB-r13

SystemInformationBlockType5-NB-r13 ::= SEQUENCE {
   interFreqCarrierFreqList-r13 [0] InterFreqCarrierFreqList-NB-r13,
   t-Reselection-r13 [1] T-Reselection-NB-r13,
   lateNonCriticalExtension [2] OCTET STRING OPTIONAL,
   ...,
   [[
      scptm-FreqOffset-r14 [3] INTEGER (1..8) OPTIONAL
   ]]
}

AB-Config-NB-r13 ::= SEQUENCE {
   ab-Category-r13 [0] ENUMERATED { a(0), b(1), c(2) },
   ab-BarringBitmap-r13 [1] BIT STRING  (SIZE (10)),
   ab-BarringForExceptionData-r13 [2] ENUMERATED { true(0) } OPTIONAL, -- Need OP
   ab-BarringForSpecialAC-r13 [3] BIT STRING  (SIZE (5))
}

AB-ConfigPLMN-NB-r13 ::= SEQUENCE {
   ab-Config-r13 [0] AB-Config-NB-r13 OPTIONAL -- Need OR
}

SystemInformationBlockType14-NB-r13 ::= SEQUENCE {
   ab-Param-r13 [0] EXPLICIT CHOICE {
      ab-Common-r13 [0] AB-Config-NB-r13,
      ab-PerPLMN-List-r13 [1] SEQUENCE (SIZE (1..maxPLMN-r11)) OF AB-ConfigPLMN-NB-r13
   } OPTIONAL, -- Need OR
   lateNonCriticalExtension [1] OCTET STRING OPTIONAL,
   ...
}

AdditionalBandInfoList-NB-r14 ::= SEQUENCE (SIZE (1..maxMultiBands)) OF 
   FreqBandIndicator-NB-r13

MBMS-SAI-InterFreq-NB-r14 ::= SEQUENCE {
   dl-CarrierFreq-r14 [0] CarrierFreq-NB-r13,
   mbms-SAI-List-r14 [1] MBMS-SAI-List-r11,
   multiBandInfoList-r14 [2] AdditionalBandInfoList-NB-r14 OPTIONAL -- Need OR
}

MBMS-SAI-InterFreqList-NB-r14 ::= SEQUENCE (SIZE (1..maxFreq)) OF 
   MBMS-SAI-InterFreq-NB-r14

SystemInformationBlockType15-NB-r14 ::= SEQUENCE {
   mbms-SAI-IntraFreq-r14 [0] MBMS-SAI-List-r11 OPTIONAL, -- Need OR
   mbms-SAI-InterFreqList-r14 [1] MBMS-SAI-InterFreqList-NB-r14 OPTIONAL, -- Need OR
   lateNonCriticalExtension [2] OCTET STRING OPTIONAL,
   ...
}

NPDCCH-SC-MCCH-Config-NB-r14 ::= SEQUENCE {
   npdcch-NumRepetitions-SC-MCCH-r14 [0] ENUMERATED { r1(0), r2(1), r4(2), 
      r8(3), r16(4), r32(5), r64(6), r128(7), r256(8), r512(9), r1024(10), 
      r2048(11) },
   npdcch-StartSF-SC-MCCH-r14 [1] ENUMERATED { v1dot5(0), v2(1), v4(2), v8(3), 
      v16(4), v32(5), v48(6), v64(7) },
   npdcch-Offset-SC-MCCH-r14 [2] ENUMERATED { zero(0), oneEighth(1), 
      oneQuarter(2), threeEighth(3), oneHalf(4), fiveEighth(5), threeQuarter(6)
      , sevenEighth(7) }
}

DL-Bitmap-NB-r13 ::= CHOICE {
   subframePattern10-r13 [0] BIT STRING  (SIZE (10)),
   subframePattern40-r13 [1] BIT STRING  (SIZE (40))
}

DL-CarrierConfigCommon-NB-r14 ::= SEQUENCE {
   dl-CarrierFreq-r14 [0] CarrierFreq-NB-r13,
   downlinkBitmapNonAnchor-r14 [1] EXPLICIT CHOICE {
      useNoBitmap-r14 [0] NULL,
      useAnchorBitmap-r14 [1] NULL,
      explicitBitmapConfiguration-r14 [2] EXPLICIT DL-Bitmap-NB-r13
   },
   dl-GapNonAnchor-r14 [2] EXPLICIT CHOICE {
      useNoGap-r14 [0] NULL,
      useAnchorGapConfig-r14 [1] NULL,
      explicitGapConfiguration-r14 [2] DL-GapConfig-NB-r13
   },
   inbandCarrierInfo-r14 [3] SEQUENCE {
      samePCI-Indicator-r14 [0] EXPLICIT CHOICE {
         samePCI-r14 [0] SEQUENCE {
            indexToMidPRB-r14 [0] INTEGER (-55..54)
         },
         differentPCI-r14 [1] SEQUENCE {
            eutra-NumCRS-Ports-r14 [0] ENUMERATED { same(0), four(1) }
         }
      } OPTIONAL, -- Cond anchor-guardband
      eutraControlRegionSize-r14 [1] ENUMERATED { n1(0), n2(1), n3(2) }
   } OPTIONAL, -- Cond non-anchor-inband
   nrs-PowerOffsetNonAnchor-r14 [4] ENUMERATED { dB-12(0), dB-10(1), dB-8(2), 
      dB-6(3), dB-4(4), dB-2(5), dB0(6), dB3(7) } DEFAULT dB0,
   ...
}

SC-MCCH-SchedulingInfo-NB-r14 ::= SEQUENCE {
   onDurationTimerSCPTM-r14 [0] ENUMERATED { pp1(0), pp2(1), pp3(2), pp4(3), 
      pp8(4), pp16(5), pp32(6), spare(7) },
   drx-InactivityTimerSCPTM-r14 [1] ENUMERATED { pp0(0), pp1(1), pp2(2), pp3(3)
      , pp4(4), pp8(5), pp16(6), pp32(7) },
   schedulingPeriodStartOffsetSCPTM-r14 [2] EXPLICIT CHOICE {
      sf10 [0] INTEGER (0..9),
      sf20 [1] INTEGER (0..19),
      sf32 [2] INTEGER (0..31),
      sf40 [3] INTEGER (0..39),
      sf64 [4] INTEGER (0..63),
      sf80 [5] INTEGER (0..79),
      sf128 [6] INTEGER (0..127),
      sf160 [7] INTEGER (0..159),
      sf256 [8] INTEGER (0..255),
      sf320 [9] INTEGER (0..319),
      sf512 [10] INTEGER (0..511),
      sf640 [11] INTEGER (0..639),
      sf1024 [12] INTEGER (0..1023),
      sf2048 [13] INTEGER (0..2047),
      sf4096 [14] INTEGER (0..4095),
      sf8192 [15] INTEGER (0..8191)
   },
   ...
}

SystemInformationBlockType20-NB-r14 ::= SEQUENCE {
   npdcch-SC-MCCH-Config-r14 [0] NPDCCH-SC-MCCH-Config-NB-r14,
   sc-mcch-CarrierConfig-r14 [1] EXPLICIT CHOICE {
      dl-CarrierConfig-r14 [0] DL-CarrierConfigCommon-NB-r14,
      dl-CarrierIndex-r14 [1] INTEGER (0..maxNonAnchorCarriers-NB-r14)
   },
   sc-mcch-RepetitionPeriod-r14 [2] ENUMERATED { rf32(0), rf128(1), rf512(2), 
      rf1024(3), rf2048(4), rf4096(5), rf8192(6), rf16384(7) },
   sc-mcch-Offset-r14 [3] INTEGER (0..10),
   sc-mcch-ModificationPeriod-r14 [4] ENUMERATED { rf32(0), rf128(1), rf256(2)
      , rf512(3), rf1024(4), rf2048(5), rf4096(6), rf8192(7), rf16384(8), 
      rf32768(9), rf65536(10), rf131072(11), rf262144(12), rf524288(13), 
      rf1048576(14), spare1(15) },
   sc-mcch-SchedulingInfo-r14 [5] SC-MCCH-SchedulingInfo-NB-r14 OPTIONAL, -- Need OP
   lateNonCriticalExtension [6] OCTET STRING OPTIONAL,
   ...
}

PCCH-Config-NB-r14 ::= SEQUENCE {
   npdcch-NumRepetitionPaging-r14 [0] ENUMERATED { r1(0), r2(1), r4(2), r8(3), 
      r16(4), r32(5), r64(6), r128(7), r256(8), r512(9), r1024(10), r2048(11), 
      spare4(12), spare3(13), spare2(14), spare1(15) } OPTIONAL, -- Need OP
   pagingWeight-r14 [1] PagingWeight-NB-r14 DEFAULT w1,
   ...
}

DL-ConfigCommon-NB-r14 ::= SEQUENCE {
   dl-CarrierConfig-r14 [0] DL-CarrierConfigCommon-NB-r14,
   pcch-Config-r14 [1] PCCH-Config-NB-r14 OPTIONAL,
   ...
}

DL-ConfigCommonList-NB-r14 ::= SEQUENCE (SIZE (1..maxNonAnchorCarriers-NB-r14)) OF DL-ConfigCommon-NB-r14

NPRACH-Parameters-NB-r14 ::= SEQUENCE {
   nprach-Parameters-r14 [0] SEQUENCE {
      nprach-Periodicity-r14 [0] ENUMERATED { ms40(0), ms80(1), ms160(2), 
         ms240(3), ms320(4), ms640(5), ms1280(6), ms2560(7) } OPTIONAL,
                   -- NEED OP
      nprach-StartTime-r14 [1] ENUMERATED { ms8(0), ms16(1), ms32(2), ms64(3), 
         ms128(4), ms256(5), ms512(6), ms1024(7) } OPTIONAL,
                   -- NEED OP
      nprach-SubcarrierOffset-r14 [2] ENUMERATED { n0(0), n12(1), n24(2), 
         n36(3), n2(4), n18(5), n34(6), spare1(7) } OPTIONAL,
                   -- NEED OP
      nprach-NumSubcarriers-r14 [3] ENUMERATED { n12(0), n24(1), n36(2), n48(3)
          } OPTIONAL,
                   -- NEED OP
      nprach-SubcarrierMSG3-RangeStart-r14 [4] ENUMERATED { zero(0), 
         oneThird(1), twoThird(2), one(3) } OPTIONAL,
                   -- NEED OP
      npdcch-NumRepetitions-RA-r14 [5] ENUMERATED { r1(0), r2(1), r4(2), r8(3)
         , r16(4), r32(5), r64(6), r128(7), r256(8), r512(9), r1024(10), 
         r2048(11), spare4(12), spare3(13), spare2(14), spare1(15) } OPTIONAL,
                   -- NEED OP
      npdcch-StartSF-CSS-RA-r14 [6] ENUMERATED { v1dot5(0), v2(1), v4(2), v8(3)
         , v16(4), v32(5), v48(6), v64(7) } OPTIONAL,
                    -- NEED OP
      npdcch-Offset-RA-r14 [7] ENUMERATED { zero(0), oneEighth(1), oneFourth(2)
         , threeEighth(3) } OPTIONAL,
                   -- NEED OP
      nprach-NumCBRA-StartSubcarriers-r14 [8] ENUMERATED { n8(0), n10(1), 
         n11(2), n12(3), n20(4), n22(5), n23(6), n24(7), n32(8), n34(9), 
         n35(10), n36(11), n40(12), n44(13), n46(14), n48(15) } OPTIONAL,
                   -- NEED OP
      npdcch-CarrierIndex-r14 [9] INTEGER (1..maxNonAnchorCarriers-NB-r14) OPTIONAL,
      ...
   } OPTIONAL -- Need OR
}

NPRACH-ParametersList-NB-r14 ::= SEQUENCE (SIZE (1..maxNPRACH-Resources-NB-r13)) OF 
   NPRACH-Parameters-NB-r14

UL-ConfigCommon-NB-r14 ::= SEQUENCE {
   ul-CarrierFreq-r14 [0] CarrierFreq-NB-r13,
   nprach-ParametersList-r14 [1] NPRACH-ParametersList-NB-r14 OPTIONAL,
   ...
}

UL-ConfigCommonList-NB-r14 ::= SEQUENCE (SIZE (1..maxNonAnchorCarriers-NB-r14)) OF UL-ConfigCommon-NB-r14

NPRACH-ProbabilityAnchor-NB-r14 ::= SEQUENCE {
   nprach-ProbabilityAnchor-r14 [0] ENUMERATED { zero(0), oneSixteenth(1), 
      oneFifteenth(2), oneFourteenth(3), oneThirteenth(4), oneTwelfth(5), 
      oneEleventh(6), oneTenth(7), oneNinth(8), oneEighth(9), oneSeventh(10), 
      oneSixth(11), oneFifth(12), oneFourth(13), oneThird(14), oneHalf(15) }
       OPTIONAL
                     -- Need OP
}

NPRACH-ProbabilityAnchorList-NB-r14 ::= SEQUENCE (SIZE (1..maxNPRACH-Resources-NB-r13)) OF 
   NPRACH-ProbabilityAnchor-NB-r14

SystemInformationBlockType22-NB-r14 ::= SEQUENCE {
   dl-ConfigList-r14 [0] DL-ConfigCommonList-NB-r14 OPTIONAL, -- Need OR
   ul-ConfigList-r14 [1] UL-ConfigCommonList-NB-r14 OPTIONAL, -- Need OR
   pagingWeightAnchor-r14 [2] PagingWeight-NB-r14 OPTIONAL, -- Cond pcch-config
   nprach-ProbabilityAnchorList-r14 [3] NPRACH-ProbabilityAnchorList-NB-r14
       OPTIONAL, -- Cond nprach-config
   lateNonCriticalExtension [4] OCTET STRING OPTIONAL,
   ...
}

SystemInformation-NB-r13-IEs ::= SEQUENCE {
   sib-TypeAndInfo-r13 [0] SEQUENCE (SIZE (1..maxSIB)) OF CHOICE {
      sib2-r13 [0] SystemInformationBlockType2-NB-r13,
      sib3-r13 [1] SystemInformationBlockType3-NB-r13,
      sib4-r13 [2] SystemInformationBlockType4-NB-r13,
      sib5-r13 [3] SystemInformationBlockType5-NB-r13,
      sib14-r13 [4] SystemInformationBlockType14-NB-r13,
      sib16-r13 [5] SystemInformationBlockType16-NB-r13,
      ...,
      sib15-v1430 [6] SystemInformationBlockType15-NB-r14,
      sib20-v1430 [7] SystemInformationBlockType20-NB-r14,
      sib22-v1430 [8] SystemInformationBlockType22-NB-r14
   },
   lateNonCriticalExtension [1] OCTET STRING OPTIONAL,
   nonCriticalExtension [2] SEQUENCE {

   } OPTIONAL
}

SystemInformation-NB ::= SEQUENCE {
   criticalExtensions [0] EXPLICIT CHOICE {
      systemInformation-r13 [0] SystemInformation-NB-r13-IEs,
      criticalExtensionsFuture [1] SEQUENCE {

      }
   }
}

PLMN-IdentityInfo-NB-r13 ::= SEQUENCE {
   plmn-Identity-r13 [0] PLMN-Identity,
   cellReservedForOperatorUse-r13 [1] ENUMERATED { reserved(0), notReserved(1)
       },
   attachWithoutPDN-Connectivity-r13 [2] ENUMERATED { true(0) } OPTIONAL -- Need OP
}

PLMN-IdentityList-NB-r13 ::= SEQUENCE (SIZE (1..maxPLMN-r11)) OF PLMN-IdentityInfo-NB-r13

SIB-MappingInfo-NB-r13 ::= SEQUENCE (SIZE (0..maxSIB-1)) OF SIB-Type-NB-r13

SchedulingInfo-NB-r13 ::= SEQUENCE {
   si-Periodicity-r13 [0] ENUMERATED { rf64(0), rf128(1), rf256(2), rf512(3), 
      rf1024(4), rf2048(5), rf4096(6), spare(7) },
   si-RepetitionPattern-r13 [1] ENUMERATED { every2ndRF(0), every4thRF(1), 
      every8thRF(2), every16thRF(3) },
   sib-MappingInfo-r13 [2] SIB-MappingInfo-NB-r13,
   si-TB-r13 [3] ENUMERATED { b56(0), b120(1), b208(2), b256(3), b328(4), 
      b440(5), b552(6), b680(7) }
}

SchedulingInfoList-NB-r13 ::= SEQUENCE (SIZE (1..maxSI-Message-NB-r13)) OF SchedulingInfo-NB-r13

SystemInfoValueTagList-NB-r13 ::= SEQUENCE (SIZE (1..maxSI-Message-NB-r13)) OF 
   SystemInfoValueTagSI-r13

CellSelectionInfo-NB-v1350 ::= SEQUENCE {
   delta-RxLevMin-v1350 [0] INTEGER (-8..-1)
}

CellSelectionInfo-NB-v1430 ::= SEQUENCE {
   powerClass14dBm-Offset-r14 [0] ENUMERATED { dB-6(0), dB-3(1), dB3(2), dB6(3)
      , dB9(4), dB12(5) } OPTIONAL, --	Need OP
   ce-authorisationOffset-r14 [1] ENUMERATED { dB5(0), dB10(1), dB15(2), 
      dB20(3), dB25(4), dB30(5), dB35(6) } OPTIONAL --	Need OP
}

SystemInformationBlockType1-NB-v1450 ::= SEQUENCE {
   nrs-CRS-PowerOffset-v1450 [0] ENUMERATED { dB-6(0), dB-4dot77(1), dB-3(2), 
      dB-1dot77(3), dB0(4), dB1(5), dB1dot23(6), dB2(7), dB3(8), dB4(9), 
      dB4dot23(10), dB5(11), dB6(12), dB7(13), dB8(14), dB9(15) } OPTIONAL, -- Cond inband-SamePCI-ExceptAnchor
   nonCriticalExtension [1] SEQUENCE {

   } OPTIONAL
}

SystemInformationBlockType1-NB-v1430 ::= SEQUENCE {
   cellSelectionInfo-v1430 [0] CellSelectionInfo-NB-v1430 OPTIONAL, -- Need OR
   nonCriticalExtension [1] SystemInformationBlockType1-NB-v1450 OPTIONAL
}

SystemInformationBlockType1-NB-v1350 ::= SEQUENCE {
   cellSelectionInfo-v1350 [0] CellSelectionInfo-NB-v1350 OPTIONAL, -- Cond Qrxlevmin
   nonCriticalExtension [1] SystemInformationBlockType1-NB-v1430 OPTIONAL
}

SystemInformationBlockType1-NB ::= SEQUENCE {
   hyperSFN-MSB-r13 [0] BIT STRING  (SIZE (8)),
   cellAccessRelatedInfo-r13 [1] SEQUENCE {
      plmn-IdentityList-r13 [0] PLMN-IdentityList-NB-r13,
      trackingAreaCode-r13 [1] TrackingAreaCode,
      cellIdentity-r13 [2] CellIdentity,
      cellBarred-r13 [3] ENUMERATED { barred(0), notBarred(1) },
      intraFreqReselection-r13 [4] ENUMERATED { allowed(0), notAllowed(1) }
   },
   cellSelectionInfo-r13 [2] SEQUENCE {
      q-RxLevMin-r13 [0] Q-RxLevMin,
      q-QualMin-r13 [1] Q-QualMin-r9
   },
   p-Max-r13 [3] P-Max OPTIONAL, -- Need OP
   freqBandIndicator-r13 [4] FreqBandIndicator-NB-r13,
   freqBandInfo-r13 [5] NS-PmaxList-NB-r13 OPTIONAL, -- Need OR
   multiBandInfoList-r13 [6] MultiBandInfoList-NB-r13 OPTIONAL, -- Need OR
   downlinkBitmap-r13 [7] EXPLICIT DL-Bitmap-NB-r13 OPTIONAL, -- Need OP,	
   eutraControlRegionSize-r13 [8] ENUMERATED { n1(0), n2(1), n3(2) } OPTIONAL, -- Cond inband
   nrs-CRS-PowerOffset-r13 [9] ENUMERATED { dB-6(0), dB-4dot77(1), dB-3(2), 
      dB-1dot77(3), dB0(4), dB1(5), dB1dot23(6), dB2(7), dB3(8), dB4(9), 
      dB4dot23(10), dB5(11), dB6(12), dB7(13), dB8(14), dB9(15) } OPTIONAL, -- Cond inband-SamePCI
   schedulingInfoList-r13 [10] SchedulingInfoList-NB-r13,
   si-WindowLength-r13 [11] ENUMERATED { ms160(0), ms320(1), ms480(2), ms640(3)
      , ms960(4), ms1280(5), ms1600(6), spare1(7) },
   si-RadioFrameOffset-r13 [12] INTEGER (1..15) OPTIONAL, -- Need OP
   systemInfoValueTagList-r13 [13] SystemInfoValueTagList-NB-r13 OPTIONAL, -- Need OR
   lateNonCriticalExtension [14] OCTET STRING OPTIONAL,
   nonCriticalExtension [15] SystemInformationBlockType1-NB-v1350 OPTIONAL
}

BCCH-DL-SCH-MessageType-NB ::= CHOICE {
   c1 [0] EXPLICIT CHOICE {
      systemInformation-r13 [0] SystemInformation-NB,
      systemInformationBlockType1-r13 [1] SystemInformationBlockType1-NB
   },
   messageClassExtension [1] SEQUENCE {

   }
}

BCCH-DL-SCH-Message-NB ::= SEQUENCE {
   message [0] EXPLICIT BCCH-DL-SCH-MessageType-NB
}

PagingRecord-NB-r13 ::= SEQUENCE {
   ue-Identity-r13 [0] EXPLICIT PagingUE-Identity,
   ...
}

PagingRecordList-NB-r13 ::= SEQUENCE (SIZE (1..maxPageRec)) OF PagingRecord-NB-r13

Paging-NB ::= SEQUENCE {
   pagingRecordList-r13 [0] PagingRecordList-NB-r13 OPTIONAL, -- Need ON
   systemInfoModification-r13 [1] ENUMERATED { true(0) } OPTIONAL, -- Need ON
   systemInfoModification-eDRX-r13 [2] ENUMERATED { true(0) } OPTIONAL, -- Need ON
   nonCriticalExtension [3] SEQUENCE {

   } OPTIONAL
}

PCCH-MessageType-NB ::= CHOICE {
   c1 [0] EXPLICIT CHOICE {
      paging-r13 [0] Paging-NB
   },
   messageClassExtension [1] SEQUENCE {

   }
}

PCCH-Message-NB ::= SEQUENCE {
   message [0] EXPLICIT PCCH-MessageType-NB
}

UL-AM-RLC-NB-r13 ::= SEQUENCE {
   t-PollRetransmit-r13 [0] T-PollRetransmit-NB-r13,
   maxRetxThreshold-r13 [1] ENUMERATED { t1(0), t2(1), t3(2), t4(3), t6(4), 
      t8(5), t16(6), t32(7) }
}

DL-AM-RLC-NB-r13 ::= SEQUENCE {
   enableStatusReportSN-Gap-r13 [0] ENUMERATED { true(0) } OPTIONAL
}

RLC-Config-NB-r13 ::= CHOICE {
   am [0] SEQUENCE {
      ul-AM-RLC-r13 [0] UL-AM-RLC-NB-r13,
      dl-AM-RLC-r13 [1] DL-AM-RLC-NB-r13
   },
   ...
}

LogicalChannelConfig-NB-r13 ::= SEQUENCE {
   priority-r13 [0] INTEGER (1..16) OPTIONAL, -- Cond UL
   logicalChannelSR-Prohibit-r13 [1] BOOLEAN OPTIONAL,
   ...
}

RLC-Config-NB-v1430 ::= SEQUENCE {
   t-Reordering-r14 [0] T-Reordering OPTIONAL -- Cond twoHARQ
}

SRB-ToAddMod-NB-r13 ::= SEQUENCE {
   rlc-Config-r13 [0] EXPLICIT CHOICE {
      explicitValue [0] EXPLICIT RLC-Config-NB-r13,
      defaultValue [1] NULL
   } OPTIONAL, -- Cond Setup
   logicalChannelConfig-r13 [1] EXPLICIT CHOICE {
      explicitValue [0] LogicalChannelConfig-NB-r13,
      defaultValue [1] NULL
   } OPTIONAL,
   ...,
   [[
      rlc-Config-v1430 [2] RLC-Config-NB-v1430 OPTIONAL
   ]]
}

SRB-ToAddModList-NB-r13 ::= SEQUENCE (SIZE (1)) OF SRB-ToAddMod-NB-r13

PDCP-Config-NB-r13 ::= SEQUENCE {
   discardTimer-r13 [0] ENUMERATED { ms5120(0), ms10240(1), ms20480(2), 
      ms40960(3), ms81920(4), infinity(5), spare2(6), spare1(7) } OPTIONAL, -- Cond Setup
   headerCompression-r13 [1] EXPLICIT CHOICE {
      notUsed [0] NULL,
      rohc [1] SEQUENCE {
         maxCID-r13 [0] INTEGER (1..16383) DEFAULT 15,
         profiles-r13 [1] SEQUENCE {
            profile0x0002 [0] BOOLEAN,
            profile0x0003 [1] BOOLEAN,
            profile0x0004 [2] BOOLEAN,
            profile0x0006 [3] BOOLEAN,
            profile0x0102 [4] BOOLEAN,
            profile0x0103 [5] BOOLEAN,
            profile0x0104 [6] BOOLEAN
         },
         ...
      }
   },
   ...
}

DRB-ToAddMod-NB-r13 ::= SEQUENCE {
   eps-BearerIdentity-r13 [0] INTEGER (0..15) OPTIONAL, -- Cond DRB-Setup
   drb-Identity-r13 [1] DRB-Identity,
   pdcp-Config-r13 [2] PDCP-Config-NB-r13 OPTIONAL, -- Cond Setup
   rlc-Config-r13 [3] EXPLICIT RLC-Config-NB-r13 OPTIONAL, -- Cond Setup
   logicalChannelIdentity-r13 [4] INTEGER (3..10) OPTIONAL, -- Cond DRB-Setup
   logicalChannelConfig-r13 [5] LogicalChannelConfig-NB-r13 OPTIONAL,
   ...,
   [[
      rlc-Config-v1430 [6] RLC-Config-NB-v1430 OPTIONAL
   ]]
}

DRB-ToAddModList-NB-r13 ::= SEQUENCE (SIZE (1..maxDRB-NB-r13)) OF DRB-ToAddMod-NB-r13

DRB-ToReleaseList-NB-r13 ::= SEQUENCE (SIZE (1..maxDRB-NB-r13)) OF DRB-Identity

DRX-Config-NB-r13 ::= CHOICE {
   release [0] NULL,
   setup [1] SEQUENCE {
      onDurationTimer-r13 [0] ENUMERATED { pp1(0), pp2(1), pp3(2), pp4(3), 
         pp8(4), pp16(5), pp32(6), spare(7) },
      drx-InactivityTimer-r13 [1] ENUMERATED { pp0(0), pp1(1), pp2(2), pp3(3), 
         pp4(4), pp8(5), pp16(6), pp32(7) },
      drx-RetransmissionTimer-r13 [2] ENUMERATED { pp0(0), pp1(1), pp2(2), 
         pp4(3), pp6(4), pp8(5), pp16(6), pp24(7), pp33(8), spare7(9), 
         spare6(10), spare5(11), spare4(12), spare3(13), spare2(14), spare1(15)
          },
      drx-Cycle-r13 [3] ENUMERATED { sf256(0), sf512(1), sf1024(2), sf1536(3), 
         sf2048(4), sf3072(5), sf4096(6), sf4608(7), sf6144(8), sf7680(9), 
         sf8192(10), sf9216(11), spare4(12), spare3(13), spare2(14), spare1(15)
          },
      drx-StartOffset-r13 [4] INTEGER (0..255),
      drx-ULRetransmissionTimer-r13 [5] ENUMERATED { pp0(0), pp1(1), pp2(2), 
         pp4(3), pp6(4), pp8(5), pp16(6), pp24(7), pp33(8), pp40(9), pp64(10), 
         pp80(11), pp96(12), pp112(13), pp128(14), pp160(15), pp320(16) }
   }
}

MAC-MainConfig-NB-r13 ::= SEQUENCE {
   ul-SCH-Config-r13 [0] SEQUENCE {
      periodicBSR-Timer-r13 [0] PeriodicBSR-Timer-NB-r13 OPTIONAL, -- Need ON
      retxBSR-Timer-r13 [1] RetxBSR-Timer-NB-r13
   } OPTIONAL, -- Need ON
   drx-Config-r13 [1] EXPLICIT DRX-Config-NB-r13 OPTIONAL, -- Need ON
   timeAlignmentTimerDedicated-r13 [2] TimeAlignmentTimer,
   logicalChannelSR-Config-r13 [3] EXPLICIT CHOICE {
      release [0] NULL,
      setup [1] SEQUENCE {
         logicalChannelSR-ProhibitTimer-r13 [0] ENUMERATED { pp2(0), pp8(1), 
            pp32(2), pp128(3), pp512(4), pp1024(5), pp2048(6), spare(7) }
      }
   } OPTIONAL,
   ...,
   [[
      rai-Activation-r14 [4] ENUMERATED { true(0) } OPTIONAL,
      dataInactivityTimerConfig-r14 [5] EXPLICIT CHOICE {
         release [0] NULL,
         setup [1] SEQUENCE {
            dataInactivityTimer-r14 [0] DataInactivityTimer-r14
         }
      } OPTIONAL
   ]],
   [[
      drx-Cycle-v1430 [6] ENUMERATED { sf1280(0), sf2560(1), sf5120(2), 
         sf10240(3) } OPTIONAL
   ]],
   [[
      ra-CFRA-Config-r14 [7] ENUMERATED { true(0) } OPTIONAL
   ]]
}

DL-CarrierConfigDedicated-NB-r13 ::= SEQUENCE {
   dl-CarrierFreq-r13 [0] CarrierFreq-NB-r13,
   downlinkBitmapNonAnchor-r13 [1] EXPLICIT CHOICE {
      useNoBitmap-r13 [0] NULL,
      useAnchorBitmap-r13 [1] NULL,
      explicitBitmapConfiguration-r13 [2] EXPLICIT DL-Bitmap-NB-r13,
      spare [3] NULL
   } OPTIONAL, -- Need ON
   dl-GapNonAnchor-r13 [2] EXPLICIT CHOICE {
      useNoGap-r13 [0] NULL,
      useAnchorGapConfig-r13 [1] NULL,
      explicitGapConfiguration-r13 [2] DL-GapConfig-NB-r13,
      spare [3] NULL
   } OPTIONAL, -- Need ON
   inbandCarrierInfo-r13 [3] SEQUENCE {
      samePCI-Indicator-r13 [0] EXPLICIT CHOICE {
         samePCI-r13 [0] SEQUENCE {
            indexToMidPRB-r13 [0] INTEGER (-55..54)
         },
         differentPCI-r13 [1] SEQUENCE {
            eutra-NumCRS-Ports-r13 [0] ENUMERATED { same(0), four(1) }
         }
      } OPTIONAL, -- Cond anchor-guardband
      eutraControlRegionSize-r13 [1] ENUMERATED { n1(0), n2(1), n3(2) }
   } OPTIONAL,
   ...,
   [[
      nrs-PowerOffsetNonAnchor-v1330 [4] ENUMERATED { dB-12(0), dB-10(1), 
         dB-8(2), dB-6(3), dB-4(4), dB-2(5), dB0(6), dB3(7) } OPTIONAL
   ]]
}

UL-CarrierConfigDedicated-NB-r13 ::= SEQUENCE {
   ul-CarrierFreq-r13 [0] CarrierFreq-NB-r13 OPTIONAL,
   ...
}

CarrierConfigDedicated-NB-r13 ::= SEQUENCE {
   dl-CarrierConfig-r13 [0] DL-CarrierConfigDedicated-NB-r13,
   ul-CarrierConfig-r13 [1] UL-CarrierConfigDedicated-NB-r13
}

NPDCCH-ConfigDedicated-NB-r13 ::= SEQUENCE {
   npdcch-NumRepetitions-r13 [0] ENUMERATED { r1(0), r2(1), r4(2), r8(3), 
      r16(4), r32(5), r64(6), r128(7), r256(8), r512(9), r1024(10), r2048(11), 
      spare4(12), spare3(13), spare2(14), spare1(15) },
   npdcch-StartSF-USS-r13 [1] ENUMERATED { v1dot5(0), v2(1), v4(2), v8(3), 
      v16(4), v32(5), v48(6), v64(7) },
   npdcch-Offset-USS-r13 [2] ENUMERATED { zero(0), oneEighth(1), oneFourth(2), 
      threeEighth(3) }
}

NPUSCH-ConfigDedicated-NB-r13 ::= SEQUENCE {
   ack-NACK-NumRepetitions-r13 [0] ACK-NACK-NumRepetitions-NB-r13 OPTIONAL, -- Need ON
   npusch-AllSymbols-r13 [1] BOOLEAN OPTIONAL, -- Cond SRS
   groupHoppingDisabled-r13 [2] ENUMERATED { true(0) } OPTIONAL -- Need OR
}

UplinkPowerControlDedicated-NB-r13 ::= SEQUENCE {
   p0-UE-NPUSCH-r13 [0] INTEGER (-8..7)
}

PhysicalConfigDedicated-NB-r13 ::= SEQUENCE {
   carrierConfigDedicated-r13 [0] CarrierConfigDedicated-NB-r13 OPTIONAL, -- Need ON
   npdcch-ConfigDedicated-r13 [1] NPDCCH-ConfigDedicated-NB-r13 OPTIONAL, -- Need ON
   npusch-ConfigDedicated-r13 [2] NPUSCH-ConfigDedicated-NB-r13 OPTIONAL, -- Need ON
   uplinkPowerControlDedicated-r13 [3] UplinkPowerControlDedicated-NB-r13
       OPTIONAL,
   ...,
   [[
      twoHARQ-ProcessesConfig-r14 [4] ENUMERATED { true(0) } OPTIONAL
   ]],
   [[
      interferenceRandomisationConfig-r14 [5] ENUMERATED { true(0) } OPTIONAL
   ]]
}

RLF-TimersAndConstants-NB-r13 ::= CHOICE {
   release [0] NULL,
   setup [1] SEQUENCE {
      t301-r13 [0] ENUMERATED { ms2500(0), ms4000(1), ms6000(2), ms10000(3), 
         ms15000(4), ms25000(5), ms40000(6), ms60000(7) },
      t310-r13 [1] ENUMERATED { ms0(0), ms200(1), ms500(2), ms1000(3), 
         ms2000(4), ms4000(5), ms8000(6) },
      n310-r13 [2] ENUMERATED { n1(0), n2(1), n3(2), n4(3), n6(4), n8(5), 
         n10(6), n20(7) },
      t311-r13 [3] ENUMERATED { ms1000(0), ms3000(1), ms5000(2), ms10000(3), 
         ms15000(4), ms20000(5), ms30000(6) },
      n311-r13 [4] ENUMERATED { n1(0), n2(1), n3(2), n4(3), n5(4), n6(5), n8(6)
         , n10(7) },
      ...,
      [[
         t311-v1350 [5] ENUMERATED { ms40000(0), ms60000(1), ms90000(2), 
            ms120000(3) } OPTIONAL
      ]]
   }
}

RadioResourceConfigDedicated-NB-r13 ::= SEQUENCE {
   srb-ToAddModList-r13 [0] SRB-ToAddModList-NB-r13 OPTIONAL, -- Need ON
   drb-ToAddModList-r13 [1] DRB-ToAddModList-NB-r13 OPTIONAL, -- Need ON
   drb-ToReleaseList-r13 [2] DRB-ToReleaseList-NB-r13 OPTIONAL, -- Need ON
   mac-MainConfig-r13 [3] EXPLICIT CHOICE {
      explicitValue-r13 [0] MAC-MainConfig-NB-r13,
      defaultValue-r13 [1] NULL
   } OPTIONAL, -- Need ON
   physicalConfigDedicated-r13 [4] PhysicalConfigDedicated-NB-r13 OPTIONAL, -- Need ON
   rlf-TimersAndConstants-r13 [5] EXPLICIT RLF-TimersAndConstants-NB-r13
       OPTIONAL,
   ...
}

RRCConnectionReestablishment-NB-v1430-IEs ::= SEQUENCE {
   dl-NAS-MAC [0] BIT STRING  (SIZE (16)) OPTIONAL, -- Cond Reestablish-CP
   nonCriticalExtension [1] SEQUENCE {

   } OPTIONAL
}

RRCConnectionReestablishment-NB-r13-IEs ::= SEQUENCE {
   radioResourceConfigDedicated-r13 [0] RadioResourceConfigDedicated-NB-r13,
   nextHopChainingCount-r13 [1] NextHopChainingCount,
   lateNonCriticalExtension [2] OCTET STRING OPTIONAL,
   nonCriticalExtension [3] RRCConnectionReestablishment-NB-v1430-IEs OPTIONAL
}

RRCConnectionReestablishment-NB ::= SEQUENCE {
   rrc-TransactionIdentifier [0] RRC-TransactionIdentifier,
   criticalExtensions [1] EXPLICIT CHOICE {
      c1 [0] EXPLICIT CHOICE {
         rrcConnectionReestablishment-r13 [0] 
            RRCConnectionReestablishment-NB-r13-IEs,
         spare1 [1] NULL
      },
      criticalExtensionsFuture [1] SEQUENCE {

      }
   }
}

RRCConnectionReject-NB-r13-IEs ::= SEQUENCE {
   extendedWaitTime-r13 [0] INTEGER (1..1800),
   rrc-SuspendIndication-r13 [1] ENUMERATED { true(0) } OPTIONAL, -- Need ON
   lateNonCriticalExtension [2] OCTET STRING OPTIONAL,
   nonCriticalExtension [3] SEQUENCE {

   } OPTIONAL
}

RRCConnectionReject-NB ::= SEQUENCE {
   criticalExtensions [0] EXPLICIT CHOICE {
      c1 [0] EXPLICIT CHOICE {
         rrcConnectionReject-r13 [0] RRCConnectionReject-NB-r13-IEs,
         spare1 [1] NULL
      },
      criticalExtensionsFuture [1] SEQUENCE {

      }
   }
}

RRCConnectionSetup-NB-r13-IEs ::= SEQUENCE {
   radioResourceConfigDedicated-r13 [0] RadioResourceConfigDedicated-NB-r13,
   lateNonCriticalExtension [1] OCTET STRING OPTIONAL,
   nonCriticalExtension [2] SEQUENCE {

   } OPTIONAL
}

RRCConnectionSetup-NB ::= SEQUENCE {
   rrc-TransactionIdentifier [0] RRC-TransactionIdentifier,
   criticalExtensions [1] EXPLICIT CHOICE {
      c1 [0] EXPLICIT CHOICE {
         rrcConnectionSetup-r13 [0] RRCConnectionSetup-NB-r13-IEs,
         spare1 [1] NULL
      },
      criticalExtensionsFuture [1] SEQUENCE {

      }
   }
}

DL-CCCH-MessageType-NB ::= CHOICE {
   c1 [0] EXPLICIT CHOICE {
      rrcConnectionReestablishment-r13 [0] RRCConnectionReestablishment-NB,
      rrcConnectionReestablishmentReject-r13 [1] 
         RRCConnectionReestablishmentReject,
      rrcConnectionReject-r13 [2] RRCConnectionReject-NB,
      rrcConnectionSetup-r13 [3] RRCConnectionSetup-NB,
      spare4 [4] NULL,
      spare3 [5] NULL,
      spare2 [6] NULL,
      spare1 [7] NULL
   },
   messageClassExtension [1] SEQUENCE {

   }
}

DL-CCCH-Message-NB ::= SEQUENCE {
   message [0] EXPLICIT DL-CCCH-MessageType-NB
}

DLInformationTransfer-NB-r13-IEs ::= SEQUENCE {
   dedicatedInfoNAS-r13 [0] DedicatedInfoNAS,
   lateNonCriticalExtension [1] OCTET STRING OPTIONAL,
   nonCriticalExtension [2] SEQUENCE {

   } OPTIONAL
}

DLInformationTransfer-NB ::= SEQUENCE {
   rrc-TransactionIdentifier [0] RRC-TransactionIdentifier,
   criticalExtensions [1] EXPLICIT CHOICE {
      c1 [0] EXPLICIT CHOICE {
         dlInformationTransfer-r13 [0] DLInformationTransfer-NB-r13-IEs,
         spare1 [1] NULL
      },
      criticalExtensionsFuture [1] SEQUENCE {

      }
   }
}

RRCConnectionReconfiguration-NB-r13-IEs ::= SEQUENCE {
   dedicatedInfoNASList-r13 [0] SEQUENCE (SIZE (1..maxDRB-NB-r13)) OF DedicatedInfoNAS
       OPTIONAL, -- Need ON
   radioResourceConfigDedicated-r13 [1] RadioResourceConfigDedicated-NB-r13
       OPTIONAL, -- Need ON
   fullConfig-r13 [2] ENUMERATED { true(0) } OPTIONAL, -- Cond Reestab
   lateNonCriticalExtension [3] OCTET STRING OPTIONAL,
   nonCriticalExtension [4] SEQUENCE {

   } OPTIONAL
}

RRCConnectionReconfiguration-NB ::= SEQUENCE {
   rrc-TransactionIdentifier [0] RRC-TransactionIdentifier,
   criticalExtensions [1] EXPLICIT CHOICE {
      c1 [0] EXPLICIT CHOICE {
         rrcConnectionReconfiguration-r13 [0] 
            RRCConnectionReconfiguration-NB-r13-IEs,
         spare1 [1] NULL
      },
      criticalExtensionsFuture [1] SEQUENCE {

      }
   }
}

RedirectedCarrierInfo-NB-v1430 ::= SEQUENCE {
   redirectedCarrierOffsetDedicated-r14 [0] ENUMERATED { dB1(0), dB2(1), dB3(2)
      , dB4(3), dB5(4), dB6(5), dB8(6), dB10(7), dB12(8), dB14(9), dB16(10), 
      dB18(11), dB20(12), dB22(13), dB24(14), dB26(15) },
   t322-r14 [1] ENUMERATED { min5(0), min10(1), min20(2), min30(3), min60(4), 
      min120(5), min180(6), spare1(7) }
}

RRCConnectionRelease-NB-v1430-IEs ::= SEQUENCE {
   redirectedCarrierInfo-v1430 [0] RedirectedCarrierInfo-NB-v1430 OPTIONAL, -- Cond Redirection
   extendedWaitTime-CPdata-r14 [1] INTEGER (1..1800) OPTIONAL, -- Cond NoExtendedWaitTime
   nonCriticalExtension [2] SEQUENCE {

   } OPTIONAL
}

RRCConnectionRelease-NB-r13-IEs ::= SEQUENCE {
   releaseCause-r13 [0] ReleaseCause-NB-r13,
   resumeIdentity-r13 [1] ResumeIdentity-r13 OPTIONAL, -- Need OR
   extendedWaitTime-r13 [2] INTEGER (1..1800) OPTIONAL, -- Need ON
   redirectedCarrierInfo-r13 [3] RedirectedCarrierInfo-NB-r13 OPTIONAL, -- Need ON
   lateNonCriticalExtension [4] OCTET STRING OPTIONAL,
   nonCriticalExtension [5] RRCConnectionRelease-NB-v1430-IEs OPTIONAL
}

RRCConnectionRelease-NB ::= SEQUENCE {
   rrc-TransactionIdentifier [0] RRC-TransactionIdentifier,
   criticalExtensions [1] EXPLICIT CHOICE {
      c1 [0] EXPLICIT CHOICE {
         rrcConnectionRelease-r13 [0] RRCConnectionRelease-NB-r13-IEs,
         spare1 [1] NULL
      },
      criticalExtensionsFuture [1] SEQUENCE {

      }
   }
}

UECapabilityEnquiry-NB-r13-IEs ::= SEQUENCE {
   lateNonCriticalExtension [0] OCTET STRING OPTIONAL,
   nonCriticalExtension [1] SEQUENCE {

   } OPTIONAL
}

UECapabilityEnquiry-NB ::= SEQUENCE {
   rrc-TransactionIdentifier [0] RRC-TransactionIdentifier,
   criticalExtensions [1] EXPLICIT CHOICE {
      c1 [0] EXPLICIT CHOICE {
         ueCapabilityEnquiry-r13 [0] UECapabilityEnquiry-NB-r13-IEs,
         spare1 [1] NULL
      },
      criticalExtensionsFuture [1] SEQUENCE {

      }
   }
}

RRCConnectionResume-NB-r13-IEs ::= SEQUENCE {
   radioResourceConfigDedicated-r13 [0] RadioResourceConfigDedicated-NB-r13
       OPTIONAL, -- Need ON
   nextHopChainingCount-r13 [1] NextHopChainingCount,
   drb-ContinueROHC-r13 [2] ENUMERATED { true(0) } OPTIONAL, -- Need OP
   lateNonCriticalExtension [3] OCTET STRING OPTIONAL,
   nonCriticalExtension [4] SEQUENCE {

   } OPTIONAL
}

RRCConnectionResume-NB ::= SEQUENCE {
   rrc-TransactionIdentifier [0] RRC-TransactionIdentifier,
   criticalExtensions [1] EXPLICIT CHOICE {
      c1 [0] EXPLICIT CHOICE {
         rrcConnectionResume-r13 [0] RRCConnectionResume-NB-r13-IEs,
         spare1 [1] NULL
      },
      criticalExtensionsFuture [1] SEQUENCE {

      }
   }
}

DL-DCCH-MessageType-NB ::= CHOICE {
   c1 [0] EXPLICIT CHOICE {
      dlInformationTransfer-r13 [0] DLInformationTransfer-NB,
      rrcConnectionReconfiguration-r13 [1] RRCConnectionReconfiguration-NB,
      rrcConnectionRelease-r13 [2] RRCConnectionRelease-NB,
      securityModeCommand-r13 [3] SecurityModeCommand,
      ueCapabilityEnquiry-r13 [4] UECapabilityEnquiry-NB,
      rrcConnectionResume-r13 [5] RRCConnectionResume-NB,
      spare2 [6] NULL,
      spare1 [7] NULL
   },
   messageClassExtension [1] SEQUENCE {

   }
}

DL-DCCH-Message-NB ::= SEQUENCE {
   message [0] EXPLICIT DL-DCCH-MessageType-NB
}

RRCConnectionReestablishmentRequest-NB-r13-IEs ::= SEQUENCE {
   ue-Identity-r13 [0] ReestabUE-Identity,
   reestablishmentCause-r13 [1] ReestablishmentCause-NB-r13,
   cqi-NPDCCH-r14 [2] CQI-NPDCCH-NB-r14,
   earlyContentionResolution-r14 [3] BOOLEAN,
   spare [4] BIT STRING  (SIZE (20))
}

ReestabUE-Identity-CP-NB-r14 ::= SEQUENCE {
   s-TMSI-r14 [0] S-TMSI,
   ul-NAS-MAC-r14 [1] BIT STRING  (SIZE (16)),
   ul-NAS-Count-r14 [2] BIT STRING  (SIZE (5))
}

RRCConnectionReestablishmentRequest-NB-r14-IEs ::= SEQUENCE {
   ue-Identity-r14 [0] ReestabUE-Identity-CP-NB-r14,
   reestablishmentCause-r14 [1] ReestablishmentCause-NB-r13,
   cqi-NPDCCH-r14 [2] CQI-NPDCCH-Short-NB-r14,
   earlyContentionResolution-r14 [3] BOOLEAN,
   spare [4] BIT STRING  (SIZE (1))
}

RRCConnectionReestablishmentRequest-NB ::= SEQUENCE {
   criticalExtensions [0] EXPLICIT CHOICE {
      rrcConnectionReestablishmentRequest-r13 [0] 
         RRCConnectionReestablishmentRequest-NB-r13-IEs,
      later [1] EXPLICIT CHOICE {
         rrcConnectionReestablishmentRequest-r14 [0] 
            RRCConnectionReestablishmentRequest-NB-r14-IEs,
         criticalExtensionsFuture [1] SEQUENCE {

         }
      }
   }
}

RRCConnectionRequest-NB-r13-IEs ::= SEQUENCE {
   ue-Identity-r13 [0] EXPLICIT InitialUE-Identity,
   establishmentCause-r13 [1] EstablishmentCause-NB-r13,
   multiToneSupport-r13 [2] ENUMERATED { true(0) } OPTIONAL,
   multiCarrierSupport-r13 [3] ENUMERATED { true(0) } OPTIONAL,
   earlyContentionResolution-r14 [4] BOOLEAN,
   cqi-NPDCCH-r14 [5] CQI-NPDCCH-NB-r14,
   spare [6] BIT STRING  (SIZE (17))
}

RRCConnectionRequest-NB ::= SEQUENCE {
   criticalExtensions [0] EXPLICIT CHOICE {
      rrcConnectionRequest-r13 [0] RRCConnectionRequest-NB-r13-IEs,
      criticalExtensionsFuture [1] SEQUENCE {

      }
   }
}

RRCConnectionResumeRequest-NB-r13-IEs ::= SEQUENCE {
   resumeID-r13 [0] ResumeIdentity-r13,
   shortResumeMAC-I-r13 [1] ShortMAC-I,
   resumeCause-r13 [2] EstablishmentCause-NB-r13,
   earlyContentionResolution-r14 [3] BOOLEAN,
   cqi-NPDCCH-r14 [4] CQI-NPDCCH-NB-r14,
   spare [5] BIT STRING  (SIZE (4))
}

RRCConnectionResumeRequest-NB ::= SEQUENCE {
   criticalExtensions [0] EXPLICIT CHOICE {
      rrcConnectionResumeRequest-r13 [0] RRCConnectionResumeRequest-NB-r13-IEs,
      criticalExtensionsFuture [1] SEQUENCE {

      }
   }
}

UL-CCCH-MessageType-NB ::= CHOICE {
   c1 [0] EXPLICIT CHOICE {
      rrcConnectionReestablishmentRequest-r13 [0] 
         RRCConnectionReestablishmentRequest-NB,
      rrcConnectionRequest-r13 [1] RRCConnectionRequest-NB,
      rrcConnectionResumeRequest-r13 [2] RRCConnectionResumeRequest-NB,
      spare1 [3] NULL
   },
   messageClassExtension [1] SEQUENCE {

   }
}

UL-CCCH-Message-NB ::= SEQUENCE {
   message [0] EXPLICIT UL-CCCH-MessageType-NB
}

SC-MTCH-SchedulingInfo-NB-r14 ::= SEQUENCE {
   onDurationTimerSCPTM-r14 [0] ENUMERATED { pp1(0), pp2(1), pp3(2), pp4(3), 
      pp8(4), pp16(5), pp32(6), spare(7) },
   drx-InactivityTimerSCPTM-r14 [1] ENUMERATED { pp0(0), pp1(1), pp2(2), pp3(3)
      , pp4(4), pp8(5), pp16(6), pp32(7) },
   schedulingPeriodStartOffsetSCPTM-r14 [2] EXPLICIT CHOICE {
      sf10 [0] INTEGER (0..9),
      sf20 [1] INTEGER (0..19),
      sf32 [2] INTEGER (0..31),
      sf40 [3] INTEGER (0..39),
      sf64 [4] INTEGER (0..63),
      sf80 [5] INTEGER (0..79),
      sf128 [6] INTEGER (0..127),
      sf160 [7] INTEGER (0..159),
      sf256 [8] INTEGER (0..255),
      sf320 [9] INTEGER (0..319),
      sf512 [10] INTEGER (0..511),
      sf640 [11] INTEGER (0..639),
      sf1024 [12] INTEGER (0..1023),
      sf2048 [13] INTEGER (0..2047),
      sf4096 [14] INTEGER (0..4095),
      sf8192 [15] INTEGER (0..8191)
   },
   ...
}

SC-MTCH-Info-NB-r14 ::= SEQUENCE {
   sc-mtch-CarrierConfig-r14 [0] EXPLICIT CHOICE {
      dl-CarrierConfig-r14 [0] DL-CarrierConfigCommon-NB-r14,
      dl-CarrierIndex-r14 [1] INTEGER (0..maxNonAnchorCarriers-NB-r14)
   },
   mbmsSessionInfo-r14 [1] MBMSSessionInfo-r13,
   g-RNTI-r14 [2] BIT STRING  (SIZE (16)),
   sc-mtch-SchedulingInfo-r14 [3] SC-MTCH-SchedulingInfo-NB-r14 OPTIONAL, -- Need OP
   sc-mtch-NeighbourCell-r14 [4] BIT STRING  (SIZE (maxNeighCell-SCPTM-NB-r14)) OPTIONAL, -- Need OP
   npdcch-NPDSCH-MaxTBS-SC-MTCH-r14 [5] ENUMERATED { n680(0), n2536(1) },
   npdcch-NumRepetitions-SC-MTCH-r14 [6] ENUMERATED { r1(0), r2(1), r4(2), 
      r8(3), r16(4), r32(5), r64(6), r128(7), r256(8), r512(9), r1024(10), 
      r2048(11), spare4(12), spare3(13), spare2(14), spare1(15) },
   npdcch-StartSF-SC-MTCH-r14 [7] ENUMERATED { v1dot5(0), v2(1), v4(2), v8(3), 
      v16(4), v32(5), v48(6), v64(7) },
   npdcch-Offset-SC-MTCH-r14 [8] ENUMERATED { zero(0), oneEighth(1), 
      oneQuarter(2), threeEighth(3), oneHalf(4), fiveEighth(5), threeQuarter(6)
      , sevenEighth(7) },
   ...
}

SC-MTCH-InfoList-NB-r14 ::= SEQUENCE (SIZE (0..maxSC-MTCH-NB-r14)) OF SC-MTCH-Info-NB-r14

PCI-ARFCN-NB-r14 ::= SEQUENCE {
   physCellId-r14 [0] PhysCellId,
   carrierFreq-r14 [1] CarrierFreq-NB-r13 OPTIONAL -- Need OP
}

SCPTM-NeighbourCellList-NB-r14 ::= SEQUENCE (SIZE (1..maxNeighCell-SCPTM-NB-r14)) OF PCI-ARFCN-NB-r14

SCPTMConfiguration-NB-r14 ::= SEQUENCE {
   sc-mtch-InfoList-r14 [0] SC-MTCH-InfoList-NB-r14,
   scptm-NeighbourCellList-r14 [1] SCPTM-NeighbourCellList-NB-r14 OPTIONAL, -- Need OP
   lateNonCriticalExtension [2] OCTET STRING OPTIONAL,
   nonCriticalExtension [3] SEQUENCE {

   } OPTIONAL
}

SC-MCCH-MessageType-NB ::= CHOICE {
   c1 [0] EXPLICIT CHOICE {
      scptmConfiguration-r14 [0] SCPTMConfiguration-NB-r14
   },
   messageClassExtension [1] SEQUENCE {

   }
}

SC-MCCH-Message-NB ::= SEQUENCE {
   message [0] EXPLICIT SC-MCCH-MessageType-NB
}

RRCConnectionReconfigurationComplete-NB-r13-IEs ::= SEQUENCE {
   lateNonCriticalExtension [0] OCTET STRING OPTIONAL,
   nonCriticalExtension [1] SEQUENCE {

   } OPTIONAL
}

RRCConnectionReconfigurationComplete-NB ::= SEQUENCE {
   rrc-TransactionIdentifier [0] RRC-TransactionIdentifier,
   criticalExtensions [1] EXPLICIT CHOICE {
      rrcConnectionReconfigurationComplete-r13 [0] 
         RRCConnectionReconfigurationComplete-NB-r13-IEs,
      criticalExtensionsFuture [1] SEQUENCE {

      }
   }
}

MeasResultServCell-NB-r14 ::= SEQUENCE {
   nrsrpResult-r14 [0] NRSRP-Range-NB-r14,
   nrsrqResult-r14 [1] NRSRQ-Range-NB-r14
}

RRCConnectionReestablishmentComplete-NB-v1470-IEs ::= SEQUENCE {
   measResultServCell-r14 [0] MeasResultServCell-NB-r14 OPTIONAL,
   nonCriticalExtension [1] SEQUENCE {

   } OPTIONAL
}

RRCConnectionReestablishmentComplete-NB-r13-IEs ::= SEQUENCE {
   lateNonCriticalExtension [0] OCTET STRING OPTIONAL,
   nonCriticalExtension [1] RRCConnectionReestablishmentComplete-NB-v1470-IEs
       OPTIONAL
}

RRCConnectionReestablishmentComplete-NB ::= SEQUENCE {
   rrc-TransactionIdentifier [0] RRC-TransactionIdentifier,
   criticalExtensions [1] EXPLICIT CHOICE {
      rrcConnectionReestablishmentComplete-r13 [0] 
         RRCConnectionReestablishmentComplete-NB-r13-IEs,
      criticalExtensionsFuture [1] SEQUENCE {

      }
   }
}

RRCConnectionSetupComplete-NB-v1470-IEs ::= SEQUENCE {
   measResultServCell-r14 [0] MeasResultServCell-NB-r14 OPTIONAL,
   nonCriticalExtension [1] SEQUENCE {

   } OPTIONAL
}

RRCConnectionSetupComplete-NB-v1430-IEs ::= SEQUENCE {
   gummei-Type-r14 [0] ENUMERATED { mapped(0) } OPTIONAL,
   dcn-ID-r14 [1] INTEGER (0..65535) OPTIONAL,
   nonCriticalExtension [2] RRCConnectionSetupComplete-NB-v1470-IEs OPTIONAL
}

RRCConnectionSetupComplete-NB-r13-IEs ::= SEQUENCE {
   selectedPLMN-Identity-r13 [0] INTEGER (1..maxPLMN-r11),
   s-TMSI-r13 [1] S-TMSI OPTIONAL,
   registeredMME-r13 [2] RegisteredMME OPTIONAL,
   dedicatedInfoNAS-r13 [3] DedicatedInfoNAS,
   attachWithoutPDN-Connectivity-r13 [4] ENUMERATED { true(0) } OPTIONAL,
   up-CIoT-EPS-Optimisation-r13 [5] ENUMERATED { true(0) } OPTIONAL,
   lateNonCriticalExtension [6] OCTET STRING OPTIONAL,
   nonCriticalExtension [7] RRCConnectionSetupComplete-NB-v1430-IEs OPTIONAL
}

RRCConnectionSetupComplete-NB ::= SEQUENCE {
   rrc-TransactionIdentifier [0] RRC-TransactionIdentifier,
   criticalExtensions [1] EXPLICIT CHOICE {
      rrcConnectionSetupComplete-r13 [0] RRCConnectionSetupComplete-NB-r13-IEs,
      criticalExtensionsFuture [1] SEQUENCE {

      }
   }
}

PDCP-Parameters-NB-r13 ::= SEQUENCE {
   supportedROHC-Profiles-r13 [0] SEQUENCE {
      profile0x0002 [0] BOOLEAN,
      profile0x0003 [1] BOOLEAN,
      profile0x0004 [2] BOOLEAN,
      profile0x0006 [3] BOOLEAN,
      profile0x0102 [4] BOOLEAN,
      profile0x0103 [5] BOOLEAN,
      profile0x0104 [6] BOOLEAN
   },
   maxNumberROHC-ContextSessions-r13 [1] ENUMERATED { cs2(0), cs4(1), cs8(2), 
      cs12(3) } DEFAULT cs2,
   ...
}

PhyLayerParameters-NB-r13 ::= SEQUENCE {
   multiTone-r13 [0] ENUMERATED { supported(0) } OPTIONAL,
   multiCarrier-r13 [1] ENUMERATED { supported(0) } OPTIONAL
}

SupportedBand-NB-r13 ::= SEQUENCE {
   band-r13 [0] FreqBandIndicator-NB-r13,
   powerClassNB-20dBm-r13 [1] ENUMERATED { supported(0) } OPTIONAL
}

SupportedBandList-NB-r13 ::= SEQUENCE (SIZE (1..maxBands)) OF SupportedBand-NB-r13

RF-Parameters-NB-r13 ::= SEQUENCE {
   supportedBandList-r13 [0] SupportedBandList-NB-r13,
   multiNS-Pmax-r13 [1] ENUMERATED { supported(0) } OPTIONAL
}

UE-Capability-NB-r13 ::= SEQUENCE {
   accessStratumRelease-r13 [0] AccessStratumRelease-NB-r13,
   ue-Category-NB-r13 [1] ENUMERATED { nb1(0) } OPTIONAL,
   multipleDRB-r13 [2] ENUMERATED { supported(0) } OPTIONAL,
   pdcp-Parameters-r13 [3] PDCP-Parameters-NB-r13 OPTIONAL,
   phyLayerParameters-r13 [4] PhyLayerParameters-NB-r13,
   rf-Parameters-r13 [5] RF-Parameters-NB-r13,
   dummy [6] SEQUENCE {

   } OPTIONAL
}

UE-RadioPagingInfo-NB-r13 ::= SEQUENCE {
   ue-Category-NB-r13 [0] ENUMERATED { nb1(0) } OPTIONAL,
   ...,
   [[
      multiCarrierPaging-r14 [1] ENUMERATED { true(0) } OPTIONAL
   ]]
}

MAC-Parameters-NB-r14 ::= SEQUENCE {
   dataInactMon-r14 [0] ENUMERATED { supported(0) } OPTIONAL,
   rai-Support-r14 [1] ENUMERATED { supported(0) } OPTIONAL
}

PhyLayerParameters-NB-v1430 ::= SEQUENCE {
   multiCarrier-NPRACH-r14 [0] ENUMERATED { supported(0) } OPTIONAL,
   twoHARQ-Processes-r14 [1] ENUMERATED { supported(0) } OPTIONAL
}

RF-Parameters-NB-v1430 ::= SEQUENCE {
   powerClassNB-14dBm-r14 [0] ENUMERATED { supported(0) } OPTIONAL
}

PhyLayerParameters-NB-v1440 ::= SEQUENCE {
   interferenceRandomisation-r14 [0] ENUMERATED { supported(0) } OPTIONAL
}

UE-Capability-NB-v1480-IEs ::= SEQUENCE {
--Following field is only to be used for late REL-14 extensions
   lateNonCriticalExtension [0] OCTET STRING OPTIONAL,
   nonCriticalExtension [1] SEQUENCE {

   } OPTIONAL
}

UE-Capability-NB-v1440-IEs ::= SEQUENCE {
   phyLayerParameters-v1440 [0] PhyLayerParameters-NB-v1440 OPTIONAL,
   nonCriticalExtension [1] UE-Capability-NB-v1480-IEs OPTIONAL
}

UE-Capability-NB-Ext-r14-IEs ::= SEQUENCE {
   ue-Category-NB-r14 [0] ENUMERATED { nb2(0) } OPTIONAL,
   mac-Parameters-r14 [1] MAC-Parameters-NB-r14 OPTIONAL,
   phyLayerParameters-v1430 [2] PhyLayerParameters-NB-v1430 OPTIONAL,
   rf-Parameters-v1430 [3] RF-Parameters-NB-v1430,
   nonCriticalExtension [4] UE-Capability-NB-v1440-IEs OPTIONAL
}

UECapabilityInformation-NB-Ext-r14-IEs ::= SEQUENCE {
   ue-Capability-ContainerExt-r14 [0] OCTET STRING (CONTAINING 
      UE-Capability-NB-Ext-r14-IEs),
   nonCriticalExtension [1] SEQUENCE {

   } OPTIONAL
}

UECapabilityInformation-NB-r13-IEs ::= SEQUENCE {
   ue-Capability-r13 [0] UE-Capability-NB-r13,
   ue-RadioPagingInfo-r13 [1] UE-RadioPagingInfo-NB-r13,
   lateNonCriticalExtension [2] OCTET STRING OPTIONAL,
   nonCriticalExtension [3] UECapabilityInformation-NB-Ext-r14-IEs OPTIONAL
}

UECapabilityInformation-NB ::= SEQUENCE {
   rrc-TransactionIdentifier [0] RRC-TransactionIdentifier,
   criticalExtensions [1] EXPLICIT CHOICE {
      ueCapabilityInformation-r13 [0] UECapabilityInformation-NB-r13-IEs,
      criticalExtensionsFuture [1] SEQUENCE {

      }
   }
}

ULInformationTransfer-NB-r13-IEs ::= SEQUENCE {
   dedicatedInfoNAS-r13 [0] DedicatedInfoNAS,
   lateNonCriticalExtension [1] OCTET STRING OPTIONAL,
   nonCriticalExtension [2] SEQUENCE {

   } OPTIONAL
}

ULInformationTransfer-NB ::= SEQUENCE {
   criticalExtensions [0] EXPLICIT CHOICE {
      ulInformationTransfer-r13 [0] ULInformationTransfer-NB-r13-IEs,
      criticalExtensionsFuture [1] SEQUENCE {

      }
   }
}

RRCConnectionResumeComplete-NB-v1470-IEs ::= SEQUENCE {
   measResultServCell-r14 [0] MeasResultServCell-NB-r14 OPTIONAL,
   nonCriticalExtension [1] SEQUENCE {

   } OPTIONAL
}

RRCConnectionResumeComplete-NB-r13-IEs ::= SEQUENCE {
   selectedPLMN-Identity-r13 [0] INTEGER (1..maxPLMN-r11) OPTIONAL,
   dedicatedInfoNAS-r13 [1] DedicatedInfoNAS OPTIONAL,
   lateNonCriticalExtension [2] OCTET STRING OPTIONAL,
   nonCriticalExtension [3] RRCConnectionResumeComplete-NB-v1470-IEs OPTIONAL
}

RRCConnectionResumeComplete-NB ::= SEQUENCE {
   rrc-TransactionIdentifier [0] RRC-TransactionIdentifier,
   criticalExtensions [1] EXPLICIT CHOICE {
      rrcConnectionResumeComplete-r13 [0] 
         RRCConnectionResumeComplete-NB-r13-IEs,
      criticalExtensionsFuture [1] SEQUENCE {

      }
   }
}

UL-DCCH-MessageType-NB ::= CHOICE {
   c1 [0] EXPLICIT CHOICE {
      rrcConnectionReconfigurationComplete-r13 [0] 
         RRCConnectionReconfigurationComplete-NB,
      rrcConnectionReestablishmentComplete-r13 [1] 
         RRCConnectionReestablishmentComplete-NB,
      rrcConnectionSetupComplete-r13 [2] RRCConnectionSetupComplete-NB,
      securityModeComplete-r13 [3] SecurityModeComplete,
      securityModeFailure-r13 [4] SecurityModeFailure,
      ueCapabilityInformation-r13 [5] UECapabilityInformation-NB,
      ulInformationTransfer-r13 [6] ULInformationTransfer-NB,
      rrcConnectionResumeComplete-r13 [7] RRCConnectionResumeComplete-NB,
      spare8 [8] NULL,
      spare7 [9] NULL,
      spare6 [10] NULL,
      spare5 [11] NULL,
      spare4 [12] NULL,
      spare3 [13] NULL,
      spare2 [14] NULL,
      spare1 [15] NULL
   },
   messageClassExtension [1] SEQUENCE {

   }
}

UL-DCCH-Message-NB ::= SEQUENCE {
   message [0] EXPLICIT UL-DCCH-MessageType-NB
}

-- Value assignments

maxNPRACH-Resources-NB-r13 INTEGER ::= 3

maxNonAnchorCarriers-NB-r14 INTEGER ::= 15

maxDRB-NB-r13 INTEGER ::= 2

maxNeighCell-SCPTM-NB-r14 INTEGER ::= 8

maxNS-Pmax-NB-r13 INTEGER ::= 4

maxSC-MTCH-NB-r14 INTEGER ::= 64

maxSI-Message-NB-r13 INTEGER ::= 8


END
