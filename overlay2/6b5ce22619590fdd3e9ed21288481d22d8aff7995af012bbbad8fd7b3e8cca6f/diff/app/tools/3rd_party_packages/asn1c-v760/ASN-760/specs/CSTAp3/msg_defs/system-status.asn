CSTA-system-status
	{ iso( 1) identified-organization( 3) icd-ecma( 12)
		standard( 0) csta3( 285) system-status( 211) }

DEFINITIONS ::=
BEGIN

IMPORTS
OPERATION, ERROR FROM Remote-Operations-Information-Objects
	{joint-iso-itu-t remote-operations(4) informationObjects(5) version1(0) }

-- Data Types --
universalFailure FROM CSTA-error-definition
	{ iso( 1) identified-organization( 3) icd-ecma( 12)
		standard( 0) csta3( 285) error-definition( 120) }
SysStatRegisterID, SystemStatus FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

systemStatus OPERATION ::=
{ 	ARGUMENT 		SystemStatusArg
	RESULT 			SystemStatusRes
	ERRORS 			{universalFailure }
	CODE 			local: 211 }

SystemStatusArg ::= SEQUENCE
{ 	sysStatRegisterID 		SysStatRegisterID 		OPTIONAL,
	systemStatus 			SystemStatus,
	extensions 			CSTACommonArguments 		OPTIONAL }

SystemStatusRes ::= CHOICE
{ 	extensions 			CSTACommonArguments,
	noData 				NULL }

END -- of CSTA-system-status
