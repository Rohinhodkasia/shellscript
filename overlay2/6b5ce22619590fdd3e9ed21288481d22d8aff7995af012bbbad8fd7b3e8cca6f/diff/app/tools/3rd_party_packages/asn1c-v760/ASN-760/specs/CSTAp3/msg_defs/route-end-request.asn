CSTA-route-end-request
	{ iso( 1) identified-organization( 3) icd-ecma( 12)
		standard( 0) csta3( 285) route-end-request( 85) }

DEFINITIONS ::=
BEGIN

IMPORTS
OPERATION, ERROR FROM Remote-Operations-Information-Objects 
	{joint-iso-itu-t remote-operations(4) informationObjects(5) version1(0) }

-- Data Types --
universalFailure, ErrorValue FROM CSTA-error-definition
	{ iso( 1) identified-organization( 3) icd-ecma( 12)
		standard( 0) csta3( 285) error-definition( 120) }
CorrelatorData, RouteRegisterReqID, RouteingCrossRefID  FROM CSTA-device-feature-types
	{ iso( 1) identified-organization( 3) icd-ecma( 12)
		standard( 0) csta3( 285) device-feature-types( 127) }
CSTACommonArguments FROM CSTA-extension-types 
	{ iso( 1) identified-organization( 3) icd-ecma( 12)
		standard( 0) csta3( 285) extension-types( 129) };

routeEndRequest OPERATION ::=
{	ARGUMENT 		RouteEndRequestArgument
	ERRORS  		{universalFailure }
	ALWAYS RESPONDS		FALSE
	CODE			local: 35 }

RouteEndRequestArgument ::= SEQUENCE {
	crossRefIdentifier		RouteingCrossRefID,
	routeRegisterReqID 		[ 0] IMPLICIT RouteRegisterReqID	OPTIONAL,
	errorValue			[ 1] ErrorValue				OPTIONAL,
	correlatorData			[ 2] IMPLICIT CorrelatorData		OPTIONAL,
	extensions			CSTACommonArguments			OPTIONAL }

END  -- of CSTA-route-end-request
