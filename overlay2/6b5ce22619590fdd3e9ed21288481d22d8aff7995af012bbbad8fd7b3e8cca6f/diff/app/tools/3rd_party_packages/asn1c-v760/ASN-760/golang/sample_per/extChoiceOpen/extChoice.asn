-- Extended choice construct

ExtChoice DEFINITIONS AUTOMATIC TAGS ::= BEGIN

AliasAddress ::= CHOICE
{
 e164           IA5String (SIZE (1..128)) (FROM ("0123456789#*,")),
 -- h323-ID        BMPString (SIZE (1..256)),	
 ...
}

END
