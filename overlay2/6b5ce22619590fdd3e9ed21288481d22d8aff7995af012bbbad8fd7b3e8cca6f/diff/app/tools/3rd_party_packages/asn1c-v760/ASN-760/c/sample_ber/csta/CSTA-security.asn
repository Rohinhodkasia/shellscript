-- This file was generated by the Objective Systems ASN1C Compiler
-- (http://www.obj-sys.com).  Version: 6.3.A, Date: 17-Oct-2009.

CSTA-security 
{ iso( 1) identified-organization( 3) icd-ecma( 0012)
		standard( 0) csta( 180) version1( 1) security( 128) }
DEFINITIONS ::= BEGIN

-- Productions

PrivilegeAttributeCertificate ::= NULL

Seal ::= SEQUENCE {
   algorithmIdentifier OBJECT IDENTIFIER,
   keyIdentifier OCTET STRING,
   seal OCTET STRING
}

CSTASecurityData ::= SEQUENCE {
   messageSequenceNumber INTEGER OPTIONAL,
   timeStamp UTCTime OPTIONAL,
   privilegeAttributeCertificate PrivilegeAttributeCertificate OPTIONAL,
   seal Seal OPTIONAL
}

END
