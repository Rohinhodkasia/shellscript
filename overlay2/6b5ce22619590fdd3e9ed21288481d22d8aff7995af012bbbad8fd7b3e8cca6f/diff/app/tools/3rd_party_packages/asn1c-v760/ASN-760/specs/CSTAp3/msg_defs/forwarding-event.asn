CSTA-forwarding-event
	{ iso( 1) identified-organization( 3) icd-ecma( 12)
		standard( 0) csta3( 285) forwarding-event( 43) }

DEFINITIONS ::=
BEGIN

IMPORTS

-- Data Types --
DeviceID, SubjectDeviceID FROM CSTA-device-identifiers
	{ iso( 1) identified-organization( 3) icd-ecma( 12)
		standard( 0) csta3( 285) device-identifiers( 123) }
ForwardingType, ForwardDefault FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

ForwardingEvent ::= SEQUENCE
{	device 				SubjectDeviceID,
	forwardingType 			ForwardingType				OPTIONAL,
	forwardStatus 			BOOLEAN,
	forwardTo	 		DeviceID				OPTIONAL,
	forwardDefault 			ForwardDefault				OPTIONAL,
	ringCount 			INTEGER (1..100)			OPTIONAL,
	ringDuration			[4] IMPLICIT INTEGER			OPTIONAL,
	extensions 			CSTACommonArguments			OPTIONAL }

END -- of CSTA-forwarding-event
