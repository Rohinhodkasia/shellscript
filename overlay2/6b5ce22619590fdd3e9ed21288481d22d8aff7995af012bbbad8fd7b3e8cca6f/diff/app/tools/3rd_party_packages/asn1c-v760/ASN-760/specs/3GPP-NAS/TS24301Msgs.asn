/* 
Module for 3GPP TS 24.301 Messages, Releases 8 through 16.
Each message, being a standard L3 Message (see TS 24.007), has a standard
message header.  The header is factored out of each of the message types.
Current versions:
    v15.8.0
    v16.8.0
    v17.3.0

*/
TS24301Msgs DEFINITIONS AUTOMATIC TAGS ::=
BEGIN

IMPORTS 
L3HdrOptions, NAS-PROTOCOL-CLASS, ProtoDiscr, SecProtMsgHeader FROM TS24007L3

IMPORTS
AccessPointName, AuthFailureParam, AuthParamAUTN, 
AuthParamRAND, DaylightSavingTime, CiphKeySeqNum, 
ConnectivityType, DeviceProperties, DRXParameter, EmergencyNumberList, 
ExtDRXParams, ExtProtoConfigOptions, GPRSTimer, GPRSTimer2, GPRSTimer3, 
IdentityType2Value, IMEISVRequest, LinkedTI, LLCSAPIValue, LocAreaIdent, 
MobileIdentity, MobileStationClassmark2, MobileStationClassmark3, 
MSNetworkCapability, MSNetFeatureSupport, NBIFOMContainer, 
NetworkName, NetResourceIdentContainer, P-TMSISignature, 
PacketFlowIdentValue, PLMNList, ProtocolConfigOptions, ReattemptInd, 
RequestTypeValue, QualityOfService, RadioPriority, SupportedCodecList, 
TFT, TimeZone, TimeZoneAndTime, TMSIStatus, VoiceDomainPref, 
WLANOffloadAccept, DcnID, Non3GPPNetPolicies, ExtQualityOfService
FROM TS24008IES

IMPORTS
AddnUpdateResult, AddnUpdateType, APNAggMaxBitRate, AuthRespParam, 
CLI, CtrlPlaneOnlyInd, CtrlPlaneSvcType, CSFBResponse, DetachType, 
EMMCause, EPSAttachType, EPSAttachResult, EPSBearerContextStatus, 
EPSMobileIdentity, EPSMobileIdentity-GUTI, EPSNetworkFeatureSupport,
EPSQualityOfService, EPSUpdateResult, EPSUpdateType,
ESMCause, ESMInfoXferFlag, ExtEMMCause, GenMessageContainer,
GenMsgContainerType, GUTIType, HdrCompressConfig, HdrCompressConfigStat, 
KSIAndSequenceNumber, LCSClientIdentity, LCSIndicator, 
LinkedEPSBearerIdent, NASKeySetIdentifier, NASMessageContainer, 
NASSecurityAlgorithms, Nonce, PagingIdentity, PDNAddress, PDNType, 
PKMFAddress, ReleaseAssistInd, RemoteUECtxtList, ServiceType, 
ServPLMNRateCtrl, ShortMAC, SMSServicesStatus, SSCode, TrackingAreaIdent, 
TrackingAreaIdentList, UENetworkCapability, 
UERadioCapInfoUpdateNeeded, UESecurityCapability, NetworkPolicy,
ExtEmergencyNumberList, CipherKeyData, UEAddlSecurityCapability,
UEStatus, AdditionalInfoReq, HashMME, ReplayedNASMsgContainer,
ExtAPNAggMaxBitRate, N1UENetCapability, UERadioCapIdAvailability,
UERadioCapIdRequest, UERadioCapId, UERadioCapIdDeletionInd,
NotificationIndicator, UserDataContainer, WUSAssistanceInfo, NBS1DRXParameter
FROM TS24301IES
;

TS24301-IE-OBJECTSET NAS-PROTOCOL-CLASS ::= {
   obj-AttachAccept | obj-AttachComplete | obj-AttachReject |
   obj-AttachRequest | obj-AuthFailure | obj-AuthReject | obj-AuthRequest |
   obj-AuthResponse | obj-CSServiceNotif | obj-DetachAccept | 
   obj-DetachRequest | obj-DLNASTransport | obj-EMMInformation |
   obj-EMMStatus | obj-ExtServiceReq | obj-GUTIReallocCmd | 
   obj-GUTIReallocCmplt | obj-IdentReq | obj-IdentResp | 
   obj-SecModeCmd | obj-SecModeCmplt | obj-SecModeReject |
   obj-ServiceRequest | obj-ServiceReject | 
   obj-TrkAreaUpdAccept | obj-TrkAreaUpdCmplt |
   obj-TrkAreaUpdReject | obj-TrkAreaUpdRequest | obj-ULNASTransport |
   obj-ULGenNASTransport | obj-DLGenNASTransport |
   obj-ActvDedEPSBearerCtxtAcc | 
   obj-ActvDedEPSBearerCtxtRej | obj-ActvDedEPSBearerCtxtReq |
   obj-ActvDfltEPSBearerCtxtAcc | obj-ActvDfltEPSBearerCtxtRej |
   obj-ActvDfltEPSBearerCtxtReq | obj-BearerResAllocRej |
   obj-BearerResAllocReq | obj-BearerResModRej | obj-BearerResModReq |
   obj-DeactEPSBearerCtxtAcc | obj-DeactEPSBearerCtxtReq | 
   obj-ESMInfoReq | obj-ESMInfoResp | obj-ESMStatus |
   obj-ModEPSBearerCtxtAcc | obj-ModEPSBearerCtxtRej | 
   obj-ModEPSBearerCtxtReq | obj-PDNConnectRej | obj-PDNConnectReq |
   obj-PDNDisconnRej | obj-PDNDisconnReq | obj-CtrlPlaneSvcReq | 
   obj-ESMDataTransport | obj-ServiceAccept | obj-RemoteUEReport
}

PDU ::= SEQUENCE {
   --<cEncSrcFname>TS24301MsgEnc_PDU_secHdr.c</cEncSrcFname>
   --<cDecSrcFname>TS24301MsgDec_PDU_secHdr.c</cDecSrcFname>
   secHdr     SecProtMsgHeader OPTIONAL, 
   l3HdrOpts  L3HdrOptions, -- L3 header, octet 1, bits 5 thru 8
   --<cDecSrcFname>PDU_protoDiscr.c</cDecSrcFname>
   protoDiscr NAS-PROTOCOL-CLASS.&protoDiscr ({TS24301-IE-OBJECTSET}), 
   --<inline/>
   pti CHOICE {
      --<selector element="protoDiscr" value="2"/>
      value INTEGER (0..255), 
      noValue NULL
   }, 
   msgType NAS-PROTOCOL-CLASS.&msgType ({TS24301-IE-OBJECTSET}), 
   data    NAS-PROTOCOL-CLASS.&Value 
              ({TS24301-IE-OBJECTSET}{@protoDiscr,@msgType}),
   --<cEncSrcFname>TS24301MsgEnc_PDU_eom.c</cEncSrcFname>   
   --<cDecSrcFname>TS24301MsgDec_PDU_eom.c</cDecSrcFname>   
   eom NULL       
}


/* This SM object set and PDU are for SM messages that can reside in the MM
    ESMMessageContainer IE... */
TS24301-IE-SM-OBJECTSET NAS-PROTOCOL-CLASS ::= {
   obj-ActvDedEPSBearerCtxtAcc | obj-ActvDedEPSBearerCtxtRej |
   obj-ActvDedEPSBearerCtxtReq | obj-ActvDfltEPSBearerCtxtAcc |
   obj-ActvDfltEPSBearerCtxtRej | obj-ActvDfltEPSBearerCtxtReq |
   obj-BearerResAllocRej | obj-BearerResAllocReq | obj-BearerResModRej |
   obj-BearerResModReq | obj-DeactEPSBearerCtxtAcc |
   obj-DeactEPSBearerCtxtReq | obj-ESMInfoReq | obj-ESMInfoResp |
   obj-ESMStatus | obj-ModEPSBearerCtxtAcc | obj-ModEPSBearerCtxtRej |
   obj-ModEPSBearerCtxtReq | obj-PDNConnectRej | obj-PDNConnectReq |
   obj-PDNDisconnRej | obj-PDNDisconnReq | obj-ESMDataTransport |
   obj-RemoteUEReport
}

PDU-SM ::= SEQUENCE {
   l3HdrOpts  L3HdrOptions, -- L3 header, octet 1, bits 5 thru 8
   --<cDecSrcFname>PDU_protoDiscr.c</cDecSrcFname>
   protoDiscr NAS-PROTOCOL-CLASS.&protoDiscr ({TS24301-IE-SM-OBJECTSET}), 
   --<inline/>
   pti CHOICE {
      --<selector element="protoDiscr" value="2"/>
      value INTEGER (0..255), 
      noValue NULL
   }, 
   msgType NAS-PROTOCOL-CLASS.&msgType ({TS24301-IE-SM-OBJECTSET}), 
   data    NAS-PROTOCOL-CLASS.&Value 
              ({TS24301-IE-SM-OBJECTSET}{@protoDiscr,@msgType})
}


/* 9.9.3.15 - ESM message container

   This is defined here rather than the IES ASN file because of the PDU-SM
   type above.  If this were in the IES file, it caused a circular reference
   issue, which changed some generated types' structs to pointers to those
   structs.  This created a backward compatability issue.  To get around that,
   it is defined here...
*/
ESMMessageContainer ::= SEQUENCE {
   --<is3GLength bitFieldSize="16"/>
   length INTEGER (0..65535),
   pduSm PDU-SM
}


/* 8.2.1 Attach accept */

mt-AttachAccept INTEGER ::= 66

obj-AttachAccept NAS-PROTOCOL-CLASS ::= {
   ID epsMobMgmt, mt-AttachAccept
   TYPE AttachAccept
}

--<is3GMessage/>
AttachAccept ::= SEQUENCE {
   spare INTEGER (0..15) DEFAULT 0, 
   result EPSAttachResult, 
   t3412Value GPRSTimer, 
   taiList TrackingAreaIdentList, 
   esmMessageContainer ESMMessageContainer,
   --<iei format="tlv">50</iei>
   guti EPSMobileIdentity OPTIONAL, 
   --<iei format="tv" length="6">13</iei>
   locAreaIdent LocAreaIdent OPTIONAL,
   --<iei format="tlv">23</iei>
   msIdentity MobileIdentity OPTIONAL,
   --<iei format="tv" length="2">53</iei>
   emmCause EMMCause OPTIONAL, 
   --<iei format="tv" length="2">17</iei>
   t3402 GPRSTimer OPTIONAL, 
   --<iei format="tv" length="2">59</iei>
   t3423 GPRSTimer OPTIONAL, 
   --<iei format="tlv">4A</iei>
   equivPLMNs PLMNList OPTIONAL, 
   --<iei format="tlv">34</iei>
   emergNumList EmergencyNumberList OPTIONAL, 
   --<iei format="tlv">64</iei>
   epsNetFeatSupp EPSNetworkFeatureSupport OPTIONAL, 
   --<iei format="tv" length="1">F</iei>
   addnUpdateResult AddnUpdateResult OPTIONAL,
   ...,
   [[ 10:
   --<iei format="tlv">5E</iei>
   t3412ExtValue GPRSTimer3 OPTIONAL
   ]],
   [[ 12:
   --<iei format="tlv">6A</iei>
   t3324Value GPRSTimer2 OPTIONAL
   ]],
   [[ 13:
   --<iei format="tlv">6E</iei>
   extDRXParams ExtDRXParams OPTIONAL, 
   --<iei format="tlv">65</iei>
   dcnId DcnID OPTIONAL,
   --<iei format="tv" length="1">E</iei>
   smsServicesStatus SMSServicesStatus OPTIONAL
   ]],
   [[ 14:
   --<iei format="tv" length="1">0D</iei>
   non3GPPNetPolicies Non3GPPNetPolicies OPTIONAL,
   --<iei format="tlv">6B</iei>
   t3448Value GPRSTimer2 OPTIONAL,
   --<iei format="tv" length="1">0C</iei>
   networkPolicy NetworkPolicy OPTIONAL
   ]],
   [[ 15:
   --<iei format="tlv">6C</iei>
   t3447Value GPRSTimer3 OPTIONAL,
   --<iei format="tlv-e">7A</iei>
   extEmergencyNumberList ExtEmergencyNumberList OPTIONAL,
   --<iei format="tlv-e">7C</iei>
   cipherKeyData CipherKeyData OPTIONAL
   ]],
   [[ 16:
   --<iei format="tlv">66</iei>
   ueradioCapabilityID UERadioCapId OPTIONAL, -- added in v16.2.0
   --<iei format="tv" length="1">0B</iei>
   ueradioCapIDDeleteInd UERadioCapIdDeletionInd OPTIONAL, -- added in v16.2.0
   --<iei format="tlv">35</iei>
   negotiatedWUSAssistInfo WUSAssistanceInfo OPTIONAL, -- added in v16.7.0
   --<iei format="tlv">36</iei>
   negotiatedDRXParam NBS1DRXParameter OPTIONAL -- added in v16.7.0
   ]]
   -- iei not yet defined in 17.3.0 format="tlv">
   -- negotiatedImsiOffset IMSIOffset OPTIONAL
}

/* 8.2.2 Attach complete */

mt-AttachComplete INTEGER ::= 67

obj-AttachComplete NAS-PROTOCOL-CLASS ::= {
   ID epsMobMgmt, mt-AttachComplete
   TYPE AttachComplete
}

AttachComplete ::= ESMMessageContainer

/* 8.2.3 Attach reject */

mt-AttachReject INTEGER ::= 68

obj-AttachReject NAS-PROTOCOL-CLASS ::= {
   ID epsMobMgmt, mt-AttachReject
   TYPE AttachReject
}

--<is3GMessage/>
AttachReject ::= SEQUENCE {
   emmCause EMMCause, 
   --<iei format="tlv-e">78</iei>
   esmMsgCont ESMMessageContainer OPTIONAL, 
   ...,
   [[ 10:
   --<iei format="tlv">5F</iei>
   t3346Value GPRSTimer2 OPTIONAL, 
   --<iei format="tlv">16</iei>
   t3402Value GPRSTimer2 OPTIONAL
   ]],
   [[ 12:
   --<iei format="tv" length="1">A</iei>
   extEMMCause ExtEMMCause OPTIONAL
   ]]
}
   
/* 8.2.4 Attach request */

mt-AttachRequest INTEGER ::= 65

obj-AttachRequest NAS-PROTOCOL-CLASS ::= {
   ID epsMobMgmt, mt-AttachRequest
   TYPE AttachRequest
}

--<is3GMessage/>
AttachRequest ::= SEQUENCE {
   nasKeySetIdentifier NASKeySetIdentifier,
   epsAttachType EPSAttachType,
   oldGUTIOrIMSI EPSMobileIdentity,
   ueNetworkCapability UENetworkCapability,
   esmMessageContainer ESMMessageContainer,
   --<iei format="tv" length="4">19</iei>
   oldP-TMSISignature P-TMSISignature OPTIONAL,
   --<iei format="tlv">50</iei>
   additionalGUTI EPSMobileIdentity OPTIONAL,
   --<iei format="tv" length="6">52</iei>
   lastVisitedRegisteredTAI TrackingAreaIdent OPTIONAL,
   --<iei format="tv" length="3">5C</iei>
   drxParameter DRXParameter OPTIONAL,
   --<iei format="tlv">31</iei>
   msNetworkCapability MSNetworkCapability OPTIONAL,
   --<iei format="tv" length="6">13</iei>
   oldLocAreaIdent LocAreaIdent OPTIONAL,
   --<iei format="tv" length="1">9</iei>
   tmsiStatus TMSIStatus OPTIONAL,
   --<iei format="tlv">11</iei>
   mobileStationClassmark2 MobileStationClassmark2 OPTIONAL,
   --<iei format="tlv">20</iei>
   mobileStationClassmark3 MobileStationClassmark3 OPTIONAL,
   --<iei format="tlv">40</iei>
   supportedCodecs SupportedCodecList OPTIONAL,
   --<iei format="tv" length="1">F</iei>
   addnUpdateType AddnUpdateType OPTIONAL, 
   ...,
   [[ 9:
   --<iei format="tlv">5D</iei>
   voiceDomainPref VoiceDomainPref OPTIONAL
   ]], 
   [[ 10:
   --<iei format="tv" length="1">D</iei>
   deviceProperties DeviceProperties OPTIONAL, 
   --<iei format="tv" length="1">E</iei>
   oldGUTIType GUTIType OPTIONAL, 
   --<iei format="tv" length="1">C</iei>
   msNetFeatureSupport MSNetFeatureSupport OPTIONAL
   ]],
   [[ 11:
   --<iei format="tlv">10</iei>
   tmsiBasedNRIContainer NetResourceIdentContainer OPTIONAL
   ]],
   [[ 12:
   --<iei format="tlv">6A</iei>
   t3324Value GPRSTimer2 OPTIONAL,
   --<iei format="tlv">5E</iei>
   t3412ExtValue GPRSTimer3 OPTIONAL
   ]],
   [[ 13:
   --<iei format="tlv">6E</iei>
   extDRXParams ExtDRXParams OPTIONAL
   ]],
   [[ 15:
   --<iei format="tlv">6F</iei>
   addlSecurityCapability UEAddlSecurityCapability OPTIONAL,
   --<iei format="tlv">6D</iei>
   ueStatus UEStatus OPTIONAL,
   --<iei format="tv" length="2">17</iei>
   addlInfoReq AdditionalInfoReq OPTIONAL
   ]],
   [[ 16:
   --<iei format="tlv">32</iei>
   n1UENetworkCapability N1UENetCapability OPTIONAL, -- added in v16.1.1
   --<iei format="tlv">34</iei>
   ueRadioCapIdAvail UERadioCapIdAvailability OPTIONAL, -- added in v16.7.0
   --<iei format="tlv">35</iei>
   requestedWUSAssistInfo WUSAssistanceInfo OPTIONAL, -- added in v16.7.0
   --<iei format="tlv">36</iei>
   nbs1DRXParam NBS1DRXParameter OPTIONAL -- added in v16.7.0
   ]]
   -- iei not yet defined in 17.3.0 format="tlv">
   -- requestedImsiOffset IMSIOffset OPTIONAL
}

/* 8.2.5 Authentication failure */

mt-AuthFailure INTEGER ::= 92

obj-AuthFailure NAS-PROTOCOL-CLASS ::= {
   ID epsMobMgmt, mt-AuthFailure
   TYPE AuthFailure
}

--<is3GMessage/>
AuthFailure ::= SEQUENCE {
   emmCause EMMCause, 
   --<iei format="tlv">30</iei>
   authFailureParam AuthFailureParam OPTIONAL
}

/* 8.2.6 Authentication reject */

mt-AuthReject INTEGER ::= 84

obj-AuthReject NAS-PROTOCOL-CLASS ::= {
   ID epsMobMgmt, mt-AuthReject
   TYPE NULL
}

/* 8.2.7 Authentication request */

mt-AuthRequest INTEGER ::= 82

obj-AuthRequest NAS-PROTOCOL-CLASS ::= {
   ID epsMobMgmt, mt-AuthRequest
   TYPE AuthRequest
}

--<is3GMessage/>
AuthRequest ::= SEQUENCE {
   spare INTEGER (0..15) DEFAULT 0, 
   nasKeySetIdent NASKeySetIdentifier, 
   authParamRAND AuthParamRAND, 
   authParamAUTN AuthParamAUTN
}
   
/* 8.2.8 Authentication response */

mt-AuthResponse INTEGER ::= 83

obj-AuthResponse NAS-PROTOCOL-CLASS ::= {
   ID epsMobMgmt, mt-AuthResponse
   TYPE AuthResponse
}

AuthResponse ::= AuthRespParam

/* 8.2.9 CS Service notification */

mt-CSServiceNotif INTEGER ::= 100

obj-CSServiceNotif NAS-PROTOCOL-CLASS ::= {
   ID epsMobMgmt, mt-CSServiceNotif
   TYPE CSServiceNotif
}

--<is3GMessage/>
CSServiceNotif ::= SEQUENCE {
   pagingIdentity PagingIdentity, 
   --<iei format="tlv">60</iei>
   cli CLI OPTIONAL,
   --<iei format="tv" length="2">61</iei>
   ssCode SSCode OPTIONAL,
   --<iei format="tv" length="2">62</iei>
   lcsIndicator LCSIndicator OPTIONAL,
   --<iei format="tlv">63</iei>
   lcsClientIdentity LCSClientIdentity OPTIONAL
}

/* 8.2.10 Detach accept */

mt-DetachAccept INTEGER ::= 70

obj-DetachAccept NAS-PROTOCOL-CLASS ::= {
   ID epsMobMgmt, mt-DetachAccept
   TYPE NULL
}

/* 8.2.11 Detach request */

mt-DetachRequest INTEGER ::= 69

obj-DetachRequest NAS-PROTOCOL-CLASS ::= {
   ID epsMobMgmt, mt-DetachRequest
   TYPE DetachRequest
}

--<cEncFuncFname>TS24301MsgEnc_DetachRequest.c</cEncFuncFname>
--<cDecFuncFname>TS24301MsgDec_DetachRequest.c</cDecFuncFname>
DetachRequest ::= CHOICE {
   ueOrig DetachRequestUEOrig, 
   ueTerm DetachRequestUETerm
}

DetachRequestUEOrig ::= SEQUENCE {
   nasKeySetIdent NASKeySetIdentifier, 
   detachType DetachType, 
   gUTIOrIMSI EPSMobileIdentity
}

--<is3GMessage/>
DetachRequestUETerm ::= SEQUENCE {
   spare INTEGER (0..15) DEFAULT 0, 
   detachType DetachType, 
   --<iei format="tv" length="2">53</iei>
   emmCause EMMCause OPTIONAL
}

/* 8.2.12 Downlink NAS transport */

mt-DLNASTransport INTEGER ::= 98

obj-DLNASTransport NAS-PROTOCOL-CLASS ::= {
   ID epsMobMgmt, mt-DLNASTransport
   TYPE DLNASTransport
}

DLNASTransport ::= NASMessageContainer

/* 8.2.13 EMM information */

mt-EMMInformation INTEGER ::= 97

obj-EMMInformation NAS-PROTOCOL-CLASS ::= {
   ID epsMobMgmt, mt-EMMInformation
   TYPE EMMInformation
}

--<is3GMessage/>
EMMInformation ::= SEQUENCE {
   --<iei format="tlv">43</iei>
   fullNameForNetwork NetworkName OPTIONAL,
   --<iei format="tlv">45</iei>
   shortNameForNetwork NetworkName OPTIONAL,
   --<iei format="tv" length="2">46</iei>
   localTimeZone TimeZone OPTIONAL,
   --<iei format="tv" length="8">47</iei>
   univTimeAndLclTimeZone TimeZoneAndTime OPTIONAL,
   --<iei format="tlv">49</iei>
   networkDaylightSavingTime DaylightSavingTime OPTIONAL
}

/* 8.2.14 EMM status */

mt-EMMStatus INTEGER ::= 96

obj-EMMStatus NAS-PROTOCOL-CLASS ::= {
   ID epsMobMgmt, mt-EMMStatus
   TYPE EMMStatus
}

EMMStatus ::= EMMCause

/* 8.2.15 Extended service request */

mt-ExtServiceReq INTEGER ::= 76

obj-ExtServiceReq NAS-PROTOCOL-CLASS ::= {
   ID epsMobMgmt, mt-ExtServiceReq
   TYPE ExtServiceReq
}

--<is3GMessage/>
ExtServiceReq ::= SEQUENCE {
   nasKeySetIdentifier NASKeySetIdentifier,
   serviceType ServiceType,
   m-tmsi MobileIdentity,
   --<iei format="tv" length="1">B</iei>
   csfbResponse CSFBResponse OPTIONAL,
   ...,
   [[ 9:
   --<iei format="tlv">57</iei>
   epsBearerContextStatus EPSBearerContextStatus OPTIONAL
   ]],
   [[ 10:
   --<iei format="tv" length="1">D</iei>
   deviceProperties DeviceProperties OPTIONAL
   ]]
   -- iei not yet defined in 17.3.0 format="tlv">
   -- ueRequestType UERequestType OPTIONAL
   -- iei not yet defined in 17.3.0 format="tlv">
   -- pagingRestriction PagingRestriction OPTIONAL
}

/* 8.2.16 GUTI reallocation command */

mt-GUTIReallocCmd INTEGER ::= 80

obj-GUTIReallocCmd NAS-PROTOCOL-CLASS ::= {
   ID epsMobMgmt, mt-GUTIReallocCmd
   TYPE GUTIReallocCmd
}

--<is3GMessage/>
GUTIReallocCmd ::= SEQUENCE {
   guti EPSMobileIdentity, 
   --<iei format="tlv">54</iei>
   taiList TrackingAreaIdentList OPTIONAL,
   ...,
   [[ 14:
   --<iei format="tlv">65</iei>
   dcnId DcnID OPTIONAL
   ]],
   [[ 16:
   --<iei format="tlv">66</iei>
   ueRadioCapId UERadioCapId OPTIONAL,  -- added in v16.4.0
   --<iei format="tv" length="1">0B</iei>
   ueRadioCapIdDelInd UERadioCapIdDeletionInd OPTIONAL -- added in v16.4.0
   ]]
}

/* 8.2.17 GUTI reallocation complete */

mt-GUTIReallocCmplt INTEGER ::= 81

obj-GUTIReallocCmplt NAS-PROTOCOL-CLASS ::= {
   ID epsMobMgmt, mt-GUTIReallocCmplt
   TYPE NULL
}

/* 8.2.18  Identity request */

mt-IdentReq INTEGER ::= 85

obj-IdentReq NAS-PROTOCOL-CLASS ::= {
   ID epsMobMgmt, mt-IdentReq
   TYPE IdentReq
}

--<is3GMessage/>
IdentReq ::= SEQUENCE {
   spare INTEGER (0..15) DEFAULT 0, 
   identType IdentityType2Value
}

/* 8.2.19 Identity response */

mt-IdentResp INTEGER ::= 86

obj-IdentResp NAS-PROTOCOL-CLASS ::= {
   ID epsMobMgmt, mt-IdentResp
   TYPE IdentResp
}

IdentResp ::= MobileIdentity

/* 8.2.20 Security mode command */

mt-SecModeCmd INTEGER ::= 93

obj-SecModeCmd NAS-PROTOCOL-CLASS ::= {
   ID epsMobMgmt, mt-SecModeCmd
   TYPE SecModeCmd
}

--<is3GMessage/>
SecModeCmd ::= SEQUENCE {
   selNASSecurityAlgs NASSecurityAlgorithms,
   spare INTEGER (0..15) DEFAULT 0, 
   nasKeySetIdentifier NASKeySetIdentifier,
   replayedUESecurityCapabilities UESecurityCapability,
   --<iei format="tv" length="1">C</iei>
   imeisvRequest IMEISVRequest OPTIONAL,
   --<iei format="tv" length="5">55</iei>
   replayedNonce Nonce OPTIONAL,
   --<iei format="tv" length="5">56</iei>
   nonce Nonce OPTIONAL,
   ...,
   [[ 14:
   --<iei format="tlv">4F</iei>
   hashMME HashMME OPTIONAL
   ]],
   [[ 15:
   --<iei format="tlv">6F</iei>
   addlSecurityCapability UEAddlSecurityCapability OPTIONAL
   ]],
   [[ 16:
   --<iei format="tlv">37</iei>
   ueRadioCapabilityIdRequest UERadioCapIdRequest OPTIONAL -- added in v16.2.0, format modified in 16.8.0
   ]]
}

/* 8.2.21 Security mode complete */

mt-SecModeCmplt INTEGER ::= 94

obj-SecModeCmplt NAS-PROTOCOL-CLASS ::= {
   ID epsMobMgmt, mt-SecModeCmplt
   TYPE SecModeCmplt
}

--<is3GMessage/>
SecModeCmplt ::= SEQUENCE {
   --<iei format="tlv">23</iei>
   imeisv MobileIdentity OPTIONAL,
   ...,
   [[ 14:
   --<iei format="tlv-e">79</iei>
   replayedNASMsgContainer ReplayedNASMsgContainer OPTIONAL
   ]],
   [[ 16:
   --<iei format="tlv">66</iei>
   ueradioCapabilityID UERadioCapId OPTIONAL -- added in v16.2.0
   ]]
}

/* 8.2.22 Security mode reject */

mt-SecModeReject INTEGER ::= 95

obj-SecModeReject NAS-PROTOCOL-CLASS ::= {
   ID epsMobMgmt, mt-SecModeReject
   TYPE SecModeReject
}

SecModeReject ::= EMMCause

/* 8.2.24 Service reject */

mt-ServiceReject INTEGER ::= 78

obj-ServiceReject NAS-PROTOCOL-CLASS ::= {
   ID epsMobMgmt, mt-ServiceReject
   TYPE ServiceReject
}

--<is3GMessage/>
ServiceReject ::= SEQUENCE {
   emmCause EMMCause, 
   --<iei format="tv" length="2">5B</iei>
   t3442Value GPRSTimer OPTIONAL, 
   ...,
   [[ 10:
   --<iei format="tlv">5F</iei>
   t3346Value GPRSTimer2 OPTIONAL
   ]],
   [[ 14:
   --<iei format="tlv">6B</iei>
   t3448Value GPRSTimer2 OPTIONAL
   ]]
}

/* 8.2.25 Service request */
/* This message is sent by the UE to the network to request the         */
/* establishment of a NAS signalling connection and of the radio and S1 */
/* bearers. Its structure does not follow the structure of a standard   */
/* layer 3 message. See table 8.2.25.1.                                 */

mt-ServiceRequest INTEGER ::= 0

obj-ServiceRequest NAS-PROTOCOL-CLASS ::= {
   ID epsMobMgmt, mt-ServiceRequest
   TYPE ServiceRequest
}

ServiceRequest ::= SEQUENCE {
   secHdr       INTEGER (0..15), 
   protoDiscr   ProtoDiscr, 
   ksiAndSequenceNumber KSIAndSequenceNumber, 
   shortMAC ShortMAC 
}

/* 8.2.26 Tracking area update accept */

mt-TrkAreaUpdAccept INTEGER ::= 73

obj-TrkAreaUpdAccept NAS-PROTOCOL-CLASS ::= {
   ID epsMobMgmt, mt-TrkAreaUpdAccept
   TYPE TrkAreaUpdAccept
}

--<is3GMessage/>
TrkAreaUpdAccept ::= SEQUENCE {
   spare INTEGER (0..15) DEFAULT 0, 
   epsUpdateResult EPSUpdateResult,
   --<iei format="tv" length="2">5A</iei>
   t3412Value GPRSTimer OPTIONAL,
   --<iei format="tlv">50</iei>
   guti EPSMobileIdentity OPTIONAL,
   --<iei format="tlv">54</iei>
   taiList TrackingAreaIdentList OPTIONAL,
   --<iei format="tlv">57</iei>
   epsBearerContextStatus EPSBearerContextStatus OPTIONAL,
   --<iei format="tv" length="6">13</iei>
   locAreaIdent LocAreaIdent OPTIONAL,
   --<iei format="tlv">23</iei>
   msIdentity MobileIdentity OPTIONAL,
   --<iei format="tv" length="2">53</iei>
   emmCause EMMCause OPTIONAL,
   --<iei format="tv" length="2">17</iei>
   t3402Value GPRSTimer OPTIONAL,
   --<iei format="tv" length="2">59</iei>
   t3423Value GPRSTimer OPTIONAL,
   --<iei format="tlv">4A</iei>
   equivalentPLMNs PLMNList OPTIONAL,
   --<iei format="tlv">34</iei>
   emergencyNumberList EmergencyNumberList OPTIONAL,
   --<iei format="tlv">64</iei>
   epsNetworkFeatureSupport EPSNetworkFeatureSupport OPTIONAL,
   --<iei format="tv" length="1">F</iei>
   addnUpdateResult AddnUpdateResult OPTIONAL,
   ...,
   [[ 10:
   --<iei format="tlv">5E</iei>
   t3412ExtValue GPRSTimer3 OPTIONAL
   ]],
   [[ 12:
   --<iei format="tlv">6A</iei>
   t3324Value GPRSTimer2 OPTIONAL
   ]],
   [[ 13:
   --<iei format="tlv">6E</iei>
   extDRXParams ExtDRXParams OPTIONAL,
   --<iei format="tlv">68</iei>
   hdrCompressConfigStat HdrCompressConfigStat OPTIONAL, 
   --<iei format="tlv">65</iei>
   dcnId DcnID OPTIONAL,
   --<iei format="tv" length="1">E</iei>
   smsServicesStatus SMSServicesStatus OPTIONAL
   ]],
   [[ 14:
   --<iei format="tv" length="1">0D</iei>
   non3GPPNetPolicies Non3GPPNetPolicies OPTIONAL,
   --<iei format="tlv">6B</iei>
   t3448Value GPRSTimer2 OPTIONAL,
   --<iei format="tv" length="1">0C</iei>
   networkPolicy NetworkPolicy OPTIONAL
   ]],
   [[ 15:
   --<iei format="tlv">6C</iei>
   t3447Value GPRSTimer3 OPTIONAL,
   --<iei format="tlv-e">7A</iei>
   extEmergencyNumberList ExtEmergencyNumberList OPTIONAL,
   --<iei format="tlv-e">7C</iei>
   cipherKeyData CipherKeyData OPTIONAL
   ]],
   [[ 16:
   --<iei format="tlv">66</iei>
   ueRadioCapabilityId UERadioCapId OPTIONAL, -- added in 16.2.0
   --<iei format="tv" length="1">0B</iei>
   ueRadioCapIdDeleteInd UERadioCapIdDeletionInd OPTIONAL, -- added in 16.2.0
   --<iei format="tlv">35</iei>
   negotiatedWUSAssistInfo WUSAssistanceInfo OPTIONAL, -- added in v16.7.0
   --<iei format="tlv">36</iei>
   negotiatedDRXParam NBS1DRXParameter OPTIONAL -- added in v16.7.0
   ]]
   -- iei not yet defined in 17.3.0 format="tlv">
   -- negotiatedImsiOffset IMSIOffset OPTIONAL
}

/* 8.2.27 Tracking area update complete */

mt-TrkAreaUpdCmplt INTEGER ::= 74

obj-TrkAreaUpdCmplt NAS-PROTOCOL-CLASS ::= {
   ID epsMobMgmt, mt-TrkAreaUpdCmplt
   TYPE NULL
}

/* 8.2.28 Tracking area update reject */

mt-TrkAreaUpdReject INTEGER ::= 75

obj-TrkAreaUpdReject NAS-PROTOCOL-CLASS ::= {
   ID epsMobMgmt, mt-TrkAreaUpdReject
   TYPE TrkAreaUpdReject
}

--<is3GMessage/>
TrkAreaUpdReject ::= SEQUENCE {
   cause EMMCause, 
   ...,
   [[ 10:
   --<iei format="tlv">5F</iei>
   t3346Value GPRSTimer2 OPTIONAL
   ]],
   [[ 12:
   --<iei format="tv" length="1">A</iei>
   extEMMCause ExtEMMCause OPTIONAL
   ]]
}

/* 8.2.29 Tracking area update request */

mt-TrkAreaUpdRequest INTEGER ::= 72

obj-TrkAreaUpdRequest NAS-PROTOCOL-CLASS ::= {
   ID epsMobMgmt, mt-TrkAreaUpdRequest
   TYPE TrkAreaUpdRequest
}

--<is3GMessage/>
TrkAreaUpdRequest ::= SEQUENCE {
   nasKeySetIdentifier NASKeySetIdentifier,
   epsUpdateType EPSUpdateType,
   oldGUTI EPSMobileIdentity,
   --<iei format="tv" length="1">B</iei>
   nonCurrNativeNASKeySetIdent NASKeySetIdentifier OPTIONAL,
   --<iei format="tv" length="1">8</iei>
   gprsCiphKeySeqNum CiphKeySeqNum OPTIONAL,
   --<iei format="tv" length="4">19</iei>
   oldP-TMSISignature P-TMSISignature OPTIONAL,
   --<iei format="tlv">50</iei>
   additionalGUTI EPSMobileIdentity OPTIONAL,
   --<iei format="tv" length="5">55</iei>
   nonce Nonce OPTIONAL,
   --<iei format="tlv">58</iei>
   ueNetworkCapability UENetworkCapability OPTIONAL,
   --<iei format="tv" length="6">52</iei>
   lastVisitedRegisteredTAI TrackingAreaIdent OPTIONAL,
   --<iei format="tv" length="3">5C</iei>
   drxParameter DRXParameter OPTIONAL,
   --<iei format="tv" length="1">A</iei>
   ueRadioCapInfoUpdateNeeded UERadioCapInfoUpdateNeeded OPTIONAL,
   --<iei format="tlv">57</iei>
   epsBearerContextStatus EPSBearerContextStatus OPTIONAL,
   --<iei format="tlv">31</iei>
   msNetworkCapability MSNetworkCapability OPTIONAL,
   --<iei format="tv" length="6">13</iei>
   oldLocAreaIdent LocAreaIdent OPTIONAL,
   --<iei format="tv" length="1">9</iei>
   tmsiStatus TMSIStatus OPTIONAL,
   --<iei format="tlv">11</iei>
   mobileStationClassmark2 MobileStationClassmark2 OPTIONAL,
   --<iei format="tlv">20</iei>
   mobileStationClassmark3 MobileStationClassmark3 OPTIONAL,
   --<iei format="tlv">40</iei>
   supportedCodecs SupportedCodecList OPTIONAL,
   --<iei format="tv" length="1">F</iei>
   addnUpdateType AddnUpdateType OPTIONAL, 
   ...,
   [[ 9:
   --<iei format="tlv">5D</iei>
   voiceDomainPref VoiceDomainPref OPTIONAL
   ]], 
   [[ 10:
   --<iei format="tv" length="1">E</iei>
   oldGUTIType GUTIType OPTIONAL, 
   --<iei format="tv" length="1">D</iei>
   deviceProperties DeviceProperties OPTIONAL, 
   --<iei format="tv" length="1">C</iei>
   msNetFeatureSupport MSNetFeatureSupport OPTIONAL
   ]],
   [[ 11:
   --<iei format="tlv">10</iei>
   tmsiBasedNRIContainer NetResourceIdentContainer OPTIONAL
   ]],
   [[ 12:
   --<iei format="tlv">6A</iei>
   t3324Value GPRSTimer2 OPTIONAL,
   --<iei format="tlv">5E</iei>
   t3412ExtValue GPRSTimer3 OPTIONAL
   ]],
   [[ 13:
   --<iei format="tlv">6E</iei>
   extDRXParams ExtDRXParams OPTIONAL
   ]],
   [[ 15:
   --<iei format="tlv">6F</iei>
   addlSecurityCapability UEAddlSecurityCapability OPTIONAL,
   --<iei format="tlv">6D</iei>
   ueStatus UEStatus OPTIONAL,
   --<iei format="tv" length="2">17</iei>
   addlInfoReq AdditionalInfoReq OPTIONAL
   ]],
   [[ 16:
   --<iei format="tlv">32</iei>
   n1UENetworkCapability N1UENetCapability OPTIONAL, -- added in v16.1.1
   --<iei format="tlv">34</iei>
   ueRadioCapIdAvail UERadioCapIdAvailability OPTIONAL, -- added in v16.7.0
   --<iei format="tlv">35</iei>
   requestedWUSAssistInfo WUSAssistanceInfo OPTIONAL, -- added in v16.7.0
   --<iei format="tlv">36</iei>
   nbs1DRXParam NBS1DRXParameter OPTIONAL -- added in v16.7.0
   ]]
   -- iei not yet defined in 17.3.0 format="tlv">
   -- requestedImsiOffset IMSIOffset OPTIONAL
   -- iei not yet defined in 17.3.0 format="tlv">
   -- ueRequestType UERequestType OPTIONAL
   -- iei not yet defined in 17.3.0 format="tlv">
   -- pagingRestriction PagingRestriction OPTIONAL
}

/* 8.2.30 Uplink NAS transport */

mt-ULNASTransport INTEGER ::= 99

obj-ULNASTransport NAS-PROTOCOL-CLASS ::= {
   ID epsMobMgmt, mt-ULNASTransport
   TYPE ULNASTransport
}

ULNASTransport ::= NASMessageContainer

/* 8.2.31 Downlink generic NAS transport */

mt-DLGenNASTransport INTEGER ::= 104

obj-DLGenNASTransport NAS-PROTOCOL-CLASS ::= {
   ID epsMobMgmt, mt-DLGenNASTransport
   TYPE DLGenNASTransport
}

DLGenNASTransport ::= GenNASTransport

--<is3GMessage/>
GenNASTransport ::= SEQUENCE {
   genMsgContainerType GenMsgContainerType, 
   genMsgContainer GenMessageContainer, 
   --<iei format="tlv">65</iei>
   addnInfo OCTET STRING (SIZE (0..253)) OPTIONAL
}

/* 8.2.32 Uplink generic NAS transport */

mt-ULGenNASTransport INTEGER ::= 105

obj-ULGenNASTransport NAS-PROTOCOL-CLASS ::= {
   ID epsMobMgmt, mt-ULGenNASTransport
   TYPE ULGenNASTransport
}

ULGenNASTransport ::= GenNASTransport

/* 8.2.33 CONTROL PLANE SERVICE REQUEST */

mt-CtrlPlaneSvcReq INTEGER ::= 77

obj-CtrlPlaneSvcReq NAS-PROTOCOL-CLASS ::= {
   ID epsMobMgmt, mt-CtrlPlaneSvcReq
   TYPE CtrlPlaneSvcReq
}

--<is3GMessage/>
CtrlPlaneSvcReq ::= SEQUENCE {
   nasKeySetId NASKeySetIdentifier,
   ctrlPlaneSvcType CtrlPlaneSvcType, 
   --<iei format="tlv-e">78</iei>
   esmMsgCont ESMMessageContainer OPTIONAL, 
   --<iei format="tlv">67</iei>
   nasMsgCont NASMessageContainer OPTIONAL, 
   --<iei format="tlv">57</iei>
   epsBearerContextStatus EPSBearerContextStatus OPTIONAL, 
   --<iei format="tv" length="1">D</iei>
   deviceProperties DeviceProperties OPTIONAL
   -- iei not yet defined in 17.3.0 format="tlv">
   -- ueRequestType UERequestType OPTIONAL
   -- iei not yet defined in 17.3.0 format="tlv">
   -- pagingRestriction PagingRestriction OPTIONAL
}
   
/* 8.2.34 Service Accept */

mt-ServiceAccept INTEGER ::= 79

obj-ServiceAccept NAS-PROTOCOL-CLASS ::= {
   ID epsMobMgmt, mt-ServiceAccept
   TYPE ServiceAccept
}

--<is3GMessage/>
ServiceAccept ::= SEQUENCE {
   --<iei format="tlv">57</iei>
   epsBearerContextStatus EPSBearerContextStatus OPTIONAL, 
   --<iei format="tlv">6B</iei>
   t3448Value GPRSTimer2 OPTIONAL
}


/* 8.3 EPS session management messages */

/* 8.3.1 Activate dedicated EPS bearer context accept */

mt-ActvDedEPSBearerCtxtAcc INTEGER ::= 198

obj-ActvDedEPSBearerCtxtAcc NAS-PROTOCOL-CLASS ::= {
   ID epsSessMgmt, mt-ActvDedEPSBearerCtxtAcc
   TYPE ActvDedEPSBearerCtxtAcc
}

--<is3GMessage/>
ActvDedEPSBearerCtxtAcc ::= SEQUENCE {
   --<iei format="tlv">27</iei>
   protocolConfigOptions ProtocolConfigOptions OPTIONAL, 
   ...,
   [[ 13:
   --<iei format="tlv">33</iei>
   nbifomContainer NBIFOMContainer OPTIONAL, 
   --<iei format="tlv-e">7B</iei>
   extProtoConfigOpts ExtProtoConfigOptions OPTIONAL
   ]]
}

/* 8.3.2 Activate dedicated EPS bearer context reject */

mt-ActvDedEPSBearerCtxtRej INTEGER ::= 199

obj-ActvDedEPSBearerCtxtRej NAS-PROTOCOL-CLASS ::= {
   ID epsSessMgmt, mt-ActvDedEPSBearerCtxtRej
   TYPE ActvDedEPSBearerCtxtRej
}

--<is3GMessage/>
ActvDedEPSBearerCtxtRej ::= SEQUENCE {
   esmCause ESMCause, 
   --<iei format="tlv">27</iei>
   protocolConfigOptions ProtocolConfigOptions OPTIONAL,
   ...,
   [[ 14:
   --<iei format="tlv">33</iei>
   nbifomContainer NBIFOMContainer OPTIONAL, 
   --<iei format="tlv-e">7B</iei>
   extProtoConfigOpts ExtProtoConfigOptions OPTIONAL
   ]]
}

/* 8.3.3 Activate dedicated EPS bearer context request */

mt-ActvDedEPSBearerCtxtReq INTEGER ::= 197

obj-ActvDedEPSBearerCtxtReq NAS-PROTOCOL-CLASS ::= {
   ID epsSessMgmt, mt-ActvDedEPSBearerCtxtReq
   TYPE ActvDedEPSBearerCtxtReq
}

--<is3GMessage/>
ActvDedEPSBearerCtxtReq ::= SEQUENCE {
   spare INTEGER (0..15) DEFAULT 0, 
   linkedEPSBearerIdent LinkedEPSBearerIdent,
   epsQoS EPSQualityOfService, 
   tft TFT,
   --<iei format="tlv">5D</iei>
   transIdent LinkedTI OPTIONAL,
   --<iei format="tlv">30</iei>
   negotiatedQoS QualityOfService OPTIONAL,
   --<iei format="tv" length="2">32</iei>
   negotiatedLLCSAPI LLCSAPIValue OPTIONAL,
   --<iei format="tv" length="1">8</iei>
   radioPriority RadioPriority OPTIONAL,
   --<iei format="tlv">34</iei>
   packetFlowIdentifier PacketFlowIdentValue OPTIONAL,
   --<iei format="tlv">27</iei>
   protocolConfigOptions ProtocolConfigOptions OPTIONAL,
   ...,
   [[ 12:
   --<iei format="tv" length="1">C</iei>
   wlanOffloadInd WLANOffloadAccept OPTIONAL
   ]],
   [[ 13:
   --<iei format="tlv">33</iei>
   nbifomContainer NBIFOMContainer OPTIONAL, 
   --<iei format="tlv-e">7B</iei>
   extProtoConfigOpts ExtProtoConfigOptions OPTIONAL
   ]],
   [[ 15:
   --<iei format="tlv">5C</iei>
   extQOS ExtQualityOfService OPTIONAL
   ]]
}

/* 8.3.4 Activate default EPS bearer context accept */

mt-ActvDfltEPSBearerCtxtAcc INTEGER ::= 194

obj-ActvDfltEPSBearerCtxtAcc NAS-PROTOCOL-CLASS ::= {
   ID epsSessMgmt, mt-ActvDfltEPSBearerCtxtAcc
   TYPE ActvDfltEPSBearerCtxtAcc
}

--<is3GMessage/>
ActvDfltEPSBearerCtxtAcc ::= SEQUENCE {
   --<iei format="tlv">27</iei>
   protocolConfigOptions ProtocolConfigOptions OPTIONAL,
   ...,
   [[ 13:
   --<iei format="tlv-e">7B</iei>
   extProtoConfigOpts ExtProtoConfigOptions OPTIONAL
   ]]
}

/* 8.3.5 Activate default EPS bearer context reject */

mt-ActvDfltEPSBearerCtxtRej INTEGER ::= 195

obj-ActvDfltEPSBearerCtxtRej NAS-PROTOCOL-CLASS ::= {
   ID epsSessMgmt, mt-ActvDfltEPSBearerCtxtRej
   TYPE ActvDfltEPSBearerCtxtRej
}

--<is3GMessage/>
ActvDfltEPSBearerCtxtRej ::= SEQUENCE {
   esmCause ESMCause, 
   --<iei format="tlv">27</iei>
   protocolConfigOptions ProtocolConfigOptions OPTIONAL,
   ...,
   [[ 13:
   --<iei format="tlv-e">7B</iei>
   extProtoConfigOpts ExtProtoConfigOptions OPTIONAL
   ]]
}

/* 8.3.6 Activate default EPS bearer context request */

mt-ActvDfltEPSBearerCtxtReq INTEGER ::= 193

obj-ActvDfltEPSBearerCtxtReq NAS-PROTOCOL-CLASS ::= {
   ID epsSessMgmt, mt-ActvDfltEPSBearerCtxtReq
   TYPE ActvDfltEPSBearerCtxtReq
}

--<is3GMessage/>
ActvDfltEPSBearerCtxtReq ::= SEQUENCE {
   epsQoS EPSQualityOfService, 
   accessPointName AccessPointName, 
   pdnAddress PDNAddress, 
   --<iei format="tlv">5D</iei>
   transIdent LinkedTI OPTIONAL,
   --<iei format="tlv">30</iei>
   negotiatedQoS QualityOfService OPTIONAL,
   --<iei format="tv" length="2">32</iei>
   negotiatedLLCSAPI LLCSAPIValue OPTIONAL,
   --<iei format="tv" length="1">8</iei>
   radioPriority RadioPriority OPTIONAL,
   --<iei format="tlv">34</iei>
   packetFlowIdentifier PacketFlowIdentValue OPTIONAL,
   --<iei format="tlv">5E</iei>
   apn-AMBR APNAggMaxBitRate OPTIONAL, 
   --<iei format="tv" length="2">58</iei>
   esmCause ESMCause OPTIONAL, 
   --<iei format="tlv">27</iei>
   protocolConfigOptions ProtocolConfigOptions OPTIONAL,
   ...,
   [[ 10:
   --<iei format="tv" length="1">B</iei>
   connectivityType ConnectivityType OPTIONAL
   ]], 
   [[ 12:
   --<iei format="tv" length="1">C</iei>
   wlanOffloadInd WLANOffloadAccept OPTIONAL
   ]],
   [[ 13:
   --<iei format="tlv">33</iei>
   nbifomContainer NBIFOMContainer OPTIONAL, 
   --<iei format="tlv">66</iei>
   hdrCompressConfigStat HdrCompressConfigStat OPTIONAL,
   --<iei format="tv" length="1">9</iei>
   ctrlPlaneOnlyInd CtrlPlaneOnlyInd OPTIONAL, 
   --<iei format="tlv-e">7B</iei>
   extProtoConfigOpts ExtProtoConfigOptions OPTIONAL,
   --<iei format="tlv">6E</iei>
   servPLMNRateCtrl ServPLMNRateCtrl OPTIONAL
   ]],
   [[ 15:
   --<iei format="tlv">5F</iei>
   extAPNAggMaxBitRate ExtAPNAggMaxBitRate OPTIONAL
   ]]
}

/* 8.3.7 Bearer resource allocation reject */

mt-BearerResAllocRej INTEGER ::= 213

obj-BearerResAllocRej NAS-PROTOCOL-CLASS ::= {
   ID epsSessMgmt, mt-BearerResAllocRej
   TYPE BearerResAllocRej
}

--<is3GMessage/>
BearerResAllocRej ::= SEQUENCE {
   esmCause ESMCause, 
   --<iei format="tlv">27</iei>
   protocolConfigOptions ProtocolConfigOptions OPTIONAL,
   ...,
   [[ 10:
   --<iei format="tlv">37</iei>
   t3396Value GPRSTimer3 OPTIONAL
   ]],
   [[ 12:
   --<iei format="tlv">6B</iei>
   reattemptInd ReattemptInd OPTIONAL
   ]],
   [[ 13:
   --<iei format="tlv">33</iei>
   nbifomContainer NBIFOMContainer OPTIONAL, 
   --<iei format="tlv-e">7B</iei>
   extProtoConfigOpts ExtProtoConfigOptions OPTIONAL
   ]]
}

/* 8.3.8 Bearer resource allocation request */

mt-BearerResAllocReq INTEGER ::= 212

obj-BearerResAllocReq NAS-PROTOCOL-CLASS ::= {
   ID epsSessMgmt, mt-BearerResAllocReq
   TYPE BearerResAllocReq
}

--<is3GMessage/>
BearerResAllocReq ::= SEQUENCE {
   spare INTEGER (0..15) DEFAULT 0, 
   linkedEPSBearerIdent LinkedEPSBearerIdent,
   trafficFlowAgg TFT,
   epsQoS EPSQualityOfService, 
   --<iei format="tlv">27</iei>
   protocolConfigOptions ProtocolConfigOptions OPTIONAL, 
   ...,
   [[ 10:
   --<iei format="tv" length="1">C</iei>
   deviceProperties DeviceProperties OPTIONAL
   ]],
   [[ 13:
   --<iei format="tlv">33</iei>
   nbifomContainer NBIFOMContainer OPTIONAL, 
   --<iei format="tlv-e">7B</iei>
   extProtoConfigOpts ExtProtoConfigOptions OPTIONAL
   ]],
   [[ 15:
   --<iei format="tlv">5C</iei>
   extQOS ExtQualityOfService OPTIONAL
   ]]
}

/* 8.3.9 Bearer resource modification reject */

mt-BearerResModRej INTEGER ::= 215

obj-BearerResModRej NAS-PROTOCOL-CLASS ::= {
   ID epsSessMgmt, mt-BearerResModRej
   TYPE BearerResModRej
}

--<is3GMessage/>
BearerResModRej ::= SEQUENCE {
   esmCause ESMCause, 
   --<iei format="tlv">27</iei>
   protocolConfigOptions ProtocolConfigOptions OPTIONAL, 
   ...,
   [[ 10:
   --<iei format="tlv">37</iei>
   t3396Value GPRSTimer3 OPTIONAL
   ]],
   [[ 12:
   --<iei format="tlv">6B</iei>
   reattemptInd ReattemptInd OPTIONAL
   ]],
   [[ 13:
   --<iei format="tlv">33</iei>
   nbifomContainer NBIFOMContainer OPTIONAL, 
   --<iei format="tlv-e">7B</iei>
   extProtoConfigOpts ExtProtoConfigOptions OPTIONAL
   ]]
}

/* 8.3.10 Bearer resource modification request */

mt-BearerResModReq INTEGER ::= 214

obj-BearerResModReq NAS-PROTOCOL-CLASS ::= {
   ID epsSessMgmt, mt-BearerResModReq
   TYPE BearerResModReq
}

--<is3GMessage/>
BearerResModReq ::= SEQUENCE {
   spare INTEGER (0..15) DEFAULT 0, 
   linkedEPSBearerIdent LinkedEPSBearerIdent,
   trafficFlowAgg TFT,
   --<iei format="tlv">5B</iei>
   reqTrafficFlowQoS EPSQualityOfService OPTIONAL, 
   --<iei format="tv" length="2">58</iei>
   esmCause ESMCause OPTIONAL, 
   --<iei format="tlv">27</iei>
   protocolConfigOptions ProtocolConfigOptions OPTIONAL, 
   ...,
   [[ 10:
   --<iei format="tv" length="1">C</iei>
   deviceProperties DeviceProperties OPTIONAL
   ]],
   [[ 13:
   --<iei format="tlv">33</iei>
   nbifomContainer NBIFOMContainer OPTIONAL, 
   --<iei format="tlv">66</iei>
   hdrCompressConfigStat HdrCompressConfigStat OPTIONAL,
   --<iei format="tlv-e">7B</iei>
   extProtoConfigOpts ExtProtoConfigOptions OPTIONAL
   ]],
   [[ 15:
   --<iei format="tlv">5C</iei>
   extQOS ExtQualityOfService OPTIONAL
   ]]
}

/* 8.3.11 Deactivate EPS bearer context accept */

mt-DeactEPSBearerCtxtAcc INTEGER ::= 206

obj-DeactEPSBearerCtxtAcc NAS-PROTOCOL-CLASS ::= {
   ID epsSessMgmt, mt-DeactEPSBearerCtxtAcc
   TYPE DeactEPSBearerCtxtAcc
}

--<is3GMessage/>
DeactEPSBearerCtxtAcc ::= SEQUENCE {
   --<iei format="tlv">27</iei>
   protocolConfigOptions ProtocolConfigOptions OPTIONAL,
   ...,
   [[ 13:
   --<iei format="tlv-e">7B</iei>
   extProtoConfigOpts ExtProtoConfigOptions OPTIONAL
   ]]
}

/* 8.3.12 Deactivate EPS bearer context request */

mt-DeactEPSBearerCtxtReq INTEGER ::= 205

obj-DeactEPSBearerCtxtReq NAS-PROTOCOL-CLASS ::= {
   ID epsSessMgmt, mt-DeactEPSBearerCtxtReq
   TYPE DeactEPSBearerCtxtReq
}

--<is3GMessage/>
DeactEPSBearerCtxtReq ::= SEQUENCE {
   esmCause ESMCause, 
   --<iei format="tlv">27</iei>
   protocolConfigOptions ProtocolConfigOptions OPTIONAL, 
   ...,
   [[ 11:
   --<iei format="tlv">37</iei>
   t3396Value GPRSTimer3 OPTIONAL
   ]], 
   [[ 12:
   --<iei format="tv" length="1">C</iei>
   wlanOffloadInd WLANOffloadAccept OPTIONAL
   ]],
   [[ 13:
   --<iei format="tlv">33</iei>
   nbifomContainer NBIFOMContainer OPTIONAL, 
   --<iei format="tlv-e">7B</iei>
   extProtoConfigOpts ExtProtoConfigOptions OPTIONAL
   ]]
}

/* 8.3.12A ESM dummy message */

mt-ESMDummyMsg INTEGER ::= 220

obj-ESMDummyMsg NAS-PROTOCOL-CLASS ::= {
   ID epsSessMgmt, mt-ESMDummyMsg
   TYPE NULL
}

/* 8.3.13 ESM information request */

mt-ESMInfoReq INTEGER ::= 217

obj-ESMInfoReq NAS-PROTOCOL-CLASS ::= {
   ID epsSessMgmt, mt-ESMInfoReq
   TYPE NULL
}

/* 8.3.14 ESM information response */

mt-ESMInfoResp INTEGER ::= 218

obj-ESMInfoResp NAS-PROTOCOL-CLASS ::= {
   ID epsSessMgmt, mt-ESMInfoResp
   TYPE ESMInfoResp
}

--<is3GMessage/>
ESMInfoResp ::= SEQUENCE {
   --<iei format="tlv">28</iei>
   accessPointName AccessPointName OPTIONAL, 
   --<iei format="tlv">27</iei>
   protocolConfigOptions ProtocolConfigOptions OPTIONAL,
   ...,
   [[ 13:
   --<iei format="tlv-e">7B</iei>
   extProtoConfigOpts ExtProtoConfigOptions OPTIONAL
   ]]
}

/* 8.3.15 ESM status */

mt-ESMStatus INTEGER ::= 232

obj-ESMStatus NAS-PROTOCOL-CLASS ::= {
   ID epsSessMgmt, mt-ESMStatus
   TYPE ESMStatus
}

ESMStatus ::= ESMCause

/* 8.3.16 Modify EPS bearer context accept */

mt-ModEPSBearerCtxtAcc INTEGER ::= 202

obj-ModEPSBearerCtxtAcc NAS-PROTOCOL-CLASS ::= {
   ID epsSessMgmt, mt-ModEPSBearerCtxtAcc
   TYPE ModEPSBearerCtxtAcc
}

--<is3GMessage/>
ModEPSBearerCtxtAcc ::= SEQUENCE {
   --<iei format="tlv">27</iei>
   protocolConfigOptions ProtocolConfigOptions OPTIONAL,
   ...,
   [[ 13:
   --<iei format="tlv">33</iei>
   nbifomContainer NBIFOMContainer OPTIONAL, 
   --<iei format="tlv-e">7B</iei>
   extProtoConfigOpts ExtProtoConfigOptions OPTIONAL
   ]]
}

/* 8.3.17 Modify EPS bearer context reject */

mt-ModEPSBearerCtxtRej INTEGER ::= 203

obj-ModEPSBearerCtxtRej NAS-PROTOCOL-CLASS ::= {
   ID epsSessMgmt, mt-ModEPSBearerCtxtRej
   TYPE ModEPSBearerCtxtRej
}

--<is3GMessage/>
ModEPSBearerCtxtRej ::= SEQUENCE {
   esmCause ESMCause, 
   --<iei format="tlv">27</iei>
   protocolConfigOptions ProtocolConfigOptions OPTIONAL,
   ...,
   [[ 13:
   --<iei format="tlv">33</iei>
   nbifomContainer NBIFOMContainer OPTIONAL, 
   --<iei format="tlv-e">7B</iei>
   extProtoConfigOpts ExtProtoConfigOptions OPTIONAL
   ]]
}

/* 8.3.18 Modify EPS bearer context request */

mt-ModEPSBearerCtxtReq INTEGER ::= 201

obj-ModEPSBearerCtxtReq NAS-PROTOCOL-CLASS ::= {
   ID epsSessMgmt, mt-ModEPSBearerCtxtReq
   TYPE ModEPSBearerCtxtReq
}

--<is3GMessage/>
ModEPSBearerCtxtReq ::= SEQUENCE {
   --<iei format="tlv">5B</iei>
   newEPSQoS EPSQualityOfService OPTIONAL, 
   --<iei format="tlv">36</iei>
   tft TFT OPTIONAL,
   --<iei format="tlv">30</iei>
   newQoS QualityOfService OPTIONAL,
   --<iei format="tv" length="2">32</iei>
   negotiatedLLCSAPI LLCSAPIValue OPTIONAL,
   --<iei format="tv" length="1">8</iei>
   radioPriority RadioPriority OPTIONAL,
   --<iei format="tlv">34</iei>
   packetFlowIdentifier PacketFlowIdentValue OPTIONAL,
   --<iei format="tlv">5E</iei>
   apn-AMBR APNAggMaxBitRate OPTIONAL, 
   --<iei format="tlv">27</iei>
   protocolConfigOptions ProtocolConfigOptions OPTIONAL,
   ..., 
   [[ 12:
   --<iei format="tv" length="1">C</iei>
   wlanOffloadInd WLANOffloadAccept OPTIONAL
   ]],
   [[ 13:
   --<iei format="tlv">33</iei>
   nbifomContainer NBIFOMContainer OPTIONAL, 
   --<iei format="tlv">66</iei>
   hdrCompressConfigStat HdrCompressConfigStat OPTIONAL,
   --<iei format="tlv-e">7B</iei>
   extProtoConfigOpts ExtProtoConfigOptions OPTIONAL
   ]],
   [[ 15:
   --<iei format="tlv">5F</iei>
   extAPNAggMaxBitRate ExtAPNAggMaxBitRate OPTIONAL,
   --<iei format="tlv">5C</iei>
   extQOS ExtQualityOfService OPTIONAL
   ]]
}

/* 8.3.18A Notification */

mt-Notification INTEGER ::= 219

obj-Notification NAS-PROTOCOL-CLASS ::= {
   ID epsSessMgmt, mt-Notification
   TYPE Notification
}

Notification ::= NotificationIndicator

/* 8.3.19 PDN connectivity reject */

mt-PDNConnectRej INTEGER ::= 209

obj-PDNConnectRej NAS-PROTOCOL-CLASS ::= {
   ID epsSessMgmt, mt-PDNConnectRej
   TYPE PDNConnectRej
}

--<is3GMessage/>
PDNConnectRej ::= SEQUENCE {
   esmCause ESMCause, 
   --<iei format="tlv">27</iei>
   protocolConfigOptions ProtocolConfigOptions OPTIONAL, 
   ...,
   [[ 10:
   --<iei format="tlv">37</iei>
   t3396Value GPRSTimer3 OPTIONAL
   ]],
   [[ 12:
   --<iei format="tlv">6B</iei>
   reattemptInd ReattemptInd OPTIONAL
   ]],
   [[ 13:
   --<iei format="tlv">33</iei>
   nbifomContainer NBIFOMContainer OPTIONAL, 
   --<iei format="tlv-e">7B</iei>
   extProtoConfigOpts ExtProtoConfigOptions OPTIONAL
   ]]
}

/* 8.3.20 PDN connectivity request */

mt-PDNConnectReq INTEGER ::= 208

obj-PDNConnectReq NAS-PROTOCOL-CLASS ::= {
   ID epsSessMgmt, mt-PDNConnectReq
   TYPE PDNConnectReq
}

--<is3GMessage/>
PDNConnectReq ::= SEQUENCE {
   pdnType PDNType, 
   requestType RequestTypeValue,
   --<iei format="tv" length="1">D</iei>
   esmInfoXferFlag ESMInfoXferFlag OPTIONAL, 
   --<iei format="tlv">28</iei>
   accessPointName AccessPointName OPTIONAL, 
   --<iei format="tlv">27</iei>
   protocolConfigOptions ProtocolConfigOptions OPTIONAL,
   ...,
   [[ 10:
   --<iei format="tv" length="1">C</iei>
   deviceProperties DeviceProperties OPTIONAL
   ]],
   [[ 13:
   --<iei format="tlv">33</iei>
   nbifomContainer NBIFOMContainer OPTIONAL, 
   --<iei format="tlv">66</iei>
   hdrCompressConfig HdrCompressConfig OPTIONAL,
   --<iei format="tlv-e">7B</iei>
   extProtoConfigOpts ExtProtoConfigOptions OPTIONAL
   ]]
}

/* 8.3.21 PDN disconnect reject */

mt-PDNDisconnRej INTEGER ::= 211

obj-PDNDisconnRej NAS-PROTOCOL-CLASS ::= {
   ID epsSessMgmt, mt-PDNDisconnRej
   TYPE PDNDisconnRej
}

--<is3GMessage/>
PDNDisconnRej ::= SEQUENCE {
   esmCause ESMCause, 
   --<iei format="tlv">27</iei>
   protocolConfigOptions ProtocolConfigOptions OPTIONAL,
   ...,
   [[ 13:
   --<iei format="tlv-e">7B</iei>
   extProtoConfigOpts ExtProtoConfigOptions OPTIONAL
   ]]
}

/* 8.3.22 PDN disconnect request */

mt-PDNDisconnReq INTEGER ::= 210

obj-PDNDisconnReq NAS-PROTOCOL-CLASS ::= {
   ID epsSessMgmt, mt-PDNDisconnReq
   TYPE PDNDisconnReq
}

--<is3GMessage/>
PDNDisconnReq ::= SEQUENCE {
   spare INTEGER (0..15) DEFAULT 0, 
   linkedEPSBearerIdent LinkedEPSBearerIdent,
   --<iei format="tlv">27</iei>
   protocolConfigOptions ProtocolConfigOptions OPTIONAL,
   ...,
   [[ 13:
   --<iei format="tlv-e">7B</iei>
   extProtoConfigOpts ExtProtoConfigOptions OPTIONAL
   ]]
}

/* 8.3.23 Remote UE report */

mt-RemoteUEReport INTEGER ::= 233

obj-RemoteUEReport NAS-PROTOCOL-CLASS ::= {
   ID epsSessMgmt, mt-RemoteUEReport
   TYPE RemoteUEReport
}

--<is3GMessage/>
RemoteUEReport ::= SEQUENCE {
   --<iei format="tlv-e">79</iei>
   remoteUECtxtConn RemoteUECtxtList OPTIONAL, 
   --<iei format="tlv-e">7A</iei>
   remoteUECtxtDisconn RemoteUECtxtList OPTIONAL, 
   --<iei format="tlv">6F</iei>
   proSeKeyMgmtFunc PKMFAddress OPTIONAL
}

/* 8.3.24 Remote UE report response */

mt-RemoteUEReportResp INTEGER ::= 234

obj-RemoteUEReportResp NAS-PROTOCOL-CLASS ::= {
   ID epsSessMgmt, mt-RemoteUEReportResp
   TYPE RemoteUEReportResp
}

RemoteUEReportResp ::= NULL

/* 8.3.25 - ESM Data Transport */

mt-ESMDataTransport INTEGER ::= 235

obj-ESMDataTransport NAS-PROTOCOL-CLASS ::= {
   ID epsSessMgmt, mt-ESMDataTransport
   TYPE ESMDataTransport
}

--<is3GMessage/>
ESMDataTransport ::= SEQUENCE {
   userDataContainer UserDataContainer, 
   --<iei format="tv" length="1">F</iei>
   releaseAssistInd ReleaseAssistInd OPTIONAL
}

END
