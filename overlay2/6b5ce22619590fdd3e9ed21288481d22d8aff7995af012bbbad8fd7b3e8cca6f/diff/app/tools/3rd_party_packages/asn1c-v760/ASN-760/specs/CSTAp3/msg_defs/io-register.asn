CSTA-io-register
	{ iso( 1) identified-organization( 3) icd-ecma( 12)
		standard( 0) csta3( 285) io-register( 340) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

ioRegister OPERATION ::=
{	ARGUMENT		IORegisterArgument
	RESULT			IORegisterResult
	ERRORS			{universalFailure }
	CODE			local: 340 }

IORegisterArgument ::= SEQUENCE
{	ioDevice			DeviceID				OPTIONAL,
	extensions			CSTACommonArguments			OPTIONAL }

IORegisterResult ::= SEQUENCE
{	ioRegisterReqID			IORegisterReqID,
	extensions			CSTACommonArguments			OPTIONAL }

END  -- of CSTA-io-register
