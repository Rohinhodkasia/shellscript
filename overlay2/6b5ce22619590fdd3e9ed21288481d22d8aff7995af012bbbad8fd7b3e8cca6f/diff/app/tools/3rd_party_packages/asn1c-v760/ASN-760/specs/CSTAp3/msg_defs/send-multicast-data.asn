CSTA-send-multicast-data
	{ iso( 1) identified-organization( 3) icd-ecma( 12)
		standard( 0) csta3( 285) send-multicast-data( 113) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IOCrossRefID, DisplayAttributeList FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

sendMulticastData OPERATION ::=
{	ARGUMENT		SendMulticastDataArgument
	RESULT			SendMulticastDataResult
	ERRORS			{universalFailure }
	CODE			local: 113 }

SendMulticastDataArgument ::= SEQUENCE
{	ioCrossRefIDList		SEQUENCE OF IOCrossRefID,
	ioData				OCTET STRING				OPTIONAL,
	displayAttributes		DisplayAttributeList			OPTIONAL,
	extensions			CSTACommonArguments			OPTIONAL }

SendMulticastDataResult ::= CHOICE
{	extensions			CSTACommonArguments,
	noData				NULL }

END  -- of CSTA-send-multicast-data
