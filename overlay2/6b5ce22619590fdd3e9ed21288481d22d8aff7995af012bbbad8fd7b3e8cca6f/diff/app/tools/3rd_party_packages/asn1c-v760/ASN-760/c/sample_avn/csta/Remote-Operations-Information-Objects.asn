-- This file was generated by the Objective Systems ASN1C Compiler
-- (http://www.obj-sys.com).  Version: 6.3.A, Date: 10-Oct-2009.

Remote-Operations-Information-Objects 
{joint-iso-itu-t remote-operations(4) informationObjects(5) version1(0)}
DEFINITIONS ::= BEGIN

IMPORTS

emptyBind, emptyUnbind
FROM Remote-Operations-Useful-Definitions 
{joint-iso-itu-t remote-operations(4) useful-definitions(7) version1(0)};

-- Productions

Priority ::= INTEGER

Code ::= CHOICE {
   local INTEGER,
   global OBJECT IDENTIFIER
}

-- Class definitions

ERROR ::= CLASS {
   &ParameterType OPTIONAL,
   &parameterTypeOptional BOOLEAN OPTIONAL,
   &ErrorPriority Priority OPTIONAL,
   &errorCode Code UNIQUE OPTIONAL
}

OPERATION ::= CLASS {
   &ArgumentType OPTIONAL,
   &argumentTypeOptional BOOLEAN OPTIONAL,
   &returnResult BOOLEAN OPTIONAL,
   &ResultType OPTIONAL,
   &resultTypeOptional BOOLEAN OPTIONAL,
   &Errors ERROR OPTIONAL,
   &Linked OPERATION OPTIONAL,
   &synchronous BOOLEAN OPTIONAL,
   &alwaysReturns BOOLEAN OPTIONAL,
   &InvokePriority Priority OPTIONAL,
   &ResultPriority Priority OPTIONAL,
   &operationCode Code UNIQUE OPTIONAL
}

OPERATION-PACKAGE ::= CLASS {
   &Both OPERATION OPTIONAL,
   &Consumer OPERATION OPTIONAL,
   &Supplier OPERATION OPTIONAL,
   &id OBJECT IDENTIFIER UNIQUE OPTIONAL
}

CONNECTION-PACKAGE ::= CLASS {
   &bind OPERATION OPTIONAL,
   &unbind OPERATION OPTIONAL,
   &responderCanUnbind BOOLEAN OPTIONAL,
   &unbindCanFail BOOLEAN OPTIONAL,
   &id OBJECT IDENTIFIER UNIQUE OPTIONAL
}

CONTRACT ::= CLASS {
   &connection CONNECTION_PACKAGE OPTIONAL,
   &OperationsOf OPERATION_PACKAGE OPTIONAL,
   &InitiatorConsumerOf OPERATION_PACKAGE OPTIONAL,
   &InitiatorSupplierOf OPERATION_PACKAGE OPTIONAL,
   &id OBJECT IDENTIFIER UNIQUE OPTIONAL
}

ROS-OBJECT-CLASS ::= CLASS {
   &Is ROS_OBJECT_CLASS OPTIONAL,
   &Initiates CONTRACT OPTIONAL,
   &Responds CONTRACT OPTIONAL,
   &InitiatesAndResponds CONTRACT OPTIONAL,
   &id OBJECT IDENTIFIER UNIQUE
}


END
