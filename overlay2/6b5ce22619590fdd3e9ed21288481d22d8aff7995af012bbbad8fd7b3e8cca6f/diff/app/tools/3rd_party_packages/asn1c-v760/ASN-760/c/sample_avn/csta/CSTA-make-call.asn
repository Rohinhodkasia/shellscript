-- This file was generated by the Objective Systems ASN1C Compiler
-- (http://www.obj-sys.com).  Version: 6.3.A, Date: 17-Oct-2009.

CSTA-make-call 
{ iso( 1) identified-organization( 3) icd-ecma( 0012) 
		standard( 0) csta( 180) version1( 1) make-call( 10) }
DEFINITIONS ::= BEGIN

IMPORTS

OPERATION, ERROR
FROM Remote-Operations-Information-Objects 
{joint-iso-itu-t remote-operations(4) informationObjects(5) version1(0)}

ConnectionID
FROM CSTA-call-connection-identifiers 
{ iso( 1) identified-organization( 3) icd-ecma( 0012)
		standard( 0) csta( 180) version1( 1) call-connection-identifiers( 124) }
   

CSTACommonArguments, CSTAPrivateData
FROM CSTA-extension-types 
{ iso( 1) identified-organization( 3) icd-ecma( 0012)
		standard( 0) csta( 180) version1( 1) extension-types( 129) }
   

DeviceID, CalledDeviceID
FROM CSTA-device-identifiers 
{ iso( 1) identified-organization( 3) icd-ecma( 0012)
		standard( 0) csta( 180) version1( 1) device-identifiers( 123) }
   

universalFailure
FROM CSTA-error-definition 
{ iso( 1) identified-organization( 3) icd-ecma( 0012)
		standard( 0) csta( 180) version1( 1) error-definition( 120) }
   ;

-- Productions

MakeCallArgument ::= SEQUENCE {
   callingDevice DeviceID,
   calledDirectoryNumber CalledDeviceID,
   extensions CSTACommonArguments OPTIONAL
}

MakeCallResult ::= CHOICE {
   aSeq SEQUENCE {
      initiatedCall ConnectionID,
      extensions CSTAPrivateData OPTIONAL
   },
   initiatedCall ConnectionID
}

-- Information Object definitions

makeCall OPERATION ::= {
   &ArgumentType MakeCallArgument, 
   &ResultType MakeCallResult, 
   &Errors {universalFailure}, 
   &operationCode local : 10
}


END
