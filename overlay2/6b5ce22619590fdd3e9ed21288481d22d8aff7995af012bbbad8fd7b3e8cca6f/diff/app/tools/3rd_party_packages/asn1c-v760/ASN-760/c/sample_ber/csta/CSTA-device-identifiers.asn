-- This file was generated by the Objective Systems ASN1C Compiler
-- (http://www.obj-sys.com).  Version: 6.3.A, Date: 17-Oct-2009.

CSTA-device-identifiers 
{ iso( 1) identified-organization( 3) icd-ecma( 0012)
		standard( 0) csta( 180) version1( 1) device-identifiers( 123) }
DEFINITIONS ::= BEGIN

-- Productions

NumberDigits ::= IA5String

DeviceNumber ::= INTEGER

DeviceID ::= CHOICE {
   dialingNumber [0] IMPLICIT NumberDigits,
   deviceNumber [1] IMPLICIT DeviceNumber
}

PublicTON ::= CHOICE {
   unknown [0] IMPLICIT IA5String,
   international [1] IMPLICIT IA5String,
   national [2] IMPLICIT IA5String,
   networkspecific [3] IMPLICIT IA5String,
   subscriber [4] IMPLICIT IA5String,
   abbreviated [5] IMPLICIT IA5String
}

PrivateTON ::= CHOICE {
   unknown [0] IMPLICIT IA5String,
   level3RegionalNumber [1] IMPLICIT IA5String,
   level2RegionalNumber [2] IMPLICIT IA5String,
   level1RegionalNumber [3] IMPLICIT IA5String,
   pTNSpecificNumber [4] IMPLICIT IA5String,
   localNumber [5] IMPLICIT IA5String,
   abbreviated [6] IMPLICIT IA5String
}

OtherPlan ::= OCTET STRING

ExtendedDeviceID ::= CHOICE {
   deviceIdentifier DeviceID,
   implicitPublic [2] IMPLICIT NumberDigits,
   explicitPublic [3] PublicTON,
   implicitPrivate [4] IMPLICIT NumberDigits,
   explicitPrivate [5] PrivateTON,
   other [6] IMPLICIT OtherPlan
}

CalledDeviceID ::= [APPLICATION 2] CHOICE {
   deviceIdentifier ExtendedDeviceID,
   notKnown [7] IMPLICIT NULL,
   notRequired [8] IMPLICIT NULL
}

SubjectDeviceID ::= [APPLICATION 3] CHOICE {
   deviceIdentifier ExtendedDeviceID,
   notKnown [7] IMPLICIT NULL,
   notRequired [8] IMPLICIT NULL
}

CallingDeviceID ::= [APPLICATION 1] CHOICE {
   deviceIdentifier ExtendedDeviceID,
   notKnown [7] IMPLICIT NULL,
   notRequired [8] IMPLICIT NULL
}

RedirectionDeviceID ::= [APPLICATION 4] CHOICE {
   numberdialed ExtendedDeviceID,
   notKnown [7] IMPLICIT NULL,
   notRequired [8] IMPLICIT NULL
}

END
