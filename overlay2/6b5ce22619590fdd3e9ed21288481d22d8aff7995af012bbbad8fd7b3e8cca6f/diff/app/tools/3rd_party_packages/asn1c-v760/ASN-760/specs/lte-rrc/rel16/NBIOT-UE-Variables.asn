-- This file was generated by the Objective Systems ASN1C Compiler
-- (http://www.obj-sys.com).  Version: 7.5.1.1, Date: 09-Jul-2021.

NBIOT-UE-Variables DEFINITIONS AUTOMATIC TAGS ::= BEGIN

IMPORTS

CellGlobalIdEUTRA, maxFreq, PLMN-IdentityList3-r11
FROM EUTRA-RRC-Definitions 

VarShortMAC-Input, VarShortResumeMAC-Input-r13
FROM EUTRA-UE-Variables 

ANR-CarrierList-NB-r16, ANR-MeasResult-NB-r16, maxFreqANR-NB-r16, 
   MeasResultServCell-NB-r14, NRSRP-Range-NB-r14, RLF-Report-NB-r16
FROM NBIOT-RRC-Definitions ;

-- Productions

VarShortMAC-Input-NB-r13 ::= VarShortMAC-Input

VarShortResumeMAC-Input-NB-r13 ::= VarShortResumeMAC-Input-r13

VarANR-MeasConfig-NB-r16 ::= SEQUENCE {
   anr-QualityThreshold-r16 [0] NRSRP-Range-NB-r14,
   anr-CarrierList-r16 [1] ANR-CarrierList-NB-r16
}

VarANR-MeasReport-NB-r16 ::= SEQUENCE {
   plmn-IdentityList-r16 [0] PLMN-IdentityList3-r11,
   servCellIdentity-r16 [1] CellGlobalIdEUTRA,
   measResultServCell-r16 [2] MeasResultServCell-NB-r14,
   relativeTimeStamp-r16 [3] INTEGER (0..95),
   measResultList-r16 [4] SEQUENCE (SIZE (1..maxFreqANR-NB-r16)) OF ANR-MeasResult-NB-r16
}

VarRLF-Report-NB-r16 ::= SEQUENCE {
   rlf-Report-r16 [0] RLF-Report-NB-r16,
   plmn-IdentityList-r16 [1] PLMN-IdentityList3-r11
}

END
