CSTA-io-register-abort
	{ iso( 1) identified-organization( 3) icd-ecma( 12)
		standard( 0) csta3( 285) io-register-abort( 341) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

ioRegisterAbort	OPERATION ::=
{	ARGUMENT		IORegisterAbortArgument
	ERRORS			{universalFailure }
	ALWAYS RESPONDS		FALSE
	CODE			local: 341 }

IORegisterAbortArgument ::= SEQUENCE
{	ioRegisterReqID			IORegisterReqID,
	extensions			CSTACommonArguments			OPTIONAL }

END  -- of CSTA-io-register-abort
