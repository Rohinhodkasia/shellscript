-- CS1-datatypes subset needed to compile CAP

CS1-DataTypes DEFINITIONS IMPLICIT TAGS ::=
BEGIN

CallingPartysCategory ::= OCTET STRING (SIZE (1))

Duration ::= INTEGER (-2..86400)

HighLayerCompatibility ::= OCTET STRING (SIZE(highLayerCompatibilityLength))

highLayerCompatibilityLength INTEGER ::= 2

Integer4 ::= INTEGER (0..2147483647)

Interval ::= INTEGER (-1..60000)

LegID ::= CHOICE {
   sendingSideID   [0] LegType,  -- used in operations sent from SCF to SSF
   receivingSideID [1] LegType   -- used in operations sent from SSF to SCF
}

LegType ::= OCTET STRING (SIZE(1))

RedirectionInformation ::= OCTET STRING (SIZE (2))

ServiceKey ::= Integer4

END
