-- This file was generated by the Objective Systems ASN1C Compiler
-- (http://www.obj-sys.com).  Version: 6.3.A, Date: 17-Oct-2009.

CSTA-ROSE-PDU-types DEFINITIONS ::= BEGIN

IMPORTS

ROS, InvokeId, Reject
FROM Remote-Operations-Generic-ROS-PDUs 
{joint-iso-itu-t remote-operations(4) generic-ROS-PDUs(6) version1(0)}

OPERATION, ERROR, Code
FROM Remote-Operations-Information-Objects 
{joint-iso-itu-t remote-operations(4) informationObjects(5) version1(0)}

makeCall
FROM CSTA-make-call 

universalFailure
FROM CSTA-error-definition 
{ iso( 1) identified-organization( 3) icd-ecma( 0012)
		standard( 0) csta( 180) version1( 1) error-definition( 120) }
   ;

-- Productions

InvokeIDs ::= INTEGER

CSTA-ROSE-PDU ::= CHOICE {
   invoke [1] IMPLICIT SEQUENCE {
      invokeId InvokeId (InvokeIDs),
      linkedId CHOICE {
         present [0] IMPLICIT INTEGER,
         absent [1] IMPLICIT NULL
      } OPTIONAL,
      opcode OPERATION.&operationCode ({OperationSet}),
      argument OPERATION.&ArgumentType ({OperationSet}{@.opcode}) OPTIONAL
   },
   returnResult [2] IMPLICIT SEQUENCE {
      invokeId InvokeId,
      result SEQUENCE {
         opcode OPERATION.&operationCode ({OperationSet}),
         result OPERATION.&ResultType ({OperationSet}{@.opcode})
      } OPTIONAL
   },
   returnError [3] IMPLICIT SEQUENCE {
      invokeId InvokeId,
      errcode ERROR.&errorCode ({Errors_ReturnError}),
      parameter ERROR.&ParameterType ({Errors_ReturnError}{@.errcode}) OPTIONAL
   },
   reject [4] IMPLICIT Reject
}

-- Information Object Set definitions

OperationSet OPERATION ::= { makeCall, ... }

Errors_ReturnError ERROR ::= { universalFailure }

END
