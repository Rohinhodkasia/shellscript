-- This file was generated by the Objective Systems ASN1C Compiler
-- (http://www.obj-sys.com).  Version: 6.3.A, Date: 17-Oct-2009.

CSTA-call-connection-identifiers 
{ iso( 1) identified-organization( 3) icd-ecma( 0012)
		standard( 0) csta( 180) version1( 1) call-connection-identifiers( 124) }
DEFINITIONS ::= BEGIN

IMPORTS

DeviceID
FROM CSTA-device-identifiers 
{ iso( 1) identified-organization( 3) icd-ecma( 0012)
		standard( 0) csta( 180) version1( 1) device-identifiers( 123) }
   ;

-- Productions

ConnectionID ::= [APPLICATION 11] IMPLICIT SEQUENCE {
   call [2] IMPLICIT OCTET STRING OPTIONAL,
   device CHOICE {
      staticID DeviceID,
      dynamicID [3] IMPLICIT OCTET STRING
   } OPTIONAL
}

END
