CSTA-send-message
	{ iso( 1) identified-organization( 3) icd-ecma( 12)
		standard( 0) csta3( 285) send-message( 376) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CallCharacteristics, CallLinkageData FROM CSTA-call-control
	{ iso( 1) identified-organization( 3) icd-ecma( 12)
		standard( 0) csta3( 285) call-control( 130) }
ConnectionID FROM CSTA-call-connection-identifiers
	{ iso( 1) identified-organization( 3) icd-ecma( 12)
		standard( 0) csta3( 285) call-connection-identifiers( 124) }
AccountInfo, AuthCode, CorrelatorData
FROM CSTA-device-feature-types
	{ iso( 1) identified-organization( 3) icd-ecma( 12)
		standard( 0) csta3( 285) device-feature-types( 127) }
MediaCallCharacteristics FROM CSTA-media-services	
	{ iso( 1) identified-organization( 3) icd-ecma( 12)
		standard( 0) csta3( 285) media-services( 136) }
CSTACommonArguments FROM CSTA-extension-types
	{ iso( 1) identified-organization( 3) icd-ecma( 12)
		standard( 0) csta3( 285) extension-types( 129) }
SubjectOfCall,LanguagePreferences, MessageInfo 
FROM CSTA-device-feature-types
	{ iso( 1) identified-organization( 3) icd-ecma( 12)
		standard( 0) csta3( 285) device-feature-types( 127) };

sendMessage OPERATION ::=
{ 	ARGUMENT 		SendMessageArgument
	RESULT 			SendMessageResult
	ERRORS 			{universalFailure }
	CODE 			local: 376 }

SendMessageArgument ::= SEQUENCE
{	callingDevice 			DeviceID,
	destinationDevices		DeviceListItems,
	messageInfo	 		MessageInfo,
	accountCode 			[0] IMPLICIT AccountInfo 			OPTIONAL,
	authCode 			[1] IMPLICIT AuthCode 				OPTIONAL,
	correlatorData 			[2] IMPLICIT CorrelatorData 			OPTIONAL,
	callCharacteristics		[3] IMPLICIT CallCharacteristics		OPTIONAL,
	mediaCallCharacteristics	[4] IMPLICIT MediaCallCharacteristics		OPTIONAL,
	subjectOfCall 			[5] IMPLICIT SubjectOfCall	 		OPTIONAL,
	languagePreferences		[6] IMPLICIT LanguagePreferences		OPTIONAL,
	extensions 			CSTACommonArguments 				OPTIONAL }

SendMessageResult ::= SEQUENCE
{ 	connectionList	 		ConnectionListItems,
	mediaCallCharacteristics	MediaCallCharacteristics			OPTIONAL,
	listOfCallLinkageData 		[1] IMPLICIT CallLinkageDataListItems		OPTIONAL,
	extensions 			CSTACommonArguments 				OPTIONAL }

DeviceListItems ::= SEQUENCE
{	device				DeviceID }

ConnectionListItems ::= SEQUENCE
{	connection			ConnectionID }

CallLinkageDataListItems ::= SEQUENCE
{	callLinkageData			CallLinkageData }

END -- of CSTA-send-message
