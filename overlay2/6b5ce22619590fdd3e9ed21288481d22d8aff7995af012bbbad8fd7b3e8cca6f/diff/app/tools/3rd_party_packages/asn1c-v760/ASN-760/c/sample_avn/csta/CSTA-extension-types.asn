-- This file was generated by the Objective Systems ASN1C Compiler
-- (http://www.obj-sys.com).  Version: 6.3.A, Date: 18-Oct-2009.

CSTA-extension-types 
{ iso( 1) identified-organization( 3) icd-ecma( 0012)
		standard( 0) csta( 180) version1( 1) extension-types( 129) }
DEFINITIONS ::= BEGIN

IMPORTS

CSTASecurityData
FROM CSTA-security 
{ iso( 1) identified-organization( 3) icd-ecma( 0012)
		standard( 0) csta( 180) version1( 1) security( 128) }
   ;

-- Productions

CSTAPrivateData ::= [APPLICATION 29] IMPLICIT SEQUENCE {
   manufacturer OBJECT IDENTIFIER,
   aOpenType ANY
}

CSTACommonArguments ::= [APPLICATION 30] IMPLICIT SEQUENCE {
   security [0] IMPLICIT CSTASecurityData OPTIONAL,
   privateData [1] IMPLICIT SEQUENCE OF  CSTAPrivateData OPTIONAL
}

END
