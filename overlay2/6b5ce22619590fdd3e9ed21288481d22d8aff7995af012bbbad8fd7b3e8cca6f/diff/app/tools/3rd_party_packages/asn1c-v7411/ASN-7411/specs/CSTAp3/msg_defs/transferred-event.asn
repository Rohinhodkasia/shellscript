CSTA-transferred-event
	{ iso( 1) identified-organization( 3) icd-ecma( 12)
		standard( 0) csta3( 285) transferred-event( 35) }

DEFINITIONS ::=
BEGIN

IMPORTS 

-- Data Types --
EventCause FROM CSTA-event-causes
	{ iso( 1) identified-organization( 3) icd-ecma( 12)
		standard( 0) csta3( 285) event-causes( 121) }
SubjectDeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
LocalConnectionState, ConnectionList FROM CSTA-connection-states
	{ iso( 1) identified-organization( 3) icd-ecma( 12)
		standard( 0) csta3( 285) connection-states( 125) }
CorrelatorData, UserData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) }
CallCharacteristics, CallLinkageDataList, ServicesPermitted FROM CSTA-call-control 
	{ iso( 1) identified-organization( 3) icd-ecma( 12)
		standard( 0) csta3( 285) call-control( 130) }
ChargingInfo FROM CSTA-charge-info
	{ iso( 1) identified-organization( 3) icd-ecma( 12)
		standard( 0) csta3( 285) charge-info( 133) }
LocationInfoList FROM CSTA-call-control
	{ iso( 1) identified-organization( 3) icd-ecma( 12)
		standard( 0) csta3( 285) call-control( 130) }
LanguagePreferences, DeviceHistory FROM CSTA-device-feature-types
	{ iso( 1) identified-organization( 3) icd-ecma( 12)
		standard( 0) csta3( 285) device-feature-types( 127) }
ConnectionInformation, MediaCallCharacteristics FROM CSTA-media-services
	{ iso( 1) identified-organization( 3) icd-ecma( 12)
		standard( 0) csta3( 285) media-services( 136) };

TransferredEvent ::= SEQUENCE
{	primaryOldCall			ConnectionID,
	secondaryOldCall		[ 0] IMPLICIT ConnectionID		OPTIONAL,
	transferringDevice		SubjectDeviceID,
	transferredToDevice		SubjectDeviceID,
	transferredConnections		[ 1] IMPLICIT ConnectionList,
	localConnectionInfo		LocalConnectionState			OPTIONAL,
	correlatorData			[ 2] IMPLICIT CorrelatorData		OPTIONAL,
	userData			UserData				OPTIONAL,
	chargingInfo			[ 3] IMPLICIT ChargingInfo		OPTIONAL,
	cause				EventCause,
	servicesPermitted		[ 4] IMPLICIT ServicesPermitted		OPTIONAL,
	mediaCallCharacteristics	[ 5] IMPLICIT MediaCallCharacteristics	OPTIONAL,
	callCharacteristics		[ 6] IMPLICIT CallCharacteristics	OPTIONAL,
	callLinkageDataList		[ 7] IMPLICIT CallLinkageDataList	OPTIONAL,
	languagePreferences		[ 8] IMPLICIT LanguagePreferences	OPTIONAL,
	deviceHistory			[ 9] IMPLICIT DeviceHistory		OPTIONAL,
	locationInfo			[10] IMPLICIT LocationInfoList		OPTIONAL,
	extensions			CSTACommonArguments			OPTIONAL }

END  -- of CSTA-transferred-event
