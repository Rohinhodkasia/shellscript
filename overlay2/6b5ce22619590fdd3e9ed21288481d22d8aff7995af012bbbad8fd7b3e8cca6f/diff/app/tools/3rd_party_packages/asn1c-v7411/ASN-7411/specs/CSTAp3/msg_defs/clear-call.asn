CSTA-clear-call
	{ iso( 1) identified-organization( 3) icd-ecma( 12)
		standard( 0) csta3( 285) clear-call( 4) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
UserData FROM CSTA-device-feature-types
	{ iso( 1) identified-organization( 3) icd-ecma( 12)
		standard( 0) csta3( 285) device-feature-types( 127) } 
EventCause FROM CSTA-event-causes
	{ iso( 1) identified-organization( 3) icd-ecma( 12)
		standard( 0) csta3( 285) event-causes( 121) }
CSTACommonArguments FROM CSTA-extension-types
	{ iso( 1) identified-organization( 3) icd-ecma( 12)
		standard( 0) csta3( 285) extension-types( 129) };

clearCall OPERATION ::=
{ 	ARGUMENT 		ClearCallArgument
	RESULT 			ClearCallResult
	ERRORS 			{universalFailure }
	CODE 			local: 4 }

ClearCallArgument ::= SEQUENCE
{ 	callToBeCleared 		ConnectionID,
	userData 			UserData 			OPTIONAL,
	reason				EventCause			OPTIONAL,
	extensions 			CSTACommonArguments 		OPTIONAL }

ClearCallResult ::= CHOICE
{	extensions 			CSTACommonArguments,
	noData 				NULL }

END -- of CSTA-clear-call
