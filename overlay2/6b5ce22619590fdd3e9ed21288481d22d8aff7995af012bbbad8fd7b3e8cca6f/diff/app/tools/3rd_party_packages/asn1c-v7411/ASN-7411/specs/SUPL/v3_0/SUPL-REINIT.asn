-- This file was generated by the Objective Systems ASN1C Compiler
-- (http://www.obj-sys.com).  Version: 6.8.A, Date: 18-Nov-2014.

SUPL-REINIT DEFINITIONS AUTOMATIC TAGS ::= BEGIN

IMPORTS

ProtectionLevel
FROM ULP-Version-2-message-extensions ;

-- Productions

Ver3-SUPLREINIT ::= SEQUENCE {
   protectionLevel [0] ProtectionLevel OPTIONAL,
   ...
}

END
