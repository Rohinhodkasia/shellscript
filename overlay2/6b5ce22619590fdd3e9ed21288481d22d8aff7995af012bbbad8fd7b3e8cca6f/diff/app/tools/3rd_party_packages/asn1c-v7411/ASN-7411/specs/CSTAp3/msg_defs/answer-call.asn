CSTA-answer-call
	{ iso( 1) identified-organization( 3) icd-ecma( 12)
		standard( 0) csta3( 285) answer-call( 2) }

DEFINITIONS ::=
BEGIN

IMPORTS
OPERATION, ERROR FROM Remote-Operations-Information-Objects
	{joint-iso-itu-t remote-operations(4) informationObjects(5) version1(0) }

-- Data Types –-
universalFailure FROM CSTA-error-definition
	{ iso( 1) identified-organization( 3) icd-ecma( 12)
		standard( 0) csta3( 285) error-definition( 120) }
ConnectionID FROM CSTA-call-connection-identifiers
	{ iso( 1) identified-organization( 3) icd-ecma( 12)
		standard( 0) csta3( 285) call-connection-identifiers( 124) }
CorrelatorData, UserData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

answerCall OPERATION ::=
{ 	ARGUMENT 		AnswerCallArgument
	RESULT 			AnswerCallResult
	ERRORS 			{universalFailure }
	CODE 			local: 2 }

AnswerCallArgument ::= SEQUENCE
{ 	callToBeAnswered 		ConnectionID,
	correlatorData 			CorrelatorData 			OPTIONAL,
	userData 			UserData 			OPTIONAL,
	extensions 			CSTACommonArguments 		OPTIONAL }

AnswerCallResult ::= CHOICE
{	extensions 			CSTACommonArguments,
	noData 				NULL }

END -- of CSTA-answer-call
