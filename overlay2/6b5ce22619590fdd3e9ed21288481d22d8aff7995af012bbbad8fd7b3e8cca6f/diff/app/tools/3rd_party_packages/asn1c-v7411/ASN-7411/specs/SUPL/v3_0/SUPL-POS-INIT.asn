-- This file was generated by the Objective Systems ASN1C Compiler
-- (http://www.obj-sys.com).  Version: 6.8.A, Date: 18-Nov-2014.

SUPL-POS-INIT DEFINITIONS AUTOMATIC TAGS ::= BEGIN

IMPORTS

SUPLPOS
FROM SUPL-POS 

SETCapabilities
FROM SUPL-START 

LocationId, Position, Ver
FROM ULP-Components 

Ver2-SUPL-POS-INIT-extension
FROM ULP-Version-2-message-extensions 

Ver2-RequestedAssistData-extension
FROM ULP-Version-2-parameter-extensions 

Ver3-SUPL-POS-INIT-extension
FROM ULP-Version-3-message-extensions ;

-- Productions

SatelliteInfoElement ::= SEQUENCE {
   satId [0] INTEGER (0..63),
   iODE [1] INTEGER (0..255),
   ...
}

SatelliteInfo ::= SEQUENCE (SIZE (1..31)) OF SatelliteInfoElement

NavigationModel ::= SEQUENCE {
   gpsWeek [0] INTEGER (0..1023),
   gpsToe [1] INTEGER (0..167),
   nSAT [2] INTEGER (0..31),
   toeLimit [3] INTEGER (0..10),
   satInfo [4] SatelliteInfo OPTIONAL,
   ...
}

RequestedAssistData ::= SEQUENCE {
   almanacRequested [0] BOOLEAN,
   utcModelRequested [1] BOOLEAN,
   ionosphericModelRequested [2] BOOLEAN,
   dgpsCorrectionsRequested [3] BOOLEAN,
   referenceLocationRequested [4] BOOLEAN,
   referenceTimeRequested [5] BOOLEAN,
   acquisitionAssistanceRequested [6] BOOLEAN,
   realTimeIntegrityRequested [7] BOOLEAN,
   navigationModelRequested [8] BOOLEAN,
   navigationModelData [9] NavigationModel OPTIONAL,
   ...,
   ver2-RequestedAssistData-extension [10] Ver2-RequestedAssistData-extension
       OPTIONAL
}

SUPLPOSINIT ::= SEQUENCE {
   sETCapabilities [0] SETCapabilities,
   requestedAssistData [1] RequestedAssistData OPTIONAL,
   locationId [2] LocationId,
   position [3] Position OPTIONAL,
   sUPLPOS [4] SUPLPOS OPTIONAL,
   ver [5] Ver OPTIONAL,
   ...,
   ver2-SUPL-POS-INIT-extension [6] Ver2-SUPL-POS-INIT-extension OPTIONAL,
   ver3-SUPL-POS-INIT-extension [7] Ver3-SUPL-POS-INIT-extension OPTIONAL
}

END
