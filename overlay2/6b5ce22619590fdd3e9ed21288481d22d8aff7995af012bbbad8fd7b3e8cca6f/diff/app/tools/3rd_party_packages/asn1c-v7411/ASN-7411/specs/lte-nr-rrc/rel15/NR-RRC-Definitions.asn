-- This file was generated by the Objective Systems ASN1C Compiler
-- (http://www.obj-sys.com).  Version: 7.4.0.3, Date: 24-Mar-2020.

NR-RRC-Definitions DEFINITIONS AUTOMATIC TAGS ::= BEGIN

-- Parameterized type assignments

SetupRelease {ElementTypeParam} ::= CHOICE {
   release NULL,
   setup ElementTypeParam
}

-- Productions

ReestablishmentCause ::= ENUMERATED { reconfigurationFailure(0), 
   handoverFailure(1), otherFailure(2), spare1(3) }

PeriodicRNAU-TimerValue ::= ENUMERATED { min5(0), min10(1), min20(2), min30(3)
   , min60(4), min120(5), min360(6), min720(7) }

PagingCycle ::= ENUMERATED { rf32(0), rf64(1), rf128(2), rf256(3) }

EstablishmentCause ::= ENUMERATED { emergency(0), highPriorityAccess(1), 
   mt-Access(2), mo-Signalling(3), mo-Data(4), mo-VoiceCall(5), mo-VideoCall(6)
   , mo-SMS(7), mps-PriorityAccess(8), mcs-PriorityAccess(9), spare6(10), 
   spare5(11), spare4(12), spare3(13), spare2(14), spare1(15) }

UAC-AccessCategory1-SelectionAssistanceInfo ::= ENUMERATED { a(0), b(1), c(2) }
   

ReducedAggregatedBandwidth ::= ENUMERATED { mhz0(0), mhz10(1), mhz20(2), 
   mhz30(3), mhz40(4), mhz50(5), mhz60(6), mhz80(7), mhz100(8), mhz200(9), 
   mhz300(10), mhz400(11) }

-- TAG-PUSCH-TPC-COMMANDCONFIG-STOP
-- TAG-Q-OFFSETRANGE-START
Q-OffsetRange ::= ENUMERATED { dB-24(0), dB-22(1), dB-20(2), dB-18(3), dB-16(4)
   , dB-14(5), dB-12(6), dB-10(7), dB-8(8), dB-6(9), dB-5(10), dB-4(11), 
   dB-3(12), dB-2(13), dB-1(14), dB0(15), dB1(16), dB2(17), dB3(18), dB4(19), 
   dB5(20), dB6(21), dB8(22), dB10(23), dB12(24), dB14(25), dB16(26), dB18(27)
   , dB20(28), dB22(29), dB24(30) }

RangeToBestCell ::= Q-OffsetRange

-- TAG-SIB9-STOP
-- TAG-ADDITIONALSPECTRUMEMISSION-START
AdditionalSpectrumEmission ::= INTEGER (0..7)

-- TAG-ADDITIONALSPECTRUMEMISSION-STOP
-- TAG-ALPHA-START
Alpha ::= ENUMERATED { alpha0(0), alpha04(1), alpha05(2), alpha06(3), 
   alpha07(4), alpha08(5), alpha09(6), alpha1(7) }

-- TAG-ALPHA-STOP
-- TAG-AMF-IDENTIFIER-START
AMF-Identifier ::= BIT STRING  (SIZE (24))

-- TAG-AMF-IDENTIFIER-STOP
-- TAG-ARFCN-VALUEEUTRA-START
ARFCN-ValueEUTRA ::= INTEGER (0..maxEARFCN)

-- TAG-ARFCN-VALUEEUTRA-STOP
-- TAG-ARFCN-VALUENR-START
ARFCN-ValueNR ::= INTEGER (0..maxNARFCN)

-- TAG-BWP-DOWNLINKDEDICATED-STOP
-- TAG-BWP-ID-START
BWP-Id ::= INTEGER (0..maxNrofBWPs)

-- TAG-CELLGROUPCONFIG-STOP
-- TAG-CELLGROUPID-START
CellGroupId ::= INTEGER (0..maxSecondaryCellGroups)

-- TAG-CELLGROUPID-STOP
-- TAG-CELLIDENTITY-START
CellIdentity ::= BIT STRING  (SIZE (36))

-- TAG-CELLIDENTITY-STOP
-- TAG-CELLRESELECTIONPRIORITY-START
CellReselectionPriority ::= INTEGER (0..7)

-- TAG-CELLRESELECTIONPRIORITY-STOP
-- TAG-CELLRESELECTIONSUBPRIORITY-START
CellReselectionSubPriority ::= ENUMERATED { oDot2(0), oDot4(1), oDot6(2), 
   oDot8(3) }

-- TAG-CONTROLRESOURCESET-STOP
-- TAG-CONTROLRESOURCESETID-START
ControlResourceSetId ::= INTEGER (0..maxNrofControlResourceSets-1)

-- TAG-CONTROLRESOURCESETID-STOP
-- TAG-CONTROLRESOURCESETZERO-START
ControlResourceSetZero ::= INTEGER (0..15)

-- TAG-CSI-IM-RESOURCE-STOP
-- TAG-CSI-IM-RESOURCEID-START
CSI-IM-ResourceId ::= INTEGER (0..maxNrofCSI-IM-Resources-1)

-- TAG-CSI-IM-RESOURCESET-STOP
-- TAG-CSI-IM-RESOURCESETID-START
CSI-IM-ResourceSetId ::= INTEGER (0..maxNrofCSI-IM-ResourceSets-1)

PortIndex8 ::= INTEGER (0..7)

PortIndex4 ::= INTEGER (0..3)

PortIndex2 ::= INTEGER (0..1)

-- TAG-CSI-REPORTCONFIG-STOP
-- TAG-CSI-REPORTCONFIGID-START
CSI-ReportConfigId ::= INTEGER (0..maxNrofCSI-ReportConfigurations-1)

-- TAG-CSI-RESOURCECONFIG-STOP
-- TAG-CSI-RESOURCECONFIGID-START
CSI-ResourceConfigId ::= INTEGER (0..maxNrofCSI-ResourceConfigurations-1)

CSI-RS-Index ::= INTEGER (0..maxNrofCSI-RS-ResourcesRRM-1)

-- TAG-CSI-SSB-RESOURCESET-STOP
-- TAG-CSI-SSB-RESOURCESETID-START
CSI-SSB-ResourceSetId ::= INTEGER (0..maxNrofCSI-SSB-ResourceSets-1)

-- TAG-CSI-SSB-RESOURCESETID-STOP
-- TAG-DEDICATED-NAS-MESSAGE-START
DedicatedNAS-Message ::= OCTET STRING

-- TAG-DOWNLINKPREEMPTION-STOP
-- TAG-DRB-IDENTITY-START
DRB-Identity ::= INTEGER (1..32)

-- TAG-DRX-CONFIG-STOP
-- TAG-FILTERCOEFFICIENT-START
FilterCoefficient ::= ENUMERATED { fc0(0), fc1(1), fc2(2), fc3(3), fc4(4), 
   fc5(5), fc6(6), fc7(7), fc8(8), fc9(9), fc11(10), fc13(11), fc15(12), 
   fc17(13), fc19(14), spare1(15), ... }

-- TAG-FILTERCOEFFICIENT-STOP
-- TAG-FREQBANDINDICATORNR-START
FreqBandIndicatorNR ::= INTEGER (1..1024)

-- TAG-FREQUENCYINFOUL-SIB-STOP
-- TAG-HYSTERESIS-START
Hysteresis ::= INTEGER (0..30)

-- TAG-HYSTERESIS-STOP
-- TAG-I-RNTI-VALUE-START
I-RNTI-Value ::= BIT STRING  (SIZE (40))

-- TAG-LOGICALCHANNELCONFIG-STOP
-- TAG-LOGICALCHANNELIDENTITY-START
LogicalChannelIdentity ::= INTEGER (1..maxLC-ID)

DataInactivityTimer ::= ENUMERATED { s1(0), s2(1), s3(2), s5(3), s7(4), s10(5)
   , s15(6), s20(7), s40(8), s50(9), s60(10), s80(11), s100(12), s120(13), 
   s150(14), s180(15) }

MeasGapSharingScheme ::= ENUMERATED { scheme00(0), scheme01(1), scheme10(2), 
   scheme11(3) }

-- TAG-MEASGAPSHARINGCONFIG-STOP
-- TAG-MEASID-START
MeasId ::= INTEGER (1..maxNrofMeasId)

EUTRA-CellIndex ::= INTEGER (1..maxCellMeasEUTRA)

-- TAG-MEASOBJECTEUTRA-STOP
-- TAG-MEASOBJECTID-START
MeasObjectId ::= INTEGER (1..maxNrofObjectId)

RSRP-RangeEUTRA ::= INTEGER (0..97)

RSRQ-RangeEUTRA ::= INTEGER (0..34)

SINR-RangeEUTRA ::= INTEGER (0..127)

-- TAG-MULTIFREQUENCYBANDLISTNR-SIB-STOP
-- TAG-NEXTHOPCHAININGCOUNT-START
NextHopChainingCount ::= INTEGER (0..7)

-- TAG-NEXTHOPCHAININGCOUNT-STOP
-- TAG-NG-5G-S-TMSI-START
NG-5G-S-TMSI ::= BIT STRING  (SIZE (48))

-- TAG-NZP-CSI-RS-RESOURCE-STOP
-- TAG-NZP-CSI-RS-RESOURCEID-START
NZP-CSI-RS-ResourceId ::= INTEGER (0..maxNrofNZP-CSI-RS-Resources-1)

-- TAG-NZP-CSI-RS-RESOURCESET-STOP
-- TAG-NZP-CSI-RS-RESOURCESETID-START
NZP-CSI-RS-ResourceSetId ::= INTEGER (0..maxNrofNZP-CSI-RS-ResourceSets-1)

-- TAG-NZP-CSI-RS-RESOURCESETID-STOP
-- TAG-P-MAX-START
P-Max ::= INTEGER (-30..33)

-- TAG-PCI-RANGEELEMENT-STOP
-- TAG-PCI-RANGEINDEX-START
PCI-RangeIndex ::= INTEGER (1..maxNrofPCI-Ranges)

UL-DataSplitThreshold ::= ENUMERATED { b0(0), b100(1), b200(2), b400(3), 
   b800(4), b1600(5), b3200(6), b6400(7), b12800(8), b25600(9), b51200(10), 
   b102400(11), b204800(12), b409600(13), b819200(14), b1228800(15), 
   b1638400(16), b2457600(17), b3276800(18), b4096000(19), b4915200(20), 
   b5734400(21), b6553600(22), infinity(23), spare8(24), spare7(25), spare6(26)
   , spare5(27), spare4(28), spare3(29), spare2(30), spare1(31) }

-- TAG-PHR-CONFIG-STOP
-- TAG-PHYSCELLID-START
PhysCellId ::= INTEGER (0..1007)

PDCCH-BlindDetection ::= INTEGER (1..15)

MCC-MNC-Digit ::= INTEGER (0..9)

-- TAG-PLMN-IDENTITYINFOLIST-STOP
-- TAG-PRB-ID-START
PRB-Id ::= INTEGER (0..maxNrofPhysicalResourceBlocks-1)

PUCCH-MaxCodeRate ::= ENUMERATED { zeroDot08(0), zeroDot15(1), zeroDot25(2), 
   zeroDot35(3), zeroDot45(4), zeroDot60(5), zeroDot80(6) }

PUCCH-ResourceSetId ::= INTEGER (0..maxNrofPUCCH-ResourceSets-1)

PUCCH-ResourceId ::= INTEGER (0..maxNrofPUCCH-Resources-1)

-- TAG-PUCCH-CONFIGCOMMON-STOP
-- TAG-PUCCH-PATHLOSSREFERENCERS-ID-START
PUCCH-PathlossReferenceRS-Id ::= INTEGER (0..maxNrofPUCCH-PathlossReferenceRSs-1)

P0-PUCCH-Id ::= INTEGER (1..8)

PUCCH-SpatialRelationInfoId ::= INTEGER (1..maxNrofSpatialRelationInfos)

P0-PUSCH-AlphaSetId ::= INTEGER (0..maxNrofP0-PUSCH-AlphaSets-1)

PUSCH-PathlossReferenceRS-Id ::= INTEGER (0..maxNrofPUSCH-PathlossReferenceRSs-1)

SRI-PUSCH-PowerControlId ::= INTEGER (0..maxNrofSRI-PUSCH-Mappings-1)

-- TAG-Q-OFFSETRANGE-STOP
-- TAG-Q-QUALMIN-START
Q-QualMin ::= INTEGER (-43..-12)

-- TAG-Q-QUALMIN-STOP
-- TAG-Q-RXLEVMIN-START
Q-RxLevMin ::= INTEGER (-70..-22)

-- TAG-RADIOLINKMONITORINGCONFIG-STOP
-- TAG-RADIOLINKMONITORINGRS-ID-START
RadioLinkMonitoringRS-Id ::= INTEGER (0..maxNrofFailureDetectionResources-1)

-- TAG-RADIOLINKMONITORINGRS-ID-STOP
-- TAG-RAN-AREACODE-START
RAN-AreaCode ::= INTEGER (0..255)

-- TAG-RATEMATCHPATTERN-STOP
-- TAG-RATEMATCHPATTERNID-START
RateMatchPatternId ::= INTEGER (0..maxNrofRateMatchPatterns-1)

-- TAG-RATEMATCHPATTERNLTE-CRS-STOP
-- TAG-REJECTWAITTIME-START
RejectWaitTime ::= INTEGER (1..16)

-- TAG-REJECTWAITTIME-STOP
-- TAG-REPORTCONFIGID-START
ReportConfigId ::= INTEGER (1..maxReportConfigId)

NR-RS-Type ::= ENUMERATED { ssb(0), csi-rs(1) }

-- TAG-REPORTCONFIGTOADDMODLIST-STOP
-- TAG-REPORTINTERVAL-START
ReportInterval ::= ENUMERATED { ms120(0), ms240(1), ms480(2), ms640(3), 
   ms1024(4), ms2048(5), ms5120(6), ms10240(7), ms20480(8), ms40960(9), 
   min1(10), min6(11), min12(12), min30(13) }

-- TAG-REPORTINTERVAL-STOP
-- TAG-RESELECTIONTHRESHOLD-START
ReselectionThreshold ::= INTEGER (0..31)

-- TAG-RESELECTIONTHRESHOLD-STOP
-- TAG-RESELECTIONTHRESHOLDQ-START
ReselectionThresholdQ ::= INTEGER (0..31)

-- TAG-RESELECTIONTHRESHOLDQ-STOP
-- TAG-RESUMECAUSE-START
ResumeCause ::= ENUMERATED { emergency(0), highPriorityAccess(1), mt-Access(2)
   , mo-Signalling(3), mo-Data(4), mo-VoiceCall(5), mo-VideoCall(6), mo-SMS(7)
   , rna-Update(8), mps-PriorityAccess(9), mcs-PriorityAccess(10), spare1(11), 
   spare2(12), spare3(13), spare4(14), spare5(15) }

T-PollRetransmit ::= ENUMERATED { ms5(0), ms10(1), ms15(2), ms20(3), ms25(4), 
   ms30(5), ms35(6), ms40(7), ms45(8), ms50(9), ms55(10), ms60(11), ms65(12), 
   ms70(13), ms75(14), ms80(15), ms85(16), ms90(17), ms95(18), ms100(19), 
   ms105(20), ms110(21), ms115(22), ms120(23), ms125(24), ms130(25), ms135(26)
   , ms140(27), ms145(28), ms150(29), ms155(30), ms160(31), ms165(32), 
   ms170(33), ms175(34), ms180(35), ms185(36), ms190(37), ms195(38), ms200(39)
   , ms205(40), ms210(41), ms215(42), ms220(43), ms225(44), ms230(45), 
   ms235(46), ms240(47), ms245(48), ms250(49), ms300(50), ms350(51), ms400(52)
   , ms450(53), ms500(54), ms800(55), ms1000(56), ms2000(57), ms4000(58), 
   spare5(59), spare4(60), spare3(61), spare2(62), spare1(63) }

PollPDU ::= ENUMERATED { p4(0), p8(1), p16(2), p32(3), p64(4), p128(5), p256(6)
   , p512(7), p1024(8), p2048(9), p4096(10), p6144(11), p8192(12), p12288(13), 
   p16384(14), p20480(15), p24576(16), p28672(17), p32768(18), p40960(19), 
   p49152(20), p57344(21), p65536(22), infinity(23), spare8(24), spare7(25), 
   spare6(26), spare5(27), spare4(28), spare3(29), spare2(30), spare1(31) }

PollByte ::= ENUMERATED { kB1(0), kB2(1), kB5(2), kB8(3), kB10(4), kB15(5), 
   kB25(6), kB50(7), kB75(8), kB100(9), kB125(10), kB250(11), kB375(12), 
   kB500(13), kB750(14), kB1000(15), kB1250(16), kB1500(17), kB2000(18), 
   kB3000(19), kB4000(20), kB4500(21), kB5000(22), kB5500(23), kB6000(24), 
   kB6500(25), kB7000(26), kB7500(27), mB8(28), mB9(29), mB10(30), mB11(31), 
   mB12(32), mB13(33), mB14(34), mB15(35), mB16(36), mB17(37), mB18(38), 
   mB20(39), mB25(40), mB30(41), mB40(42), infinity(43), spare20(44), 
   spare19(45), spare18(46), spare17(47), spare16(48), spare15(49), spare14(50)
   , spare13(51), spare12(52), spare11(53), spare10(54), spare9(55), spare8(56)
   , spare7(57), spare6(58), spare5(59), spare4(60), spare3(61), spare2(62), 
   spare1(63) }

T-Reassembly ::= ENUMERATED { ms0(0), ms5(1), ms10(2), ms15(3), ms20(4), 
   ms25(5), ms30(6), ms35(7), ms40(8), ms45(9), ms50(10), ms55(11), ms60(12), 
   ms65(13), ms70(14), ms75(15), ms80(16), ms85(17), ms90(18), ms95(19), 
   ms100(20), ms110(21), ms120(22), ms130(23), ms140(24), ms150(25), ms160(26)
   , ms170(27), ms180(28), ms190(29), ms200(30), spare1(31) }

T-StatusProhibit ::= ENUMERATED { ms0(0), ms5(1), ms10(2), ms15(3), ms20(4), 
   ms25(5), ms30(6), ms35(7), ms40(8), ms45(9), ms50(10), ms55(11), ms60(12), 
   ms65(13), ms70(14), ms75(15), ms80(16), ms85(17), ms90(18), ms95(19), 
   ms100(20), ms105(21), ms110(22), ms115(23), ms120(24), ms125(25), ms130(26)
   , ms135(27), ms140(28), ms145(29), ms150(30), ms155(31), ms160(32), 
   ms165(33), ms170(34), ms175(35), ms180(36), ms185(37), ms190(38), ms195(39)
   , ms200(40), ms205(41), ms210(42), ms215(43), ms220(44), ms225(45), 
   ms230(46), ms235(47), ms240(48), ms245(49), ms250(50), ms300(51), ms350(52)
   , ms400(53), ms450(54), ms500(55), ms800(56), ms1000(57), ms1200(58), 
   ms1600(59), ms2000(60), ms2400(61), spare2(62), spare1(63) }

SN-FieldLengthUM ::= ENUMERATED { size6(0), size12(1) }

SN-FieldLengthAM ::= ENUMERATED { size12(0), size18(1) }

-- TAG-RLF-TIMERSANDCONSTANTS-STOP
-- TAG-RNTI-VALUE-START
RNTI-Value ::= INTEGER (0..65535)

-- TAG-RNTI-VALUE-STOP
-- TAG-RSRP-RANGE-START
RSRP-Range ::= INTEGER (0..127)

-- TAG-RSRP-RANGE-STOP
-- TAG-RSRQ-RANGE-START
RSRQ-Range ::= INTEGER (0..127)

-- TAG-RSRQ-RANGE-STOP
-- TAG-SCELLINDEX-START
SCellIndex ::= INTEGER (1..31)

-- TAG-SCHEDULINGREQUESTCONFIG-STOP
-- TAG-SCHEDULINGREQUESTID-START
SchedulingRequestId ::= INTEGER (0..7)

-- TAG-SCHEDULINGREQUESTRESOURCECONFIG-STOP
-- TAG-SCHEDULINGREQUESTRESOURCEID-START
SchedulingRequestResourceId ::= INTEGER (1..maxNrofSR-Resources)

-- TAG-SCHEDULINGREQUESTRESOURCEID-STOP
-- TAG-SCRAMBLINGID-START
ScramblingId ::= INTEGER (0..1023)

QFI ::= INTEGER (0..maxQFI)

PDU-SessionID ::= INTEGER (0..255)

-- TAG-SEARCHSPACE-STOP
-- TAG-SEARCHSPACEID-START
SearchSpaceId ::= INTEGER (0..maxNrofSearchSpaces-1)

-- TAG-SEARCHSPACEID-STOP
-- TAG-SEARCHSPACEZERO-START
SearchSpaceZero ::= INTEGER (0..15)

IntegrityProtAlgorithm ::= ENUMERATED { nia0(0), nia1(1), nia2(2), nia3(3), 
   spare4(4), spare3(5), spare2(6), spare1(7), ... }

CipheringAlgorithm ::= ENUMERATED { nea0(0), nea1(1), nea2(2), nea3(3), 
   spare4(4), spare3(5), spare2(6), spare1(7), ... }

-- TAG-SECURITYALGORITHMCONFIG-STOP
-- TAG-SERVCELLINDEX-START
ServCellIndex ::= INTEGER (0..maxNrofServingCells-1)

-- TAG-SERVINGCELLCONFIGCOMMONSIB-STOP
-- TAG-SHORTI-RNTI-VALUE-START
ShortI-RNTI-Value ::= BIT STRING  (SIZE (24))

-- TAG-SHORTI-RNTI-VALUE-STOP
-- TAG-SHORTMAC-I-START
ShortMAC-I ::= BIT STRING  (SIZE (16))

-- TAG-SHORTMAC-I-STOP
-- TAG-SINR-RANGE-START
SINR-Range ::= INTEGER (0..127)

-- TAG-SI-SCHEDULINGINFO-STOP
-- TAG-SKCOUNTER-START
SK-Counter ::= INTEGER (0..65535)

SlotFormatCombinationId ::= INTEGER (0..maxNrofSlotFormatCombinationsPerSet-1)

-- TAG-SPS-CONFIG-STOP
-- TAG-SRB-IDENTITY-START
SRB-Identity ::= INTEGER (1..3)

SRS-ResourceSetId ::= INTEGER (0..maxNrofSRS-ResourceSets-1)

SRS-ResourceId ::= INTEGER (0..maxNrofSRS-Resources-1)

-- TAG-SRS-TPC-COMMANDCONFIG-STOP
-- TAG-SSB-INDEX-START
SSB-Index ::= INTEGER (0..maxNrofSSBs-1)

-- TAG-SS-RSSI-MEASUREMENT-STOP
-- TAG-SUBCARRIERSPACING-START
SubcarrierSpacing ::= ENUMERATED { kHz15(0), kHz30(1), kHz60(2), kHz120(3), 
   kHz240(4), spare3(5), spare2(6), spare1(7) }

TAG-Id ::= INTEGER (0..maxNrofTAGs-1)

TimeAlignmentTimer ::= ENUMERATED { ms500(0), ms750(1), ms1280(2), ms1920(3), 
   ms2560(4), ms5120(5), ms10240(6), infinity(7) }

-- TAG-TCI-STATE-STOP
-- TAG-TCI-STATEID-START
TCI-StateId ::= INTEGER (0..maxNrofTCI-States-1)

TDD-UL-DL-SlotIndex ::= INTEGER (0..maxNrofSlots-1)

-- TAG-TDD-UL-DL-CONFIGDEDICATED-STOP
-- TAG-TRACKINGAREACODE-START
TrackingAreaCode ::= BIT STRING  (SIZE (24))

-- TAG-TRACKINGAREACODE-STOP
-- TAG-TRESELECTION-START
T-Reselection ::= INTEGER (0..7)

-- TAG-TRESELECTION-STOP
-- TAG-TIMETOTRIGGER-START
TimeToTrigger ::= ENUMERATED { ms0(0), ms40(1), ms64(2), ms80(3), ms100(4), 
   ms128(5), ms160(6), ms256(7), ms320(8), ms480(9), ms512(10), ms640(11), 
   ms1024(12), ms1280(13), ms2560(14), ms5120(15) }

-- TAG-TIMETOTRIGGER-STOP
-- TAG-UAC-BARRINGINFOSETINDEX-START
UAC-BarringInfoSetIndex ::= INTEGER (1..maxBarringInfoSet)

ZP-CSI-RS-ResourceId ::= INTEGER (0..maxNrofZP-CSI-RS-Resources-1)

-- TAG-ZP-CSI-RS-RESOURCESET-STOP
-- TAG-ZP-CSI-RS-RESOURCESETID-START
ZP-CSI-RS-ResourceSetId ::= INTEGER (0..maxNrofZP-CSI-RS-ResourceSets-1)

-- TAG-ZP-CSI-RS-RESOURCESETID-STOP
-- TAG-ACCESSSTRATUMRELEASE-START
AccessStratumRelease ::= ENUMERATED { rel15(0), spare7(1), spare6(2), spare5(3)
   , spare4(4), spare3(5), spare2(6), spare1(7), ... }

-- TAG-BANDCOMBINATIONLIST-STOP
-- TAG-CA-BANDWIDTHCLASSEUTRA-START
CA-BandwidthClassEUTRA ::= ENUMERATED { a(0), b(1), c(2), d(3), e(4), f(5), ...
    }

-- TAG-CA-BANDWIDTHCLASSEUTRA-STOP
-- TAG-CA-BANDWIDTHCLASSNR-START
CA-BandwidthClassNR ::= ENUMERATED { a(0), b(1), c(2), d(3), e(4), f(5), g(6), 
   h(7), i(8), j(9), k(10), l(11), m(12), n(13), o(14), p(15), q(16), ... }

-- TAG-FEATURESETCOMBINATION-STOP
-- TAG-FEATURESETCOMBINATIONID-START
FeatureSetCombinationId ::= INTEGER (0..maxFeatureSetCombinations)

-- TAG-FEATURESETDOWNLINK-STOP
-- TAG-FEATURESETDOWNLINKID-START
FeatureSetDownlinkId ::= INTEGER (0..maxDownlinkFeatureSets)

-- TAG-FEATURESETDOWNLINKPERCC-STOP
-- TAG-FEATURESETDOWNLINKPERCC-ID-START
FeatureSetDownlinkPerCC-Id ::= INTEGER (1..maxPerCC-FeatureSets)

-- TAG-FEATURESETDOWNLINKPERCC-ID-STOP
-- TAG-FEATURESETEUTRADOWNLINKID-START
FeatureSetEUTRA-DownlinkId ::= INTEGER (0..maxEUTRA-DL-FeatureSets)

-- TAG-FEATURESETEUTRADOWNLINKID-STOP
-- TAG-FEATURESETEUTRAUPLINKID-START
FeatureSetEUTRA-UplinkId ::= INTEGER (0..maxEUTRA-UL-FeatureSets)

-- TAG-FEATURESETUPLINK-STOP
-- TAG-FEATURESETUPLINKID-START
FeatureSetUplinkId ::= INTEGER (0..maxUplinkFeatureSets)

-- TAG-FEATURESETUPLINKPERCC-STOP
-- TAG-FEATURESETUPLINKPERCC-ID-START
FeatureSetUplinkPerCC-Id ::= INTEGER (1..maxPerCC-FeatureSets)

-- TAG-FEATURESETUPLINKPERCC-ID-STOP
-- TAG-FREQBANDINDICATOREUTRA-START
FreqBandIndicatorEUTRA ::= INTEGER (1..maxBandsEUTRA)

AggregatedBandwidth ::= ENUMERATED { mhz50(0), mhz100(1), mhz150(2), mhz200(3)
   , mhz250(4), mhz300(5), mhz350(6), mhz400(7), mhz450(8), mhz500(9), 
   mhz550(10), mhz600(11), mhz650(12), mhz700(13), mhz750(14), mhz800(15) }

-- TAG-FREQBANDLIST-STOP
-- TAG-FREQSEPARATIONCLASS-START
FreqSeparationClass ::= ENUMERATED { c1(0), c2(1), c3(2), ... }

-- TAG-MEASANDMOBPARAMETERSMRDC-STOP
-- TAG-MIMO-LAYERS-START
MIMO-LayersDL ::= ENUMERATED { twoLayers(0), fourLayers(1), eightLayers(2) }

MIMO-LayersUL ::= ENUMERATED { oneLayer(0), twoLayers(1), fourLayers(2) }

-- TAG-MIMO-PARAMETERSPERBAND-STOP
-- TAG-MODULATIONORDER-START
ModulationOrder ::= ENUMERATED { bpsk-halfpi(0), bpsk(1), qpsk(2), qam16(3), 
   qam64(4), qam256(5) }

NumberOfCarriers ::= INTEGER (1..16)

-- TAG-PROCESSINGPARAMETERS-STOP
-- TAG-RAT-TYPE-START
RAT-Type ::= ENUMERATED { nr(0), eutra-nr(1), eutra(2), spare1(3), ... }

-- TAG-UE-NR-CAPABILITY-STOP
-- TAG-EUTRA-ALLOWEDMEASBANDWIDTH-START
EUTRA-AllowedMeasBandwidth ::= ENUMERATED { mbw6(0), mbw15(1), mbw25(2), 
   mbw50(3), mbw75(4), mbw100(5) }

-- TAG-EUTRA-NS-PMAXLIST-STOP
-- TAG-EUTRA-PHYSCELLID-START
EUTRA-PhysCellId ::= INTEGER (0..503)

-- TAG-EUTRA-PHYSCELLIDRANGE-STOP
-- TAG-EUTRA-PRESENCEANTENNAPORT1-START
EUTRA-PresenceAntennaPort1 ::= BOOLEAN

-- TAG-EUTRA-PRESENCEANTENNAPORT1-STOP
-- TAG-EUTRA-Q-OFFSETRANGE-START
EUTRA-Q-OffsetRange ::= ENUMERATED { dB-24(0), dB-22(1), dB-20(2), dB-18(3), 
   dB-16(4), dB-14(5), dB-12(6), dB-10(7), dB-8(8), dB-6(9), dB-5(10), dB-4(11)
   , dB-3(12), dB-2(13), dB-1(14), dB0(15), dB1(16), dB2(17), dB3(18), dB4(19)
   , dB5(20), dB6(21), dB8(22), dB10(23), dB12(24), dB14(25), dB16(26), 
   dB18(27), dB20(28), dB22(29), dB24(30) }

-- TAG-OTHERCONFIG-STOP
-- TAG-RRC-TRANSACTIONIDENTIFIER-START
RRC-TransactionIdentifier ::= INTEGER (0..3)

-- TAG-PDCCH-CONFIGCOMMON-STOP
-- TAG-PDCCH-CONFIGSIB1-START
PDCCH-ConfigSIB1 ::= SEQUENCE {
   controlResourceSetZero [0] ControlResourceSetZero,
   searchSpaceZero [1] SearchSpaceZero
}

-- TAG-MEASUREMENTREPORT-STOP
-- TAG-MIB-START
MIB ::= SEQUENCE {
   systemFrameNumber [0] BIT STRING  (SIZE (6)),
   subCarrierSpacingCommon [1] ENUMERATED { scs15or60(0), scs30or120(1) },
   ssb-SubcarrierOffset [2] INTEGER (0..15),
   dmrs-TypeA-Position [3] ENUMERATED { pos2(0), pos3(1) },
   pdcch-ConfigSIB1 [4] PDCCH-ConfigSIB1,
   cellBarred [5] ENUMERATED { barred(0), notBarred(1) },
   intraFreqReselection [6] ENUMERATED { allowed(0), notAllowed(1) },
   spare [7] BIT STRING  (SIZE (1))
}

BCCH-BCH-MessageType ::= CHOICE {
   mib [0] MIB,
   messageClassExtension [1] SEQUENCE {

   }
}

-- TAG-NR-RRC-DEFINITIONS-STOP
-- TAG-BCCH-BCH-MESSAGE-START
BCCH-BCH-Message ::= SEQUENCE {
   message [0] EXPLICIT BCCH-BCH-MessageType
}

ThresholdNR ::= SEQUENCE {
   thresholdRSRP [0] RSRP-Range OPTIONAL, -- Need R
   thresholdRSRQ [1] RSRQ-Range OPTIONAL, -- Need R
   thresholdSINR [2] SINR-Range OPTIONAL -- Need R
}

-- TAG-MEASTRIGGERQUANTITYEUTRA-STOP
-- TAG-MOBILITYSTATEPARAMETERS-START
MobilityStateParameters ::= SEQUENCE {
   t-Evaluation [0] ENUMERATED { s30(0), s60(1), s120(2), s180(3), s240(4), 
      spare3(5), spare2(6), spare1(7) },
   t-HystNormal [1] ENUMERATED { s30(0), s60(1), s120(2), s180(3), s240(4), 
      spare3(5), spare2(6), spare1(7) },
   n-CellChangeMedium [2] INTEGER (1..16),
   n-CellChangeHigh [3] INTEGER (1..16)
}

NR-NS-PmaxValue ::= SEQUENCE {
   additionalPmax [0] P-Max OPTIONAL, -- Need N
   additionalSpectrumEmission [1] AdditionalSpectrumEmission
}

-- TAG-NG-5G-S-TMSI-STOP
-- TAG-NR-NS-PMAXLIST-START
NR-NS-PmaxList ::= SEQUENCE (SIZE (1..maxNR-NS-Pmax)) OF NR-NS-PmaxValue

NR-MultiBandInfo ::= SEQUENCE {
   freqBandIndicatorNR [0] FreqBandIndicatorNR OPTIONAL, -- Cond OptULNotSIB2
   nr-NS-PmaxList [1] NR-NS-PmaxList OPTIONAL -- Need S
}

-- TAG-MULTIFREQUENCYBANDLISTNR-STOP
-- TAG-MULTIFREQUENCYBANDLISTNR-SIB-START
MultiFrequencyBandListNR-SIB ::= SEQUENCE (SIZE (1..maxNrofMultiBands)) OF NR-MultiBandInfo

-- TAG-SSB-INDEX-STOP
-- TAG-SSB-MTC-START
SSB-MTC ::= SEQUENCE {
   periodicityAndOffset [0] EXPLICIT CHOICE {
      sf5 [0] INTEGER (0..4),
      sf10 [1] INTEGER (0..9),
      sf20 [2] INTEGER (0..19),
      sf40 [3] INTEGER (0..39),
      sf80 [4] INTEGER (0..79),
      sf160 [5] INTEGER (0..159)
   },
   duration [1] ENUMERATED { sf1(0), sf2(1), sf3(2), sf4(3), sf5(4) }
}

-- TAG-SSB-TOMEASURE-STOP
-- TAG-SS-RSSI-MEASUREMENT-START
SS-RSSI-Measurement ::= SEQUENCE {
   measurementSlots [0] BIT STRING  (SIZE (1..80)),
   endSymbol [1] INTEGER (0..3)
}

-- TAG-SSB-MTC-STOP
-- TAG-SSB-TOMEASURE-START
SSB-ToMeasure ::= CHOICE {
   shortBitmap [0] BIT STRING  (SIZE (4)),
   mediumBitmap [1] BIT STRING  (SIZE (8)),
   longBitmap [2] BIT STRING  (SIZE (64))
}

-- TAG-S-NSSAI-STOP
-- TAG-SPEEDSTATESCALEFACTORS-START
SpeedStateScaleFactors ::= SEQUENCE {
   sf-Medium [0] ENUMERATED { oDot25(0), oDot5(1), oDot75(2), lDot0(3) },
   sf-High [1] ENUMERATED { oDot25(0), oDot5(1), oDot75(2), lDot0(3) }
}

-- TAG-SETUPRELEASE-STOP
-- TAG-SIB2-START
SIB2 ::= SEQUENCE {
   cellReselectionInfoCommon [0] SEQUENCE {
      nrofSS-BlocksToAverage [0] INTEGER (2..maxNrofSS-BlocksToAverage) OPTIONAL, -- Need S
      absThreshSS-BlocksConsolidation [1] ThresholdNR OPTIONAL, -- Need S
      rangeToBestCell [2] RangeToBestCell OPTIONAL, -- Need R
      q-Hyst [3] ENUMERATED { dB0(0), dB1(1), dB2(2), dB3(3), dB4(4), dB5(5), 
         dB6(6), dB8(7), dB10(8), dB12(9), dB14(10), dB16(11), dB18(12), 
         dB20(13), dB22(14), dB24(15) },
      speedStateReselectionPars [4] SEQUENCE {
         mobilityStateParameters [0] MobilityStateParameters,
         q-HystSF [1] SEQUENCE {
            sf-Medium [0] ENUMERATED { dB-6(0), dB-4(1), dB-2(2), dB0(3) },
            sf-High [1] ENUMERATED { dB-6(0), dB-4(1), dB-2(2), dB0(3) }
         }
      } OPTIONAL,
      ...
   },
   cellReselectionServingFreqInfo [1] SEQUENCE {
      s-NonIntraSearchP [0] ReselectionThreshold OPTIONAL, -- Need S
      s-NonIntraSearchQ [1] ReselectionThresholdQ OPTIONAL, -- Need S
      threshServingLowP [2] ReselectionThreshold,
      threshServingLowQ [3] ReselectionThresholdQ OPTIONAL, -- Need R
      cellReselectionPriority [4] CellReselectionPriority,
      cellReselectionSubPriority [5] CellReselectionSubPriority OPTIONAL,
      ...
   },
   intraFreqCellReselectionInfo [2] SEQUENCE {
      q-RxLevMin [0] Q-RxLevMin,
      q-RxLevMinSUL [1] Q-RxLevMin OPTIONAL, -- Need R
      q-QualMin [2] Q-QualMin OPTIONAL, -- Need S
      s-IntraSearchP [3] ReselectionThreshold,
      s-IntraSearchQ [4] ReselectionThresholdQ OPTIONAL, -- Need S
      t-ReselectionNR [5] T-Reselection,
      frequencyBandList [6] MultiFrequencyBandListNR-SIB OPTIONAL, -- Need S
      frequencyBandListSUL [7] MultiFrequencyBandListNR-SIB OPTIONAL, -- Need R
      p-Max [8] P-Max OPTIONAL, -- Need S
      smtc [9] SSB-MTC OPTIONAL, -- Need S
      ss-RSSI-Measurement [10] SS-RSSI-Measurement OPTIONAL, -- Need R
      ssb-ToMeasure [11] EXPLICIT SSB-ToMeasure OPTIONAL, -- Need S
      deriveSSB-IndexFromCell [12] BOOLEAN,
      ...,
      [[
         t-ReselectionNR-SF [13] SpeedStateScaleFactors OPTIONAL
      ]]
   },
   ...
}

IntraFreqNeighCellInfo ::= SEQUENCE {
   physCellId [0] PhysCellId,
   q-OffsetCell [1] Q-OffsetRange,
   q-RxLevMinOffsetCell [2] INTEGER (1..8) OPTIONAL, -- Need R
   q-RxLevMinOffsetCellSUL [3] INTEGER (1..8) OPTIONAL, -- Need R
   q-QualMinOffsetCell [4] INTEGER (1..8) OPTIONAL,
   ...
}

IntraFreqNeighCellList ::= SEQUENCE (SIZE (1..maxCellIntra)) OF IntraFreqNeighCellInfo

-- TAG-PCI-LIST-STOP
-- TAG-PCI-RANGE-START
PCI-Range ::= SEQUENCE {
   start [0] PhysCellId,
   range [1] ENUMERATED { n4(0), n8(1), n12(2), n16(3), n24(4), n32(5), n48(6)
      , n64(7), n84(8), n96(9), n128(10), n168(11), n252(12), n504(13), 
      n1008(14), spare1(15) } OPTIONAL -- Need S
}

IntraFreqBlackCellList ::= SEQUENCE (SIZE (1..maxCellBlack)) OF PCI-Range

-- TAG-SIB2-STOP
-- TAG-SIB3-START
SIB3 ::= SEQUENCE {
   intraFreqNeighCellList [0] IntraFreqNeighCellList OPTIONAL, -- Need R
   intraFreqBlackCellList [1] IntraFreqBlackCellList OPTIONAL, -- Need R
   lateNonCriticalExtension [2] OCTET STRING OPTIONAL,
   ...
}

InterFreqNeighCellInfo ::= SEQUENCE {
   physCellId [0] PhysCellId,
   q-OffsetCell [1] Q-OffsetRange,
   q-RxLevMinOffsetCell [2] INTEGER (1..8) OPTIONAL, -- Need R
   q-RxLevMinOffsetCellSUL [3] INTEGER (1..8) OPTIONAL, -- Need R
   q-QualMinOffsetCell [4] INTEGER (1..8) OPTIONAL,
   ...
}

InterFreqNeighCellList ::= SEQUENCE (SIZE (1..maxCellInter)) OF InterFreqNeighCellInfo

InterFreqBlackCellList ::= SEQUENCE (SIZE (1..maxCellBlack)) OF PCI-Range

InterFreqCarrierFreqInfo ::= SEQUENCE {
   dl-CarrierFreq [0] ARFCN-ValueNR,
   frequencyBandList [1] MultiFrequencyBandListNR-SIB OPTIONAL, -- Cond Mandatory
   frequencyBandListSUL [2] MultiFrequencyBandListNR-SIB OPTIONAL, -- Need R
   nrofSS-BlocksToAverage [3] INTEGER (2..maxNrofSS-BlocksToAverage) OPTIONAL, -- Need S
   absThreshSS-BlocksConsolidation [4] ThresholdNR OPTIONAL, -- Need S
   smtc [5] SSB-MTC OPTIONAL, -- Need S
   ssbSubcarrierSpacing [6] SubcarrierSpacing,
   ssb-ToMeasure [7] EXPLICIT SSB-ToMeasure OPTIONAL, -- Need S
   deriveSSB-IndexFromCell [8] BOOLEAN,
   ss-RSSI-Measurement [9] SS-RSSI-Measurement OPTIONAL,
   q-RxLevMin [10] Q-RxLevMin,
   q-RxLevMinSUL [11] Q-RxLevMin OPTIONAL, -- Need R
   q-QualMin [12] Q-QualMin OPTIONAL, -- Need S
   p-Max [13] P-Max OPTIONAL, -- Need S
   t-ReselectionNR [14] T-Reselection,
   t-ReselectionNR-SF [15] SpeedStateScaleFactors OPTIONAL, -- Need S
   threshX-HighP [16] ReselectionThreshold,
   threshX-LowP [17] ReselectionThreshold,
   threshX-Q [18] SEQUENCE {
      threshX-HighQ [0] ReselectionThresholdQ,
      threshX-LowQ [1] ReselectionThresholdQ
   } OPTIONAL, -- Cond RSRQ
   cellReselectionPriority [19] CellReselectionPriority OPTIONAL, -- Need R
   cellReselectionSubPriority [20] CellReselectionSubPriority OPTIONAL, -- Need R
   q-OffsetFreq [21] Q-OffsetRange DEFAULT dB0,
   interFreqNeighCellList [22] InterFreqNeighCellList OPTIONAL, -- Need R
   interFreqBlackCellList [23] InterFreqBlackCellList OPTIONAL,
   ...
}

InterFreqCarrierFreqList ::= SEQUENCE (SIZE (1..maxFreq)) OF InterFreqCarrierFreqInfo

-- TAG-SIB3-STOP
-- TAG-SIB4-START
SIB4 ::= SEQUENCE {
   interFreqCarrierFreqList [0] InterFreqCarrierFreqList,
   lateNonCriticalExtension [1] OCTET STRING OPTIONAL,
   ...
}

EUTRA-NS-PmaxValue ::= SEQUENCE {
   additionalPmax [0] INTEGER (-30..33) OPTIONAL, -- Need R
   additionalSpectrumEmission [1] INTEGER (1..288) OPTIONAL -- Need R
}

-- TAG-EUTRA-MULTIBANDINFOLIST-STOP
-- TAG-EUTRA-NS-PMAXLIST-START
EUTRA-NS-PmaxList ::= SEQUENCE (SIZE (1..maxEUTRA-NS-Pmax)) OF EUTRA-NS-PmaxValue

EUTRA-MultiBandInfo ::= SEQUENCE {
   eutra-FreqBandIndicator [0] FreqBandIndicatorEUTRA,
   eutra-NS-PmaxList [1] EUTRA-NS-PmaxList OPTIONAL -- Need R
}

-- TAG-EUTRA-MBSFN-SUBFRAMECONFIGLIST-STOP
-- TAG-EUTRA-MULTIBANDINFOLIST-START
EUTRA-MultiBandInfoList ::= SEQUENCE (SIZE (1..maxMultiBands)) OF EUTRA-MultiBandInfo

EUTRA-FreqNeighCellInfo ::= SEQUENCE {
   physCellId [0] EUTRA-PhysCellId,
   dummy [1] EUTRA-Q-OffsetRange,
   q-RxLevMinOffsetCell [2] INTEGER (1..8) OPTIONAL, -- Need R
   q-QualMinOffsetCell [3] INTEGER (1..8) OPTIONAL -- Need R
}

EUTRA-FreqNeighCellList ::= SEQUENCE (SIZE (1..maxCellEUTRA)) OF EUTRA-FreqNeighCellInfo

-- TAG-EUTRA-PHYSCELLID-STOP
-- TAG-EUTRA-PHYSCELLIDRANGE-START
EUTRA-PhysCellIdRange ::= SEQUENCE {
   start [0] EUTRA-PhysCellId,
   range [1] ENUMERATED { n4(0), n8(1), n12(2), n16(3), n24(4), n32(5), n48(6)
      , n64(7), n84(8), n96(9), n128(10), n168(11), n252(12), n504(13), 
      spare2(14), spare1(15) } OPTIONAL -- Need N
}

EUTRA-FreqBlackCellList ::= SEQUENCE (SIZE (1..maxEUTRA-CellBlack)) OF EUTRA-PhysCellIdRange

CarrierFreqEUTRA ::= SEQUENCE {
   carrierFreq [0] ARFCN-ValueEUTRA,
   eutra-multiBandInfoList [1] EUTRA-MultiBandInfoList OPTIONAL, -- Need R
   eutra-FreqNeighCellList [2] EUTRA-FreqNeighCellList OPTIONAL, -- Need R
   eutra-BlackCellList [3] EUTRA-FreqBlackCellList OPTIONAL, -- Need R
   allowedMeasBandwidth [4] EUTRA-AllowedMeasBandwidth,
   presenceAntennaPort1 [5] EUTRA-PresenceAntennaPort1,
   cellReselectionPriority [6] CellReselectionPriority OPTIONAL, -- Need R
   cellReselectionSubPriority [7] CellReselectionSubPriority OPTIONAL, -- Need R
   threshX-High [8] ReselectionThreshold,
   threshX-Low [9] ReselectionThreshold,
   q-RxLevMin [10] INTEGER (-70..-22),
   q-QualMin [11] INTEGER (-34..-3),
   p-MaxEUTRA [12] INTEGER (-30..33),
   threshX-Q [13] SEQUENCE {
      threshX-HighQ [0] ReselectionThresholdQ,
      threshX-LowQ [1] ReselectionThresholdQ
   } OPTIONAL -- Cond RSRQ
}

CarrierFreqListEUTRA ::= SEQUENCE (SIZE (1..maxEUTRA-Carrier)) OF CarrierFreqEUTRA

-- TAG-SIB4-STOP
-- TAG-SIB5-START
SIB5 ::= SEQUENCE {
   carrierFreqListEUTRA [0] CarrierFreqListEUTRA OPTIONAL, -- Need R
   t-ReselectionEUTRA [1] T-Reselection,
   t-ReselectionEUTRA-SF [2] SpeedStateScaleFactors OPTIONAL, -- Need S
   lateNonCriticalExtension [3] OCTET STRING OPTIONAL,
   ...
}

-- TAG-SIB5-STOP
-- TAG-SIB6-START
SIB6 ::= SEQUENCE {
   messageIdentifier [0] BIT STRING  (SIZE (16)),
   serialNumber [1] BIT STRING  (SIZE (16)),
   warningType [2] OCTET STRING (SIZE (2)),
   lateNonCriticalExtension [3] OCTET STRING OPTIONAL,
   ...
}

-- TAG-SIB6-STOP
-- TAG-SIB7-START
SIB7 ::= SEQUENCE {
   messageIdentifier [0] BIT STRING  (SIZE (16)),
   serialNumber [1] BIT STRING  (SIZE (16)),
   warningMessageSegmentType [2] ENUMERATED { notLastSegment(0), lastSegment(1)
       },
   warningMessageSegmentNumber [3] INTEGER (0..63),
   warningMessageSegment [4] OCTET STRING,
   dataCodingScheme [5] OCTET STRING (SIZE (1)) OPTIONAL, -- Cond Segment1
   lateNonCriticalExtension [6] OCTET STRING OPTIONAL,
   ...
}

-- TAG-SIB7-STOP
-- TAG-SIB8-START
SIB8 ::= SEQUENCE {
   messageIdentifier [0] BIT STRING  (SIZE (16)),
   serialNumber [1] BIT STRING  (SIZE (16)),
   warningMessageSegmentType [2] ENUMERATED { notLastSegment(0), lastSegment(1)
       },
   warningMessageSegmentNumber [3] INTEGER (0..63),
   warningMessageSegment [4] OCTET STRING,
   dataCodingScheme [5] OCTET STRING (SIZE (1)) OPTIONAL, -- Cond Segment1
   warningAreaCoordinatesSegment [6] OCTET STRING OPTIONAL, -- Need R
   lateNonCriticalExtension [7] OCTET STRING OPTIONAL,
   ...
}

-- TAG-SIB8-STOP
-- TAG-SIB9-START
SIB9 ::= SEQUENCE {
   timeInfo [0] SEQUENCE {
      timeInfoUTC [0] INTEGER (0..549755813887),
      dayLightSavingTime [1] BIT STRING  (SIZE (2)) OPTIONAL, -- Need R
      leapSeconds [2] INTEGER (-127..128) OPTIONAL, -- Need R
      localTimeOffset [3] INTEGER (-63..64) OPTIONAL -- Need R
   } OPTIONAL, -- Need R
   lateNonCriticalExtension [1] OCTET STRING OPTIONAL,
   ...
}

SystemInformation-IEs ::= SEQUENCE {
   sib-TypeAndInfo [0] SEQUENCE (SIZE (1..maxSIB)) OF CHOICE {
      sib2 [0] SIB2,
      sib3 [1] SIB3,
      sib4 [2] SIB4,
      sib5 [3] SIB5,
      sib6 [4] SIB6,
      sib7 [5] SIB7,
      sib8 [6] SIB8,
      sib9 [7] SIB9,
      ...
   },
   lateNonCriticalExtension [1] OCTET STRING OPTIONAL,
   nonCriticalExtension [2] SEQUENCE {

   } OPTIONAL
}

-- TAG-SIB1-STOP
-- TAG-SYSTEMINFORMATION-START
SystemInformation ::= SEQUENCE {
   criticalExtensions [0] EXPLICIT CHOICE {
      systemInformation [0] SystemInformation-IEs,
      criticalExtensionsFuture [1] SEQUENCE {

      }
   }
}

MCC ::= SEQUENCE (SIZE (3)) OF MCC-MNC-Digit

MNC ::= SEQUENCE (SIZE (2..3)) OF MCC-MNC-Digit

-- TAG-PHYSICALCELLGROUPCONFIG-STOP
-- TAG-PLMN-IDENTITY-START
PLMN-Identity ::= SEQUENCE {
   mcc [0] MCC OPTIONAL, -- Cond MCC
   mnc [1] MNC
}

PLMN-IdentityInfo ::= SEQUENCE {
   plmn-IdentityList [0] SEQUENCE (SIZE (1..maxPLMN)) OF PLMN-Identity,
   trackingAreaCode [1] TrackingAreaCode OPTIONAL, -- Need R
   ranac [2] RAN-AreaCode OPTIONAL, -- Need R
   cellIdentity [3] CellIdentity,
   cellReservedForOperatorUse [4] ENUMERATED { reserved(0), notReserved(1) },
   ...
}

-- TAG-PLMN-IDENTITY-STOP
-- TAG-PLMN-IDENTITYINFOLIST-START
PLMN-IdentityInfoList ::= SEQUENCE (SIZE (1..maxPLMN)) OF PLMN-IdentityInfo

-- TAG-BWP-UPLINKDEDICATED-STOP
-- TAG-CELLACCESSRELATEDINFO-START
CellAccessRelatedInfo ::= SEQUENCE {
   plmn-IdentityList [0] PLMN-IdentityInfoList,
   cellReservedForOtherUse [1] ENUMERATED { true(0) } OPTIONAL,
   ...
}

-- TAG-CONFIGUREDGRANTCONFIG-STOP
-- TAG-CONNESTFAILURECONTROL-START
ConnEstFailureControl ::= SEQUENCE {
   connEstFailCount [0] ENUMERATED { n1(0), n2(1), n3(2), n4(3) },
   connEstFailOffsetValidity [1] ENUMERATED { s30(0), s60(1), s120(2), s240(3)
      , s300(4), s420(5), s600(6), s900(7) },
   connEstFailOffset [2] INTEGER (0..15) OPTIONAL -- Need S
}

SIB-TypeInfo ::= SEQUENCE {
   type [0] ENUMERATED { sibType2(0), sibType3(1), sibType4(2), sibType5(3), 
      sibType6(4), sibType7(5), sibType8(6), sibType9(7), spare8(8), spare7(9)
      , spare6(10), spare5(11), spare4(12), spare3(13), spare2(14), spare1(15)
      , ... },
   valueTag [1] INTEGER (0..31) OPTIONAL, -- Cond SIB-TYPE
   areaScope [2] ENUMERATED { true(0) } OPTIONAL -- Need S
}

SIB-Mapping ::= SEQUENCE (SIZE (1..maxSIB)) OF SIB-TypeInfo

SchedulingInfo ::= SEQUENCE {
   si-BroadcastStatus [0] ENUMERATED { broadcasting(0), notBroadcasting(1) },
   si-Periodicity [1] ENUMERATED { rf8(0), rf16(1), rf32(2), rf64(3), rf128(4)
      , rf256(5), rf512(6) },
   sib-MappingInfo [2] SIB-Mapping
}

-- TAG-RACH-CONFIGDEDICATED-STOP
-- TAG-RACH-CONFIGGENERIC-START
RACH-ConfigGeneric ::= SEQUENCE {
   prach-ConfigurationIndex [0] INTEGER (0..255),
   msg1-FDM [1] ENUMERATED { one(0), two(1), four(2), eight(3) },
   msg1-FrequencyStart [2] INTEGER (0..maxNrofPhysicalResourceBlocks-1),
   zeroCorrelationZoneConfig [3] INTEGER (0..15),
   preambleReceivedTargetPower [4] INTEGER (-202..-60),
   preambleTransMax [5] ENUMERATED { n3(0), n4(1), n5(2), n6(3), n7(4), n8(5), 
      n10(6), n20(7), n50(8), n100(9), n200(10) },
   powerRampingStep [6] ENUMERATED { dB0(0), dB2(1), dB4(2), dB6(3) },
   ra-ResponseWindow [7] ENUMERATED { sl1(0), sl2(1), sl4(2), sl8(3), sl10(4), 
      sl20(5), sl40(6), sl80(7) },
   ...
}

SI-RequestResources ::= SEQUENCE {
   ra-PreambleStartIndex [0] INTEGER (0..63),
   ra-AssociationPeriodIndex [1] INTEGER (0..15) OPTIONAL, -- Need R
   ra-ssb-OccasionMaskIndex [2] INTEGER (0..15) OPTIONAL -- Need R
}

-- Configuration for Msg1 based SI Request
SI-RequestConfig ::= SEQUENCE {
   rach-OccasionsSI [0] SEQUENCE {
      rach-ConfigSI [0] RACH-ConfigGeneric,
      ssb-perRACH-Occasion [1] ENUMERATED { oneEighth(0), oneFourth(1), 
         oneHalf(2), one(3), two(4), four(5), eight(6), sixteen(7) }
   } OPTIONAL, -- Need R
   si-RequestPeriod [1] ENUMERATED { one(0), two(1), four(2), six(3), eight(4)
      , ten(5), twelve(6), sixteen(7) } OPTIONAL, -- Need R
   si-RequestResources [2] SEQUENCE (SIZE (1..maxSI-Message)) OF SI-RequestResources
}

-- TAG-SINR-RANGE-STOP
-- TAG–SI-SCHEDULINGINFO-START
SI-SchedulingInfo ::= SEQUENCE {
   schedulingInfoList [0] SEQUENCE (SIZE (1..maxSI-Message)) OF SchedulingInfo,
   si-WindowLength [1] ENUMERATED { s5(0), s10(1), s20(2), s40(3), s80(4), 
      s160(5), s320(6), s640(7), s1280(8) },
   si-RequestConfig [2] SI-RequestConfig OPTIONAL, -- Cond MSG-1
   si-RequestConfigSUL [3] SI-RequestConfig OPTIONAL, -- Cond SUL-MSG-1
   systemInformationAreaID [4] BIT STRING  (SIZE (24)) OPTIONAL,
   ...
}

-- TAG-SCRAMBLINGID-STOP
-- TAG-SCS-SPECIFICCARRIER-START
SCS-SpecificCarrier ::= SEQUENCE {
   offsetToCarrier [0] INTEGER (0..2199),
   subcarrierSpacing [1] SubcarrierSpacing,
   carrierBandwidth [2] INTEGER (1..maxNrofPhysicalResourceBlocks),
   ...,
   [[
      txDirectCurrentLocation [3] INTEGER (0..4095) OPTIONAL
   ]]
}

-- TAG-FREQUENCYINFODL-STOP
-- TAG-FREQUENCYINFODL-SIB-START
FrequencyInfoDL-SIB ::= SEQUENCE {
   frequencyBandList [0] MultiFrequencyBandListNR-SIB,
   offsetToPointA [1] INTEGER (0..2199),
   scs-SpecificCarrierList [2] SEQUENCE (SIZE (1..maxSCSs)) OF SCS-SpecificCarrier
}

-- TAG-BSR-CONFIG-STOP
-- TAG-BWP-START
BWP ::= SEQUENCE {
   locationAndBandwidth [0] INTEGER (0..37949),
   subcarrierSpacing [1] SubcarrierSpacing,
   cyclicPrefix [2] ENUMERATED { extended(0) } OPTIONAL -- Need R
}

-- TAG-CONNESTFAILURECONTROL-STOP
-- TAG-CONTROLRESOURCESET-START
ControlResourceSet ::= SEQUENCE {
   controlResourceSetId [0] ControlResourceSetId,
   frequencyDomainResources [1] BIT STRING  (SIZE (45)),
   duration [2] INTEGER (1..maxCoReSetDuration),
   cce-REG-MappingType [3] EXPLICIT CHOICE {
      interleaved [0] SEQUENCE {
         reg-BundleSize [0] ENUMERATED { n2(0), n3(1), n6(2) },
         interleaverSize [1] ENUMERATED { n2(0), n3(1), n6(2) },
         shiftIndex [2] INTEGER (0..maxNrofPhysicalResourceBlocks-1) OPTIONAL -- Need S
      },
      nonInterleaved [1] NULL
   },
   precoderGranularity [4] ENUMERATED { sameAsREG-bundle(0), 
      allContiguousRBs(1) },
   tci-StatesPDCCH-ToAddList [5] SEQUENCE (SIZE (1..maxNrofTCI-StatesPDCCH)) OF TCI-StateId OPTIONAL, -- Cond NotSIB1-initialBWP
   tci-StatesPDCCH-ToReleaseList [6] SEQUENCE (SIZE (1..maxNrofTCI-StatesPDCCH)) OF TCI-StateId
       OPTIONAL, -- Cond NotSIB1-initialBWP
   tci-PresentInDCI [7] ENUMERATED { enabled(0) } OPTIONAL, -- Need S
   pdcch-DMRS-ScramblingID [8] INTEGER (0..65535) OPTIONAL,
   ...
}

-- TAG-SDAP-CONFIG-STOP
-- TAG-SEARCHSPACE-START
SearchSpace ::= SEQUENCE {
   searchSpaceId [0] SearchSpaceId,
   controlResourceSetId [1] ControlResourceSetId OPTIONAL, -- Cond SetupOnly
   monitoringSlotPeriodicityAndOffset [2] EXPLICIT CHOICE {
      sl1 [0] NULL,
      sl2 [1] INTEGER (0..1),
      sl4 [2] INTEGER (0..3),
      sl5 [3] INTEGER (0..4),
      sl8 [4] INTEGER (0..7),
      sl10 [5] INTEGER (0..9),
      sl16 [6] INTEGER (0..15),
      sl20 [7] INTEGER (0..19),
      sl40 [8] INTEGER (0..39),
      sl80 [9] INTEGER (0..79),
      sl160 [10] INTEGER (0..159),
      sl320 [11] INTEGER (0..319),
      sl640 [12] INTEGER (0..639),
      sl1280 [13] INTEGER (0..1279),
      sl2560 [14] INTEGER (0..2559)
   } OPTIONAL, -- Cond Setup
   duration [3] INTEGER (2..2559) OPTIONAL, -- Need R
   monitoringSymbolsWithinSlot [4] BIT STRING  (SIZE (14)) OPTIONAL, -- Cond Setup
   nrofCandidates [5] SEQUENCE {
      aggregationLevel1 [0] ENUMERATED { n0(0), n1(1), n2(2), n3(3), n4(4), 
         n5(5), n6(6), n8(7) },
      aggregationLevel2 [1] ENUMERATED { n0(0), n1(1), n2(2), n3(3), n4(4), 
         n5(5), n6(6), n8(7) },
      aggregationLevel4 [2] ENUMERATED { n0(0), n1(1), n2(2), n3(3), n4(4), 
         n5(5), n6(6), n8(7) },
      aggregationLevel8 [3] ENUMERATED { n0(0), n1(1), n2(2), n3(3), n4(4), 
         n5(5), n6(6), n8(7) },
      aggregationLevel16 [4] ENUMERATED { n0(0), n1(1), n2(2), n3(3), n4(4), 
         n5(5), n6(6), n8(7) }
   } OPTIONAL, -- Cond Setup
   searchSpaceType [6] EXPLICIT CHOICE {
      common [0] SEQUENCE {
         dci-Format0-0-AndFormat1-0 [0] SEQUENCE {

            ...
         } OPTIONAL, -- Need R
         dci-Format2-0 [1] SEQUENCE {
            nrofCandidates-SFI [0] SEQUENCE {
               aggregationLevel1 [0] ENUMERATED { n1(0), n2(1) } OPTIONAL, -- Need R
               aggregationLevel2 [1] ENUMERATED { n1(0), n2(1) } OPTIONAL, -- Need R
               aggregationLevel4 [2] ENUMERATED { n1(0), n2(1) } OPTIONAL, -- Need R
               aggregationLevel8 [3] ENUMERATED { n1(0), n2(1) } OPTIONAL, -- Need R
               aggregationLevel16 [4] ENUMERATED { n1(0), n2(1) } OPTIONAL -- Need R
            },
            ...
         } OPTIONAL, -- Need R
         dci-Format2-1 [2] SEQUENCE {

            ...
         } OPTIONAL, -- Need R
         dci-Format2-2 [3] SEQUENCE {

            ...
         } OPTIONAL, -- Need R
         dci-Format2-3 [4] SEQUENCE {
            dummy1 [0] ENUMERATED { sl1(0), sl2(1), sl4(2), sl5(3), sl8(4), 
               sl10(5), sl16(6), sl20(7) } OPTIONAL, -- Cond Setup
            dummy2 [1] ENUMERATED { n1(0), n2(1) },
            ...
         } OPTIONAL -- Need R
      },
      ue-Specific [1] SEQUENCE {
         dci-Formats [0] ENUMERATED { formats0-0-And-1-0(0), 
            formats0-1-And-1-1(1) },
         ...
      }
   } OPTIONAL -- Cond Setup
}

-- TAG-PDCCH-CONFIG-STOP
-- TAG-PDCCH-CONFIGCOMMON-START
PDCCH-ConfigCommon ::= SEQUENCE {
   controlResourceSetZero [0] ControlResourceSetZero OPTIONAL, -- Cond InitialBWP-Only
   commonControlResourceSet [1] ControlResourceSet OPTIONAL, -- Need R
   searchSpaceZero [2] SearchSpaceZero OPTIONAL, -- Cond InitialBWP-Only
   commonSearchSpaceList [3] SEQUENCE (SIZE (1..4)) OF SearchSpace OPTIONAL, -- Need R
   searchSpaceSIB1 [4] SearchSpaceId OPTIONAL, -- Need S
   searchSpaceOtherSystemInformation [5] SearchSpaceId OPTIONAL, -- Need S
   pagingSearchSpace [6] SearchSpaceId OPTIONAL, -- Need S
   ra-SearchSpace [7] SearchSpaceId OPTIONAL,
   ...,
   [[
      firstPDCCH-MonitoringOccasionOfPO [8] EXPLICIT CHOICE {
         sCS15KHZoneT [0] SEQUENCE (SIZE (1..maxPO-perPF)) OF INTEGER (0..139),
         sCS30KHZoneT-SCS15KHZhalfT [1] SEQUENCE (SIZE (1..maxPO-perPF)) OF INTEGER (0..279),
         sCS60KHZoneT-SCS30KHZhalfT-SCS15KHZquarterT [2] SEQUENCE (SIZE (1..maxPO-perPF)
            ) OF INTEGER (0..559),
         sCS120KHZoneT-SCS60KHZhalfT-SCS30KHZquarterT-SCS15KHZoneEighthT [3] 
            SEQUENCE (SIZE (1..maxPO-perPF)) OF INTEGER (0..1119),
         sCS120KHZhalfT-SCS60KHZquarterT-SCS30KHZoneEighthT-SCS15KHZoneSixteenthT 
            [4] SEQUENCE (SIZE (1..maxPO-perPF)) OF INTEGER (0..2239),
         sCS120KHZquarterT-SCS60KHZoneEighthT-SCS30KHZoneSixteenthT [5] 
            SEQUENCE (SIZE (1..maxPO-perPF)) OF INTEGER (0..4479),
         sCS120KHZoneEighthT-SCS60KHZoneSixteenthT [6] SEQUENCE (SIZE (1..maxPO-perPF)) OF 
            INTEGER (0..8959),
         sCS120KHZoneSixteenthT [7] SEQUENCE (SIZE (1..maxPO-perPF)) OF INTEGER (0..17919)
      } OPTIONAL
   ]]
}

PDSCH-TimeDomainResourceAllocation ::= SEQUENCE {
   k0 [0] INTEGER (0..32) OPTIONAL, -- Need S
   mappingType [1] ENUMERATED { typeA(0), typeB(1) },
   startSymbolAndLength [2] INTEGER (0..127)
}

-- TAG-PDSCH-SERVINGCELLCONFIG-STOP
-- TAG-PDSCH-TIMEDOMAINRESOURCEALLOCATIONLIST-START
PDSCH-TimeDomainResourceAllocationList ::= SEQUENCE (SIZE (1..maxNrofDL-Allocations)) OF 
   PDSCH-TimeDomainResourceAllocation

-- TAG-PDSCH-CONFIG-STOP
-- TAG-PDSCH-CONFIGCOMMON-START
PDSCH-ConfigCommon ::= SEQUENCE {
   pdsch-TimeDomainAllocationList [0] PDSCH-TimeDomainResourceAllocationList
       OPTIONAL,
   ...
}

-- TAG-BWP-DOWNLINK-STOP
-- TAG-BWP-DOWNLINKCOMMON-START
BWP-DownlinkCommon ::= SEQUENCE {
   genericParameters [0] BWP,
   pdcch-ConfigCommon [1] EXPLICIT CHOICE {
      release [0] NULL,
      setup [1] EXPLICIT PDCCH-ConfigCommon
   } OPTIONAL, -- Need M
   pdsch-ConfigCommon [2] EXPLICIT CHOICE {
      release [0] NULL,
      setup [1] EXPLICIT PDSCH-ConfigCommon
   } OPTIONAL,
   ...
}

BCCH-Config ::= SEQUENCE {
   modificationPeriodCoeff [0] ENUMERATED { n2(0), n4(1), n8(2), n16(3) },
   ...
}

PCCH-Config ::= SEQUENCE {
   defaultPagingCycle [0] PagingCycle,
   nAndPagingFrameOffset [1] EXPLICIT CHOICE {
      oneT [0] NULL,
      halfT [1] INTEGER (0..1),
      quarterT [2] INTEGER (0..3),
      oneEighthT [3] INTEGER (0..7),
      oneSixteenthT [4] INTEGER (0..15)
   },
   ns [2] ENUMERATED { four(0), two(1), one(2) },
   firstPDCCH-MonitoringOccasionOfPO [3] EXPLICIT CHOICE {
      sCS15KHZoneT [0] SEQUENCE (SIZE (1..maxPO-perPF)) OF INTEGER (0..139),
      sCS30KHZoneT-SCS15KHZhalfT [1] SEQUENCE (SIZE (1..maxPO-perPF)) OF INTEGER (0..279),
      sCS60KHZoneT-SCS30KHZhalfT-SCS15KHZquarterT [2] SEQUENCE (SIZE (1..maxPO-perPF)) OF 
         INTEGER (0..559),
      sCS120KHZoneT-SCS60KHZhalfT-SCS30KHZquarterT-SCS15KHZoneEighthT [3] 
         SEQUENCE (SIZE (1..maxPO-perPF)) OF INTEGER (0..1119),
      sCS120KHZhalfT-SCS60KHZquarterT-SCS30KHZoneEighthT-SCS15KHZoneSixteenthT 
         [4] SEQUENCE (SIZE (1..maxPO-perPF)) OF INTEGER (0..2239),
      sCS120KHZquarterT-SCS60KHZoneEighthT-SCS30KHZoneSixteenthT [5] SEQUENCE (
         SIZE (1..maxPO-perPF)) OF INTEGER (0..4479),
      sCS120KHZoneEighthT-SCS60KHZoneSixteenthT [6] SEQUENCE (SIZE (1..maxPO-perPF)) OF 
         INTEGER (0..8959),
      sCS120KHZoneSixteenthT [7] SEQUENCE (SIZE (1..maxPO-perPF)) OF INTEGER (0..17919)
   } OPTIONAL,
   ...
}

-- TAG-DOWNLINKCONFIGCOMMON-STOP
-- TAG-DOWNLINKCONFIGCOMMONSIB-START
DownlinkConfigCommonSIB ::= SEQUENCE {
   frequencyInfoDL [0] FrequencyInfoDL-SIB,
   initialDownlinkBWP [1] BWP-DownlinkCommon,
   bcch-Config [2] BCCH-Config,
   pcch-Config [3] PCCH-Config,
   ...
}

-- TAG-FREQUENCYINFOUL-STOP
-- TAG-FREQUENCYINFOUL-SIB-START
FrequencyInfoUL-SIB ::= SEQUENCE {
   frequencyBandList [0] MultiFrequencyBandListNR-SIB OPTIONAL, -- Cond FDD-OrSUL
   absoluteFrequencyPointA [1] ARFCN-ValueNR OPTIONAL, -- Cond FDD-OrSUL
   scs-SpecificCarrierList [2] SEQUENCE (SIZE (1..maxSCSs)) OF SCS-SpecificCarrier,
   p-Max [3] P-Max OPTIONAL, -- Need S
   frequencyShift7p5khz [4] ENUMERATED { true(0) } OPTIONAL,
   ...
}

-- TAG-QUANTITYCONFIG-STOP
-- TAG-RACH-CONFIGCOMMON-START
RACH-ConfigCommon ::= SEQUENCE {
   rach-ConfigGeneric [0] RACH-ConfigGeneric,
   totalNumberOfRA-Preambles [1] INTEGER (1..63) OPTIONAL, -- Need S
   ssb-perRACH-OccasionAndCB-PreamblesPerSSB [2] EXPLICIT CHOICE {
      oneEighth [0] ENUMERATED { n4(0), n8(1), n12(2), n16(3), n20(4), n24(5), 
         n28(6), n32(7), n36(8), n40(9), n44(10), n48(11), n52(12), n56(13), 
         n60(14), n64(15) },
      oneFourth [1] ENUMERATED { n4(0), n8(1), n12(2), n16(3), n20(4), n24(5), 
         n28(6), n32(7), n36(8), n40(9), n44(10), n48(11), n52(12), n56(13), 
         n60(14), n64(15) },
      oneHalf [2] ENUMERATED { n4(0), n8(1), n12(2), n16(3), n20(4), n24(5), 
         n28(6), n32(7), n36(8), n40(9), n44(10), n48(11), n52(12), n56(13), 
         n60(14), n64(15) },
      one [3] ENUMERATED { n4(0), n8(1), n12(2), n16(3), n20(4), n24(5), n28(6)
         , n32(7), n36(8), n40(9), n44(10), n48(11), n52(12), n56(13), n60(14)
         , n64(15) },
      two [4] ENUMERATED { n4(0), n8(1), n12(2), n16(3), n20(4), n24(5), n28(6)
         , n32(7) },
      four [5] INTEGER (1..16),
      eight [6] INTEGER (1..8),
      sixteen [7] INTEGER (1..4)
   } OPTIONAL, -- Need M
   groupBconfigured [3] SEQUENCE {
      ra-Msg3SizeGroupA [0] ENUMERATED { b56(0), b144(1), b208(2), b256(3), 
         b282(4), b480(5), b640(6), b800(7), b1000(8), b72(9), spare6(10), 
         spare5(11), spare4(12), spare3(13), spare2(14), spare1(15) },
      messagePowerOffsetGroupB [1] ENUMERATED { minusinfinity(0), dB0(1), 
         dB5(2), dB8(3), dB10(4), dB12(5), dB15(6), dB18(7) },
      numberOfRA-PreamblesGroupA [2] INTEGER (1..64)
   } OPTIONAL, -- Need R
   ra-ContentionResolutionTimer [4] ENUMERATED { sf8(0), sf16(1), sf24(2), 
      sf32(3), sf40(4), sf48(5), sf56(6), sf64(7) },
   rsrp-ThresholdSSB [5] RSRP-Range OPTIONAL, -- Need R
   rsrp-ThresholdSSB-SUL [6] RSRP-Range OPTIONAL, -- Cond SUL
   prach-RootSequenceIndex [7] EXPLICIT CHOICE {
      l839 [0] INTEGER (0..837),
      l139 [1] INTEGER (0..137)
   },
   msg1-SubcarrierSpacing [8] SubcarrierSpacing OPTIONAL, -- Cond L139
   restrictedSetConfig [9] ENUMERATED { unrestrictedSet(0), 
      restrictedSetTypeA(1), restrictedSetTypeB(2) },
   msg3-transformPrecoder [10] ENUMERATED { enabled(0) } OPTIONAL,
   ...
}

PUSCH-TimeDomainResourceAllocation ::= SEQUENCE {
   k2 [0] INTEGER (0..32) OPTIONAL, -- Need S
   mappingType [1] ENUMERATED { typeA(0), typeB(1) },
   startSymbolAndLength [2] INTEGER (0..127)
}

-- TAG-PUSCH-SERVINGCELLCONFIG-STOP
-- TAG-PUSCH-TIMEDOMAINRESOURCEALLOCATIONLIST-START
PUSCH-TimeDomainResourceAllocationList ::= SEQUENCE (SIZE (1..maxNrofUL-Allocations)) OF 
   PUSCH-TimeDomainResourceAllocation

-- TAG-PUSCH-CONFIG-STOP
-- TAG-PUSCH-CONFIGCOMMON-START
PUSCH-ConfigCommon ::= SEQUENCE {
   groupHoppingEnabledTransformPrecoding [0] ENUMERATED { enabled(0) } OPTIONAL
      , -- Need R
   pusch-TimeDomainAllocationList [1] PUSCH-TimeDomainResourceAllocationList
       OPTIONAL, -- Need R
   msg3-DeltaPreamble [2] INTEGER (-1..6) OPTIONAL, -- Need R
   p0-NominalWithGrant [3] INTEGER (-202..24) OPTIONAL,
   ...
}

-- TAG-PUCCH-CONFIG-STOP
-- TAG-PUCCH-CONFIGCOMMON-START
PUCCH-ConfigCommon ::= SEQUENCE {
   pucch-ResourceCommon [0] INTEGER (0..15) OPTIONAL, -- Cond InitialBWP-Only
   pucch-GroupHopping [1] ENUMERATED { neither(0), enable(1), disable(2) },
   hoppingId [2] INTEGER (0..1023) OPTIONAL, -- Need R
   p0-nominal [3] INTEGER (-202..24) OPTIONAL,
   ...
}

-- TAG-BWP-UPLINK-STOP
-- TAG-BWP-UPLINKCOMMON-START
BWP-UplinkCommon ::= SEQUENCE {
   genericParameters [0] BWP,
   rach-ConfigCommon [1] EXPLICIT CHOICE {
      release [0] NULL,
      setup [1] EXPLICIT RACH-ConfigCommon
   } OPTIONAL, -- Need M
   pusch-ConfigCommon [2] EXPLICIT CHOICE {
      release [0] NULL,
      setup [1] EXPLICIT PUSCH-ConfigCommon
   } OPTIONAL, -- Need M
   pucch-ConfigCommon [3] EXPLICIT CHOICE {
      release [0] NULL,
      setup [1] EXPLICIT PUCCH-ConfigCommon
   } OPTIONAL,
   ...
}

-- TAG-UPLINKCONFIGCOMMON-STOP
-- TAG-UPLINKCONFIGCOMMONSIB-START
UplinkConfigCommonSIB ::= SEQUENCE {
   frequencyInfoUL [0] FrequencyInfoUL-SIB,
   initialUplinkBWP [1] BWP-UplinkCommon,
   timeAlignmentTimerCommon [2] TimeAlignmentTimer
}

TDD-UL-DL-Pattern ::= SEQUENCE {
   dl-UL-TransmissionPeriodicity [0] ENUMERATED { ms0p5(0), ms0p625(1), ms1(2)
      , ms1p25(3), ms2(4), ms2p5(5), ms5(6), ms10(7) },
   nrofDownlinkSlots [1] INTEGER (0..maxNrofSlots),
   nrofDownlinkSymbols [2] INTEGER (0..maxNrofSymbols-1),
   nrofUplinkSlots [3] INTEGER (0..maxNrofSlots),
   nrofUplinkSymbols [4] INTEGER (0..maxNrofSymbols-1),
   ...,
   [[
      dl-UL-TransmissionPeriodicity-v1530 [5] ENUMERATED { ms3(0), ms4(1) }
          OPTIONAL
   ]]
}

-- TAG-TCI-STATEID-STOP
-- TAG-TDD-UL-DL-CONFIGCOMMON-START
TDD-UL-DL-ConfigCommon ::= SEQUENCE {
   referenceSubcarrierSpacing [0] SubcarrierSpacing,
   pattern1 [1] TDD-UL-DL-Pattern,
   pattern2 [2] TDD-UL-DL-Pattern OPTIONAL,
   ...
}

-- TAG-SERVINGCELLCONFIGCOMMON-STOP
-- TAG-SERVINGCELLCONFIGCOMMONSIB-START
ServingCellConfigCommonSIB ::= SEQUENCE {
   downlinkConfigCommon [0] DownlinkConfigCommonSIB,
   uplinkConfigCommon [1] UplinkConfigCommonSIB OPTIONAL, -- Need R
   supplementaryUplink [2] UplinkConfigCommonSIB OPTIONAL, -- Need R
   n-TimingAdvanceOffset [3] ENUMERATED { n0(0), n25600(1), n39936(2) }
       OPTIONAL, -- Need S
   ssb-PositionsInBurst [4] SEQUENCE {
      inOneGroup [0] BIT STRING  (SIZE (8)),
      groupPresence [1] BIT STRING  (SIZE (8)) OPTIONAL -- Cond FR2-Only
   },
   ssb-PeriodicityServingCell [5] ENUMERATED { ms5(0), ms10(1), ms20(2), 
      ms40(3), ms80(4), ms160(5) },
   tdd-UL-DL-ConfigurationCommon [6] TDD-UL-DL-ConfigCommon OPTIONAL, -- Cond TDD
   ss-PBCH-BlockPower [7] INTEGER (-60..50),
   ...
}

-- TAG-UAC-BARRINGPERPLMN-LIST-STOP
-- TAG-UE-TIMERSANDCONSTANTS-START
UE-TimersAndConstants ::= SEQUENCE {
   t300 [0] ENUMERATED { ms100(0), ms200(1), ms300(2), ms400(3), ms600(4), 
      ms1000(5), ms1500(6), ms2000(7) },
   t301 [1] ENUMERATED { ms100(0), ms200(1), ms300(2), ms400(3), ms600(4), 
      ms1000(5), ms1500(6), ms2000(7) },
   t310 [2] ENUMERATED { ms0(0), ms50(1), ms100(2), ms200(3), ms500(4), 
      ms1000(5), ms2000(6) },
   n310 [3] ENUMERATED { n1(0), n2(1), n3(2), n4(3), n6(4), n8(5), n10(6), 
      n20(7) },
   t311 [4] ENUMERATED { ms1000(0), ms3000(1), ms5000(2), ms10000(3), 
      ms15000(4), ms20000(5), ms30000(6) },
   n311 [5] ENUMERATED { n1(0), n2(1), n3(2), n4(3), n5(4), n6(5), n8(6), 
      n10(7) },
   t319 [6] ENUMERATED { ms100(0), ms200(1), ms300(2), ms400(3), ms600(4), 
      ms1000(5), ms1500(6), ms2000(7) },
   ...
}

UAC-BarringPerCat ::= SEQUENCE {
   accessCategory [0] INTEGER (1..maxAccessCat-1),
   uac-barringInfoSetIndex [1] UAC-BarringInfoSetIndex
}

-- TAG-UAC-BARRINGINFOSETLIST-STOP
-- TAG-UAC-BARRINGPERCATLIST-START
UAC-BarringPerCatList ::= SEQUENCE (SIZE (1..maxAccessCat-1)) OF UAC-BarringPerCat

UAC-BarringPerPLMN ::= SEQUENCE {
   plmn-IdentityIndex [0] INTEGER (1..maxPLMN),
   uac-ACBarringListType [1] EXPLICIT CHOICE {
      uac-ImplicitACBarringList [0] SEQUENCE (SIZE (maxAccessCat-1)) OF 
         UAC-BarringInfoSetIndex,
      uac-ExplicitACBarringList [1] UAC-BarringPerCatList
   } OPTIONAL -- Need S
}

-- TAG-UAC-BARRINGPERCATLIST-STOP
-- TAG-UAC-BARRINGPERPLMN-LIST-START
UAC-BarringPerPLMN-List ::= SEQUENCE (SIZE (1..maxPLMN)) OF UAC-BarringPerPLMN

UAC-BarringInfoSet ::= SEQUENCE {
   uac-BarringFactor [0] ENUMERATED { p00(0), p05(1), p10(2), p15(3), p20(4), 
      p25(5), p30(6), p40(7), p50(8), p60(9), p70(10), p75(11), p80(12), 
      p85(13), p90(14), p95(15) },
   uac-BarringTime [1] ENUMERATED { s4(0), s8(1), s16(2), s32(3), s64(4), 
      s128(5), s256(6), s512(7) },
   uac-BarringForAccessIdentity [2] BIT STRING  (SIZE (7))
}

-- TAG-UAC-BARRINGINFOSETINDEX-STOP
-- TAG-UAC-BARRINGINFOSETLIST-START
UAC-BarringInfoSetList ::= SEQUENCE (SIZE (1..maxBarringInfoSet)) OF UAC-BarringInfoSet

-- TAG-SECURITYMODEFAILURE-STOP
-- TAG-SIB1-START
SIB1 ::= SEQUENCE {
   cellSelectionInfo [0] SEQUENCE {
      q-RxLevMin [0] Q-RxLevMin,
      q-RxLevMinOffset [1] INTEGER (1..8) OPTIONAL, -- Need S
      q-RxLevMinSUL [2] Q-RxLevMin OPTIONAL, -- Need R
      q-QualMin [3] Q-QualMin OPTIONAL, -- Need S
      q-QualMinOffset [4] INTEGER (1..8) OPTIONAL -- Need S
   } OPTIONAL, -- Cond Standalone
   cellAccessRelatedInfo [1] CellAccessRelatedInfo,
   connEstFailureControl [2] ConnEstFailureControl OPTIONAL, -- Need R
   si-SchedulingInfo [3] SI-SchedulingInfo OPTIONAL, -- Need R
   servingCellConfigCommon [4] ServingCellConfigCommonSIB OPTIONAL, -- Need R
   ims-EmergencySupport [5] ENUMERATED { true(0) } OPTIONAL, -- Need R
   eCallOverIMS-Support [6] ENUMERATED { true(0) } OPTIONAL, -- Cond Absent
   ue-TimersAndConstants [7] UE-TimersAndConstants OPTIONAL, -- Need R
   uac-BarringInfo [8] SEQUENCE {
      uac-BarringForCommon [0] UAC-BarringPerCatList OPTIONAL, -- Need S
      uac-BarringPerPLMN-List [1] UAC-BarringPerPLMN-List OPTIONAL, -- Need S
      uac-BarringInfoSetList [2] UAC-BarringInfoSetList,
      uac-AccessCategory1-SelectionAssistanceInfo [3] EXPLICIT CHOICE {
         plmnCommon [0] UAC-AccessCategory1-SelectionAssistanceInfo,
         individualPLMNList [1] SEQUENCE (SIZE (2..maxPLMN)) OF 
            UAC-AccessCategory1-SelectionAssistanceInfo
      } OPTIONAL -- Need S
   } OPTIONAL, -- Need R
   useFullResumeID [9] ENUMERATED { true(0) } OPTIONAL, -- Need R
   lateNonCriticalExtension [10] OCTET STRING OPTIONAL,
   nonCriticalExtension [11] SEQUENCE {

   } OPTIONAL
}

BCCH-DL-SCH-MessageType ::= CHOICE {
   c1 [0] EXPLICIT CHOICE {
      systemInformation [0] SystemInformation,
      systemInformationBlockType1 [1] SIB1
   },
   messageClassExtension [1] SEQUENCE {

   }
}

-- TAG-BCCH-BCH-MESSAGE-STOP
-- TAG-BCCH-DL-SCH-MESSAGE-START
BCCH-DL-SCH-Message ::= SEQUENCE {
   message [0] EXPLICIT BCCH-DL-SCH-MessageType
}

RRCReject-IEs ::= SEQUENCE {
   waitTime [0] RejectWaitTime OPTIONAL, -- Need N
   lateNonCriticalExtension [1] OCTET STRING OPTIONAL,
   nonCriticalExtension [2] SEQUENCE {

   } OPTIONAL
}

-- TAG-RRCRECONFIGURATIONCOMPLETE-STOP
-- TAG-RRCREJECT-START
RRCReject ::= SEQUENCE {
   criticalExtensions [0] EXPLICIT CHOICE {
      rrcReject [0] RRCReject-IEs,
      criticalExtensionsFuture [1] SEQUENCE {

      }
   }
}

-- TAG-PDCCH-SERVINGCELLCONFIG-STOP
-- TAG-PDCP-CONFIG-START
PDCP-Config ::= SEQUENCE {
   drb [0] SEQUENCE {
      discardTimer [0] ENUMERATED { ms10(0), ms20(1), ms30(2), ms40(3), ms50(4)
         , ms60(5), ms75(6), ms100(7), ms150(8), ms200(9), ms250(10), ms300(11)
         , ms500(12), ms750(13), ms1500(14), infinity(15) } OPTIONAL, -- Cond Setup
      pdcp-SN-SizeUL [1] ENUMERATED { len12bits(0), len18bits(1) } OPTIONAL, -- Cond Setup2
      pdcp-SN-SizeDL [2] ENUMERATED { len12bits(0), len18bits(1) } OPTIONAL, -- Cond Setup2
      headerCompression [3] EXPLICIT CHOICE {
         notUsed [0] NULL,
         rohc [1] SEQUENCE {
            maxCID [0] INTEGER (1..16383) DEFAULT 15,
            profiles [1] SEQUENCE {
               profile0x0001 [0] BOOLEAN,
               profile0x0002 [1] BOOLEAN,
               profile0x0003 [2] BOOLEAN,
               profile0x0004 [3] BOOLEAN,
               profile0x0006 [4] BOOLEAN,
               profile0x0101 [5] BOOLEAN,
               profile0x0102 [6] BOOLEAN,
               profile0x0103 [7] BOOLEAN,
               profile0x0104 [8] BOOLEAN
            },
            drb-ContinueROHC [2] ENUMERATED { true(0) } OPTIONAL -- Need N
         },
         uplinkOnlyROHC [2] SEQUENCE {
            maxCID [0] INTEGER (1..16383) DEFAULT 15,
            profiles [1] SEQUENCE {
               profile0x0006 [0] BOOLEAN
            },
            drb-ContinueROHC [2] ENUMERATED { true(0) } OPTIONAL -- Need N
         },
         ...
      },
      integrityProtection [4] ENUMERATED { enabled(0) } OPTIONAL, -- Cond ConnectedTo5GC1
      statusReportRequired [5] ENUMERATED { true(0) } OPTIONAL, -- Cond Rlc-AM
      outOfOrderDelivery [6] ENUMERATED { true(0) } OPTIONAL -- Need R
   } OPTIONAL, -- Cond DRB
   moreThanOneRLC [1] SEQUENCE {
      primaryPath [0] SEQUENCE {
         cellGroup [0] CellGroupId OPTIONAL, -- Need R
         logicalChannel [1] LogicalChannelIdentity OPTIONAL -- Need R
      },
      ul-DataSplitThreshold [1] UL-DataSplitThreshold OPTIONAL, -- Cond SplitBearer
      pdcp-Duplication [2] BOOLEAN OPTIONAL -- Need R
   } OPTIONAL, -- Cond MoreThanOneRLC
   t-Reordering [2] ENUMERATED { ms0(0), ms1(1), ms2(2), ms4(3), ms5(4), ms8(5)
      , ms10(6), ms15(7), ms20(8), ms30(9), ms40(10), ms50(11), ms60(12), 
      ms80(13), ms100(14), ms120(15), ms140(16), ms160(17), ms180(18), 
      ms200(19), ms220(20), ms240(21), ms260(22), ms280(23), ms300(24), 
      ms500(25), ms750(26), ms1000(27), ms1250(28), ms1500(29), ms1750(30), 
      ms2000(31), ms2250(32), ms2500(33), ms2750(34), ms3000(35), spare28(36), 
      spare27(37), spare26(38), spare25(39), spare24(40), spare23(41), 
      spare22(42), spare21(43), spare20(44), spare19(45), spare18(46), 
      spare17(47), spare16(48), spare15(49), spare14(50), spare13(51), 
      spare12(52), spare11(53), spare10(54), spare09(55), spare08(56), 
      spare07(57), spare06(58), spare05(59), spare04(60), spare03(61), 
      spare02(62), spare01(63) } OPTIONAL,
   ...,
   [[
      cipheringDisabled [3] ENUMERATED { true(0) } OPTIONAL
   ]]
}

SRB-ToAddMod ::= SEQUENCE {
   srb-Identity [0] SRB-Identity,
   reestablishPDCP [1] ENUMERATED { true(0) } OPTIONAL, -- Need N
   discardOnPDCP [2] ENUMERATED { true(0) } OPTIONAL, -- Need N
   pdcp-Config [3] PDCP-Config OPTIONAL,
   ...
}

SRB-ToAddModList ::= SEQUENCE (SIZE (1..2)) OF SRB-ToAddMod

-- TAG-SCS-SPECIFICCARRIER-STOP
-- TAG-SDAP-CONFIG-START
SDAP-Config ::= SEQUENCE {
   pdu-Session [0] PDU-SessionID,
   sdap-HeaderDL [1] ENUMERATED { present(0), absent(1) },
   sdap-HeaderUL [2] ENUMERATED { present(0), absent(1) },
   defaultDRB [3] BOOLEAN,
   mappedQoS-FlowsToAdd [4] SEQUENCE (SIZE (1..maxNrofQFIs)) OF QFI OPTIONAL, -- Need N
   mappedQoS-FlowsToRelease [5] SEQUENCE (SIZE (1..maxNrofQFIs)) OF QFI OPTIONAL,
   ...
}

DRB-ToAddMod ::= SEQUENCE {
   cnAssociation [0] EXPLICIT CHOICE {
      eps-BearerIdentity [0] INTEGER (0..15),
      sdap-Config [1] SDAP-Config
   } OPTIONAL, -- Cond DRBSetup
   drb-Identity [1] DRB-Identity,
   reestablishPDCP [2] ENUMERATED { true(0) } OPTIONAL, -- Need N
   recoverPDCP [3] ENUMERATED { true(0) } OPTIONAL, -- Need N
   pdcp-Config [4] PDCP-Config OPTIONAL,
   ...
}

DRB-ToAddModList ::= SEQUENCE (SIZE (1..maxDRB)) OF DRB-ToAddMod

DRB-ToReleaseList ::= SEQUENCE (SIZE (1..maxDRB)) OF DRB-Identity

-- TAG-SEARCHSPACEZERO-STOP
-- TAG-SECURITYALGORITHMCONFIG-START
SecurityAlgorithmConfig ::= SEQUENCE {
   cipheringAlgorithm [0] CipheringAlgorithm,
   integrityProtAlgorithm [1] IntegrityProtAlgorithm OPTIONAL,
   ...
}

SecurityConfig ::= SEQUENCE {
   securityAlgorithmConfig [0] SecurityAlgorithmConfig OPTIONAL, -- Cond RBTermChange1
   keyToUse [1] ENUMERATED { master(0), secondary(1) } OPTIONAL,
   ...
}

-- TAG-RA-PRIORITIZATION-STOP
-- TAG-RADIOBEARERCONFIG-START
RadioBearerConfig ::= SEQUENCE {
   srb-ToAddModList [0] SRB-ToAddModList OPTIONAL, -- Cond HO-Conn
   srb3-ToRelease [1] ENUMERATED { true(0) } OPTIONAL, -- Need N
   drb-ToAddModList [2] DRB-ToAddModList OPTIONAL, -- Cond HO-toNR
   drb-ToReleaseList [3] DRB-ToReleaseList OPTIONAL, -- Need N
   securityConfig [4] SecurityConfig OPTIONAL,
   ...
}

UL-AM-RLC ::= SEQUENCE {
   sn-FieldLength [0] SN-FieldLengthAM OPTIONAL, -- Cond Reestab
   t-PollRetransmit [1] T-PollRetransmit,
   pollPDU [2] PollPDU,
   pollByte [3] PollByte,
   maxRetxThreshold [4] ENUMERATED { t1(0), t2(1), t3(2), t4(3), t6(4), t8(5), 
      t16(6), t32(7) }
}

DL-AM-RLC ::= SEQUENCE {
   sn-FieldLength [0] SN-FieldLengthAM OPTIONAL, -- Cond Reestab
   t-Reassembly [1] T-Reassembly,
   t-StatusProhibit [2] T-StatusProhibit
}

UL-UM-RLC ::= SEQUENCE {
   sn-FieldLength [0] SN-FieldLengthUM OPTIONAL -- Cond Reestab
}

DL-UM-RLC ::= SEQUENCE {
   sn-FieldLength [0] SN-FieldLengthUM OPTIONAL, -- Cond Reestab
   t-Reassembly [1] T-Reassembly
}

-- TAG-RLC-BEARERCONFIG-STOP
-- TAG-RLC-CONFIG-START
RLC-Config ::= CHOICE {
   am [0] SEQUENCE {
      ul-AM-RLC [0] UL-AM-RLC,
      dl-AM-RLC [1] DL-AM-RLC
   },
   um-Bi-Directional [1] SEQUENCE {
      ul-UM-RLC [0] UL-UM-RLC,
      dl-UM-RLC [1] DL-UM-RLC
   },
   um-Uni-Directional-UL [2] SEQUENCE {
      ul-UM-RLC [0] UL-UM-RLC
   },
   um-Uni-Directional-DL [3] SEQUENCE {
      dl-UM-RLC [0] DL-UM-RLC
   },
   ...
}

-- TAG-LOCATIONMEASUREMENTINFO-STOP
-- TAG-LOGICALCHANNELCONFIG-START
LogicalChannelConfig ::= SEQUENCE {
   ul-SpecificParameters [0] SEQUENCE {
      priority [0] INTEGER (1..16),
      prioritisedBitRate [1] ENUMERATED { kBps0(0), kBps8(1), kBps16(2), 
         kBps32(3), kBps64(4), kBps128(5), kBps256(6), kBps512(7), kBps1024(8)
         , kBps2048(9), kBps4096(10), kBps8192(11), kBps16384(12), 
         kBps32768(13), kBps65536(14), infinity(15) },
      bucketSizeDuration [2] ENUMERATED { ms5(0), ms10(1), ms20(2), ms50(3), 
         ms100(4), ms150(5), ms300(6), ms500(7), ms1000(8), spare7(9), 
         spare6(10), spare5(11), spare4(12), spare3(13), spare2(14), spare1(15)
          },
      allowedServingCells [3] SEQUENCE (SIZE (1..maxNrofServingCells-1)) OF ServCellIndex OPTIONAL,
                                                                                                                  -- PDCP-CADuplication
      allowedSCS-List [4] SEQUENCE (SIZE (1..maxSCSs)) OF SubcarrierSpacing OPTIONAL, -- Need R
      maxPUSCH-Duration [5] ENUMERATED { ms0p02(0), ms0p04(1), ms0p0625(2), 
         ms0p125(3), ms0p25(4), ms0p5(5), spare2(6), spare1(7) } OPTIONAL,
                                                                                                                  -- Need R
      configuredGrantType1Allowed [6] ENUMERATED { true(0) } OPTIONAL, -- Need R
      logicalChannelGroup [7] INTEGER (0..maxLCG-ID) OPTIONAL, -- Need R
      schedulingRequestID [8] SchedulingRequestId OPTIONAL, -- Need R
      logicalChannelSR-Mask [9] BOOLEAN,
      logicalChannelSR-DelayTimerApplied [10] BOOLEAN,
      ...,
      bitRateQueryProhibitTimer [11] ENUMERATED { s0(0), s0dot4(1), s0dot8(2), 
         s1dot6(3), s3(4), s6(5), s12(6), s30(7) } OPTIONAL -- Need R
   } OPTIONAL,
   ...
}

-- TAG-RESUMECAUSE-STOP
-- TAG-RLC-BEARERCONFIG-START
RLC-BearerConfig ::= SEQUENCE {
   logicalChannelIdentity [0] LogicalChannelIdentity,
   servedRadioBearer [1] EXPLICIT CHOICE {
      srb-Identity [0] SRB-Identity,
      drb-Identity [1] DRB-Identity
   } OPTIONAL, -- Cond LCH-SetupOnly
   reestablishRLC [2] ENUMERATED { true(0) } OPTIONAL, -- Need N
   rlc-Config [3] EXPLICIT RLC-Config OPTIONAL, -- Cond LCH-Setup
   mac-LogicalChannelConfig [4] LogicalChannelConfig OPTIONAL,
   ...
}

-- TAG-DRB-IDENTITY-STOP
-- TAG-DRX-CONFIG-START
DRX-Config ::= SEQUENCE {
   drx-onDurationTimer [0] EXPLICIT CHOICE {
      subMilliSeconds [0] INTEGER (1..31),
      milliSeconds [1] ENUMERATED { ms1(0), ms2(1), ms3(2), ms4(3), ms5(4), 
         ms6(5), ms8(6), ms10(7), ms20(8), ms30(9), ms40(10), ms50(11), 
         ms60(12), ms80(13), ms100(14), ms200(15), ms300(16), ms400(17), 
         ms500(18), ms600(19), ms800(20), ms1000(21), ms1200(22), ms1600(23), 
         spare8(24), spare7(25), spare6(26), spare5(27), spare4(28), spare3(29)
         , spare2(30), spare1(31) }
   },
   drx-InactivityTimer [1] ENUMERATED { ms0(0), ms1(1), ms2(2), ms3(3), ms4(4)
      , ms5(5), ms6(6), ms8(7), ms10(8), ms20(9), ms30(10), ms40(11), ms50(12)
      , ms60(13), ms80(14), ms100(15), ms200(16), ms300(17), ms500(18), 
      ms750(19), ms1280(20), ms1920(21), ms2560(22), spare9(23), spare8(24), 
      spare7(25), spare6(26), spare5(27), spare4(28), spare3(29), spare2(30), 
      spare1(31) },
   drx-HARQ-RTT-TimerDL [2] INTEGER (0..56),
   drx-HARQ-RTT-TimerUL [3] INTEGER (0..56),
   drx-RetransmissionTimerDL [4] ENUMERATED { sl0(0), sl1(1), sl2(2), sl4(3), 
      sl6(4), sl8(5), sl16(6), sl24(7), sl33(8), sl40(9), sl64(10), sl80(11), 
      sl96(12), sl112(13), sl128(14), sl160(15), sl320(16), spare15(17), 
      spare14(18), spare13(19), spare12(20), spare11(21), spare10(22), 
      spare9(23), spare8(24), spare7(25), spare6(26), spare5(27), spare4(28), 
      spare3(29), spare2(30), spare1(31) },
   drx-RetransmissionTimerUL [5] ENUMERATED { sl0(0), sl1(1), sl2(2), sl4(3), 
      sl6(4), sl8(5), sl16(6), sl24(7), sl33(8), sl40(9), sl64(10), sl80(11), 
      sl96(12), sl112(13), sl128(14), sl160(15), sl320(16), spare15(17), 
      spare14(18), spare13(19), spare12(20), spare11(21), spare10(22), 
      spare9(23), spare8(24), spare7(25), spare6(26), spare5(27), spare4(28), 
      spare3(29), spare2(30), spare1(31) },
   drx-LongCycleStartOffset [6] EXPLICIT CHOICE {
      ms10 [0] INTEGER (0..9),
      ms20 [1] INTEGER (0..19),
      ms32 [2] INTEGER (0..31),
      ms40 [3] INTEGER (0..39),
      ms60 [4] INTEGER (0..59),
      ms64 [5] INTEGER (0..63),
      ms70 [6] INTEGER (0..69),
      ms80 [7] INTEGER (0..79),
      ms128 [8] INTEGER (0..127),
      ms160 [9] INTEGER (0..159),
      ms256 [10] INTEGER (0..255),
      ms320 [11] INTEGER (0..319),
      ms512 [12] INTEGER (0..511),
      ms640 [13] INTEGER (0..639),
      ms1024 [14] INTEGER (0..1023),
      ms1280 [15] INTEGER (0..1279),
      ms2048 [16] INTEGER (0..2047),
      ms2560 [17] INTEGER (0..2559),
      ms5120 [18] INTEGER (0..5119),
      ms10240 [19] INTEGER (0..10239)
   },
   shortDRX [7] SEQUENCE {
      drx-ShortCycle [0] ENUMERATED { ms2(0), ms3(1), ms4(2), ms5(3), ms6(4), 
         ms7(5), ms8(6), ms10(7), ms14(8), ms16(9), ms20(10), ms30(11), 
         ms32(12), ms35(13), ms40(14), ms64(15), ms80(16), ms128(17), ms160(18)
         , ms256(19), ms320(20), ms512(21), ms640(22), spare9(23), spare8(24), 
         spare7(25), spare6(26), spare5(27), spare4(28), spare3(29), spare2(30)
         , spare1(31) },
      drx-ShortCycleTimer [1] INTEGER (1..16)
   } OPTIONAL, -- Need R
   drx-SlotOffset [8] INTEGER (0..31)
}

SchedulingRequestToAddMod ::= SEQUENCE {
   schedulingRequestId [0] SchedulingRequestId,
   sr-ProhibitTimer [1] ENUMERATED { ms1(0), ms2(1), ms4(2), ms8(3), ms16(4), 
      ms32(5), ms64(6), ms128(7) } OPTIONAL, -- Need S
   sr-TransMax [2] ENUMERATED { n4(0), n8(1), n16(2), n32(3), n64(4), spare3(5)
      , spare2(6), spare1(7) }
}

-- TAG-SCELLINDEX-STOP
-- TAG-SCHEDULINGREQUESTCONFIG-START
SchedulingRequestConfig ::= SEQUENCE {
   schedulingRequestToAddModList [0] SEQUENCE (SIZE (1..maxNrofSR-ConfigPerCellGroup)) OF 
      SchedulingRequestToAddMod OPTIONAL,
                                                                                                                     -- Need N
   schedulingRequestToReleaseList [1] SEQUENCE (SIZE (1..maxNrofSR-ConfigPerCellGroup)) OF 
      SchedulingRequestId OPTIONAL
                                                                                                                     -- Need N
}

-- TAG-BETAOFFSETS-STOP
-- TAG-BSR-CONFIG-START
BSR-Config ::= SEQUENCE {
   periodicBSR-Timer [0] ENUMERATED { sf1(0), sf5(1), sf10(2), sf16(3), sf20(4)
      , sf32(5), sf40(6), sf64(7), sf80(8), sf128(9), sf160(10), sf320(11), 
      sf640(12), sf1280(13), sf2560(14), infinity(15) },
   retxBSR-Timer [1] ENUMERATED { sf10(0), sf20(1), sf40(2), sf80(3), sf160(4)
      , sf320(5), sf640(6), sf1280(7), sf2560(8), sf5120(9), sf10240(10), 
      spare5(11), spare4(12), spare3(13), spare2(14), spare1(15) },
   logicalChannelSR-DelayTimer [2] ENUMERATED { sf20(0), sf40(1), sf64(2), 
      sf128(3), sf512(4), sf1024(5), sf2560(6), spare1(7) } OPTIONAL,
   ...
}

TAG ::= SEQUENCE {
   tag-Id [0] TAG-Id,
   timeAlignmentTimer [1] TimeAlignmentTimer,
   ...
}

-- TAG-SUBCARRIERSPACING-STOP
-- TAG-TAG-CONFIG-START
TAG-Config ::= SEQUENCE {
   tag-ToReleaseList [0] SEQUENCE (SIZE (1..maxNrofTAGs)) OF TAG-Id OPTIONAL, -- Need N
   tag-ToAddModList [1] SEQUENCE (SIZE (1..maxNrofTAGs)) OF TAG OPTIONAL -- Need N
}

-- TAG-PDSCH-TIMEDOMAINRESOURCEALLOCATIONLIST-STOP
-- TAG-PHR-CONFIG-START
PHR-Config ::= SEQUENCE {
   phr-PeriodicTimer [0] ENUMERATED { sf10(0), sf20(1), sf50(2), sf100(3), 
      sf200(4), sf500(5), sf1000(6), infinity(7) },
   phr-ProhibitTimer [1] ENUMERATED { sf0(0), sf10(1), sf20(2), sf50(3), 
      sf100(4), sf200(5), sf500(6), sf1000(7) },
   phr-Tx-PowerFactorChange [2] ENUMERATED { dB1(0), dB3(1), dB6(2), 
      infinity(3) },
   multiplePHR [3] BOOLEAN,
   dummy [4] BOOLEAN,
   phr-Type2OtherCell [5] BOOLEAN,
   phr-ModeOtherCG [6] ENUMERATED { real(0), virtual(1) },
   ...
}

-- TAG-LOGICALCHANNELIDENTITY-STOP
-- TAG-MAC-CELLGROUPCONFIG-START
MAC-CellGroupConfig ::= SEQUENCE {
   drx-Config [0] EXPLICIT CHOICE {
      release [0] NULL,
      setup [1] EXPLICIT DRX-Config
   } OPTIONAL, -- Need M
   schedulingRequestConfig [1] SchedulingRequestConfig OPTIONAL, -- Need M
   bsr-Config [2] BSR-Config OPTIONAL, -- Need M
   tag-Config [3] TAG-Config OPTIONAL, -- Need M
   phr-Config [4] EXPLICIT CHOICE {
      release [0] NULL,
      setup [1] EXPLICIT PHR-Config
   } OPTIONAL, -- Need M
   skipUplinkTxDynamic [5] BOOLEAN,
   ...,
   [[
      csi-Mask [6] BOOLEAN OPTIONAL,
      dataInactivityTimer [7] EXPLICIT CHOICE {
         release [0] NULL,
         setup [1] EXPLICIT DataInactivityTimer
      } OPTIONAL
   ]]
}

-- TAG-PHYSCELLID-STOP
-- TAG-PHYSICALCELLGROUPCONFIG-START
PhysicalCellGroupConfig ::= SEQUENCE {
   harq-ACK-SpatialBundlingPUCCH [0] ENUMERATED { true(0) } OPTIONAL, -- Need S
   harq-ACK-SpatialBundlingPUSCH [1] ENUMERATED { true(0) } OPTIONAL, -- Need S
   p-NR-FR1 [2] P-Max OPTIONAL, -- Need R
   pdsch-HARQ-ACK-Codebook [3] ENUMERATED { semiStatic(0), dynamic(1) },
   tpc-SRS-RNTI [4] RNTI-Value OPTIONAL, -- Need R
   tpc-PUCCH-RNTI [5] RNTI-Value OPTIONAL, -- Need R
   tpc-PUSCH-RNTI [6] RNTI-Value OPTIONAL, -- Need R
   sp-CSI-RNTI [7] RNTI-Value OPTIONAL, -- Need R
   cs-RNTI [8] EXPLICIT CHOICE {
      release [0] NULL,
      setup [1] EXPLICIT RNTI-Value
   } OPTIONAL,
   ...,
   [[
      mcs-C-RNTI [9] RNTI-Value OPTIONAL,
      p-UE-FR1 [10] P-Max OPTIONAL
   ]],
   [[
      xScale [11] ENUMERATED { dB0(0), dB6(1), spare2(2), spare1(3) } OPTIONAL
   ]],
   [[
      pdcch-BlindDetection [12] EXPLICIT CHOICE {
         release [0] NULL,
         setup [1] EXPLICIT PDCCH-BlindDetection
      } OPTIONAL
   ]]
}

-- TAG-MOBILITYSTATEPARAMETERS-STOP
-- TAG-MULTIFREQUENCYBANDLISTNR-START
MultiFrequencyBandListNR ::= SEQUENCE (SIZE (1..maxNrofMultiBands)) OF FreqBandIndicatorNR

-- TAG-FREQBANDINDICATORNR-STOP
-- TAG-FREQUENCYINFODL-START
FrequencyInfoDL ::= SEQUENCE {
   absoluteFrequencySSB [0] ARFCN-ValueNR OPTIONAL, -- Cond SpCellAdd
   frequencyBandList [1] MultiFrequencyBandListNR,
   absoluteFrequencyPointA [2] ARFCN-ValueNR,
   scs-SpecificCarrierList [3] SEQUENCE (SIZE (1..maxSCSs)) OF SCS-SpecificCarrier,
   ...
}

-- TAG-DMRS-UPLINKCONFIG-STOP
-- TAG-DOWNLINKCONFIGCOMMON-START
DownlinkConfigCommon ::= SEQUENCE {
   frequencyInfoDL [0] FrequencyInfoDL OPTIONAL, -- Cond InterFreqHOAndServCellAdd
   initialDownlinkBWP [1] BWP-DownlinkCommon OPTIONAL,
   ...
}

-- TAG-FREQUENCYINFODL-SIB-STOP
-- TAG-FREQUENCYINFOUL-START
FrequencyInfoUL ::= SEQUENCE {
   frequencyBandList [0] MultiFrequencyBandListNR OPTIONAL, -- Cond FDD-OrSUL
   absoluteFrequencyPointA [1] ARFCN-ValueNR OPTIONAL, -- Cond FDD-OrSUL
   scs-SpecificCarrierList [2] SEQUENCE (SIZE (1..maxSCSs)) OF SCS-SpecificCarrier,
   additionalSpectrumEmission [3] AdditionalSpectrumEmission OPTIONAL, -- Need S
   p-Max [4] P-Max OPTIONAL, -- Need S
   frequencyShift7p5khz [5] ENUMERATED { true(0) } OPTIONAL,
   ...
}

-- TAG-UE-TIMERSANDCONSTANTS-STOP
-- TAG-UPLINKCONFIGCOMMON-START
UplinkConfigCommon ::= SEQUENCE {
   frequencyInfoUL [0] FrequencyInfoUL OPTIONAL, -- Cond InterFreqHOAndServCellAdd
   initialUplinkBWP [1] BWP-UplinkCommon OPTIONAL, -- Cond ServCellAdd
   dummy [2] TimeAlignmentTimer
}

EUTRA-MBSFN-SubframeConfig ::= SEQUENCE {
   radioframeAllocationPeriod [0] ENUMERATED { n1(0), n2(1), n4(2), n8(3), 
      n16(4), n32(5) },
   radioframeAllocationOffset [1] INTEGER (0..7),
   subframeAllocation1 [2] EXPLICIT CHOICE {
      oneFrame [0] BIT STRING  (SIZE (6)),
      fourFrames [1] BIT STRING  (SIZE (24))
   },
   subframeAllocation2 [3] EXPLICIT CHOICE {
      oneFrame [0] BIT STRING  (SIZE (2)),
      fourFrames [1] BIT STRING  (SIZE (8))
   } OPTIONAL,
   ...
}

-- TAG-EUTRA-ALLOWEDMEASBANDWIDTH-STOP
-- TAG-EUTRA-MBSFN-SUBFRAMECONFIGLIST-START
EUTRA-MBSFN-SubframeConfigList ::= SEQUENCE (SIZE (1..maxMBSFN-Allocations)) OF 
   EUTRA-MBSFN-SubframeConfig

-- TAG-RATEMATCHPATTERNID-STOP
-- TAG-RATEMATCHPATTERNLTE-CRS-START
RateMatchPatternLTE-CRS ::= SEQUENCE {
   carrierFreqDL [0] INTEGER (0..16383),
   carrierBandwidthDL [1] ENUMERATED { n6(0), n15(1), n25(2), n50(3), n75(4), 
      n100(5), spare2(6), spare1(7) },
   mbsfn-SubframeConfigList [2] EUTRA-MBSFN-SubframeConfigList OPTIONAL, -- Need M
   nrofCRS-Ports [3] ENUMERATED { n1(0), n2(1), n4(2) },
   v-Shift [4] ENUMERATED { n0(0), n1(1), n2(2), n3(3), n4(4), n5(5) }
}

-- TAG-RAN-AREACODE-STOP
-- TAG-RATEMATCHPATTERN-START
RateMatchPattern ::= SEQUENCE {
   rateMatchPatternId [0] RateMatchPatternId,
   patternType [1] EXPLICIT CHOICE {
      bitmaps [0] SEQUENCE {
         resourceBlocks [0] BIT STRING  (SIZE (275)),
         symbolsInResourceBlock [1] EXPLICIT CHOICE {
            oneSlot [0] BIT STRING  (SIZE (14)),
            twoSlots [1] BIT STRING  (SIZE (28))
         },
         periodicityAndPattern [2] EXPLICIT CHOICE {
            n2 [0] BIT STRING  (SIZE (2)),
            n4 [1] BIT STRING  (SIZE (4)),
            n5 [2] BIT STRING  (SIZE (5)),
            n8 [3] BIT STRING  (SIZE (8)),
            n10 [4] BIT STRING  (SIZE (10)),
            n20 [5] BIT STRING  (SIZE (20)),
            n40 [6] BIT STRING  (SIZE (40))
         } OPTIONAL,
         ...
      },
      controlResourceSet [1] ControlResourceSetId
   },
   subcarrierSpacing [2] SubcarrierSpacing OPTIONAL, -- Cond CellLevel
   dummy [3] ENUMERATED { dynamic(0), semiStatic(1) },
   ...
}

-- TAG-SERVINGCELLCONFIG-STOP
-- TAG-SERVINGCELLCONFIGCOMMON-START
ServingCellConfigCommon ::= SEQUENCE {
   physCellId [0] PhysCellId OPTIONAL, -- Cond HOAndServCellAdd,
   downlinkConfigCommon [1] DownlinkConfigCommon OPTIONAL, -- Cond HOAndServCellAdd
   uplinkConfigCommon [2] UplinkConfigCommon OPTIONAL, -- Need M
   supplementaryUplinkConfig [3] UplinkConfigCommon OPTIONAL, -- Need S
   n-TimingAdvanceOffset [4] ENUMERATED { n0(0), n25600(1), n39936(2) }
       OPTIONAL, -- Need S
   ssb-PositionsInBurst [5] EXPLICIT CHOICE {
      shortBitmap [0] BIT STRING  (SIZE (4)),
      mediumBitmap [1] BIT STRING  (SIZE (8)),
      longBitmap [2] BIT STRING  (SIZE (64))
   } OPTIONAL, -- Cond AbsFreqSSB
   ssb-periodicityServingCell [6] ENUMERATED { ms5(0), ms10(1), ms20(2), 
      ms40(3), ms80(4), ms160(5), spare2(6), spare1(7) } OPTIONAL, -- Need S
   dmrs-TypeA-Position [7] ENUMERATED { pos2(0), pos3(1) },
   lte-CRS-ToMatchAround [8] EXPLICIT CHOICE {
      release [0] NULL,
      setup [1] EXPLICIT RateMatchPatternLTE-CRS
   } OPTIONAL, -- Need M
   rateMatchPatternToAddModList [9] SEQUENCE (SIZE (1..maxNrofRateMatchPatterns)) OF RateMatchPattern
       OPTIONAL, -- Need N
   rateMatchPatternToReleaseList [10] SEQUENCE (SIZE (1..maxNrofRateMatchPatterns)) OF 
      RateMatchPatternId OPTIONAL, -- Need N
   ssbSubcarrierSpacing [11] SubcarrierSpacing OPTIONAL, -- Cond HOAndServCellWithSSB
   tdd-UL-DL-ConfigurationCommon [12] TDD-UL-DL-ConfigCommon OPTIONAL, -- Cond TDD
   ss-PBCH-BlockPower [13] INTEGER (-60..50),
   ...
}

CFRA-SSB-Resource ::= SEQUENCE {
   ssb [0] SSB-Index,
   ra-PreambleIndex [1] INTEGER (0..63),
   ...
}

CFRA-CSIRS-Resource ::= SEQUENCE {
   csi-RS [0] CSI-RS-Index,
   ra-OccasionList [1] SEQUENCE (SIZE (1..maxRA-OccasionsPerCSIRS)) OF INTEGER (0..maxRA-Occasions-1),
   ra-PreambleIndex [2] INTEGER (0..63),
   ...
}

CFRA ::= SEQUENCE {
   occasions [0] SEQUENCE {
      rach-ConfigGeneric [0] RACH-ConfigGeneric,
      ssb-perRACH-Occasion [1] ENUMERATED { oneEighth(0), oneFourth(1), 
         oneHalf(2), one(3), two(4), four(5), eight(6), sixteen(7) } OPTIONAL
                                                                                                                        -- Cond SSB-CFRA
   } OPTIONAL, -- Need S
   resources [1] EXPLICIT CHOICE {
      ssb [0] SEQUENCE {
         ssb-ResourceList [0] SEQUENCE (SIZE (1..maxRA-SSB-Resources)) OF CFRA-SSB-Resource,
         ra-ssb-OccasionMaskIndex [1] INTEGER (0..15)
      },
      csirs [1] SEQUENCE {
         csirs-ResourceList [0] SEQUENCE (SIZE (1..maxRA-CSIRS-Resources)) OF CFRA-CSIRS-Resource,
         rsrp-ThresholdCSI-RS [1] RSRP-Range
      }
   },
   ...,
   [[
      totalNumberOfRA-Preambles [2] INTEGER (1..63) OPTIONAL
   ]]
}

-- TAG-RACH-CONFIGGENERIC-STOP
-- TAG-RA-PRIORITIZATION-START
RA-Prioritization ::= SEQUENCE {
   powerRampingStepHighPriority [0] ENUMERATED { dB0(0), dB2(1), dB4(2), dB6(3)
       },
   scalingFactorBI [1] ENUMERATED { zero(0), dot25(1), dot5(2), dot75(3) }
       OPTIONAL,
   ...
}

-- TAG-RACH-CONFIGCOMMON-STOP
-- TAG-RACH-CONFIGDEDICATED-START
RACH-ConfigDedicated ::= SEQUENCE {
   cfra [0] CFRA OPTIONAL, -- Need S
   ra-Prioritization [1] RA-Prioritization OPTIONAL,
   ...
}

ReconfigurationWithSync ::= SEQUENCE {
   spCellConfigCommon [0] ServingCellConfigCommon OPTIONAL, -- Need M
   newUE-Identity [1] RNTI-Value,
   t304 [2] ENUMERATED { ms50(0), ms100(1), ms150(2), ms200(3), ms500(4), 
      ms1000(5), ms2000(6), ms10000(7) },
   rach-ConfigDedicated [3] EXPLICIT CHOICE {
      uplink [0] RACH-ConfigDedicated,
      supplementaryUplink [1] RACH-ConfigDedicated
   } OPTIONAL,
   ...,
   [[
      smtc [4] SSB-MTC OPTIONAL
   ]]
}

-- TAG-RLC-CONFIG-STOP
-- TAG-RLF-TIMERSANDCONSTANTS-START
RLF-TimersAndConstants ::= SEQUENCE {
   t310 [0] ENUMERATED { ms0(0), ms50(1), ms100(2), ms200(3), ms500(4), 
      ms1000(5), ms2000(6), ms4000(7), ms6000(8) },
   n310 [1] ENUMERATED { n1(0), n2(1), n3(2), n4(3), n6(4), n8(5), n10(6), 
      n20(7) },
   n311 [2] ENUMERATED { n1(0), n2(1), n3(2), n4(3), n5(4), n6(5), n8(6), 
      n10(7) },
   ...,
   [[
      t311 [3] ENUMERATED { ms1000(0), ms3000(1), ms5000(2), ms10000(3), 
         ms15000(4), ms20000(5), ms30000(6) }
   ]]
}

TDD-UL-DL-SlotConfig ::= SEQUENCE {
   slotIndex [0] TDD-UL-DL-SlotIndex,
   symbols [1] EXPLICIT CHOICE {
      allDownlink [0] NULL,
      allUplink [1] NULL,
      explicit [2] SEQUENCE {
         nrofDownlinkSymbols [0] INTEGER (1..maxNrofSymbols-1) OPTIONAL, -- Need S
         nrofUplinkSymbols [1] INTEGER (1..maxNrofSymbols-1) OPTIONAL -- Need S
      }
   }
}

-- TAG-TDD-UL-DL-CONFIGCOMMON-STOP
-- TAG-TDD-UL-DL-CONFIGDEDICATED-START
TDD-UL-DL-ConfigDedicated ::= SEQUENCE {
   slotSpecificConfigurationsToAddModList [0] SEQUENCE (SIZE (1..maxNrofSlots)) OF 
      TDD-UL-DL-SlotConfig OPTIONAL, -- Need N
   slotSpecificConfigurationsToReleaseList [1] SEQUENCE (SIZE (1..maxNrofSlots)) OF 
      TDD-UL-DL-SlotIndex OPTIONAL,
   ...
}

INT-ConfigurationPerServingCell ::= SEQUENCE {
   servingCellId [0] ServCellIndex,
   positionInDCI [1] INTEGER (0..maxINT-DCI-PayloadSize-1)
}

-- TAG-DOWNLINKCONFIGCOMMONSIB-STOP
-- TAG-DOWNLINKPREEMPTION-START
DownlinkPreemption ::= SEQUENCE {
   int-RNTI [0] RNTI-Value,
   timeFrequencySet [1] ENUMERATED { set0(0), set1(1) },
   dci-PayloadSize [2] INTEGER (0..maxINT-DCI-PayloadSize),
   int-ConfigurationPerServingCell [3] SEQUENCE (SIZE (1..maxNrofServingCells)) OF 
      INT-ConfigurationPerServingCell,
   ...
}

-- TAG-PUSCH-TIMEDOMAINRESOURCEALLOCATIONLIST-STOP
-- TAG-PUSCH-TPC-COMMANDCONFIG-START
PUSCH-TPC-CommandConfig ::= SEQUENCE {
   tpc-Index [0] INTEGER (1..15) OPTIONAL, -- Cond SUL
   tpc-IndexSUL [1] INTEGER (1..15) OPTIONAL, -- Cond SUL-Only
   targetCell [2] ServCellIndex OPTIONAL,
   ...
}

-- TAG-PUCCH-SPATIALRELATIONINFO-STOP
-- TAG-PUCCH-TPC-COMMANDCONFIG-START
PUCCH-TPC-CommandConfig ::= SEQUENCE {
   tpc-IndexPCell [0] INTEGER (1..15) OPTIONAL, -- Cond PDCCH-OfSpcell
   tpc-IndexPUCCH-SCell [1] INTEGER (1..15) OPTIONAL,
   ...
}

-- TAG-SRS-CONFIG-STOP
-- TAG-SRS-TPC-COMMANDCONFIG-START
SRS-TPC-CommandConfig ::= SEQUENCE {
   startingBitOfFormat2-3 [0] INTEGER (1..31) OPTIONAL, -- Need R
   fieldTypeFormat2-3 [1] INTEGER (0..1) OPTIONAL,
   ...,
   [[
      startingBitOfFormat2-3SUL [2] INTEGER (1..31) OPTIONAL
   ]]
}

-- TAG-PCI-RANGEINDEXLIST-STOP
-- TAG-PDCCH-CONFIG-START
PDCCH-Config ::= SEQUENCE {
   controlResourceSetToAddModList [0] SEQUENCE (SIZE (1..3)) OF 
      ControlResourceSet OPTIONAL, -- Need N
   controlResourceSetToReleaseList [1] SEQUENCE (SIZE (1..3)) OF 
      ControlResourceSetId OPTIONAL, -- Need N
   searchSpacesToAddModList [2] SEQUENCE (SIZE (1..10)) OF SearchSpace OPTIONAL, -- Need N
   searchSpacesToReleaseList [3] SEQUENCE (SIZE (1..10)) OF SearchSpaceId OPTIONAL
      , -- Need N
   downlinkPreemption [4] EXPLICIT CHOICE {
      release [0] NULL,
      setup [1] EXPLICIT DownlinkPreemption
   } OPTIONAL, -- Need M
   tpc-PUSCH [5] EXPLICIT CHOICE {
      release [0] NULL,
      setup [1] EXPLICIT PUSCH-TPC-CommandConfig
   } OPTIONAL, -- Need M
   tpc-PUCCH [6] EXPLICIT CHOICE {
      release [0] NULL,
      setup [1] EXPLICIT PUCCH-TPC-CommandConfig
   } OPTIONAL, -- Need M
   tpc-SRS [7] EXPLICIT CHOICE {
      release [0] NULL,
      setup [1] EXPLICIT SRS-TPC-CommandConfig
   } OPTIONAL,
   ...
}

-- TAG-PRB-ID-STOP
-- TAG-PTRS-DOWNLINKCONFIG-START
PTRS-DownlinkConfig ::= SEQUENCE {
   frequencyDensity [0] SEQUENCE (SIZE (2)) OF INTEGER (1..276) OPTIONAL, -- Need S
   timeDensity [1] SEQUENCE (SIZE (3)) OF INTEGER (0..29) OPTIONAL, -- Need S
   epre-Ratio [2] INTEGER (0..3) OPTIONAL, -- Need S
   resourceElementOffset [3] ENUMERATED { offset01(0), offset10(1), offset11(2)
       } OPTIONAL,
   ...
}

-- TAG-DEDICATED-NAS-MESSAGE-STOP
-- TAG-DMRS-DOWNLINKCONFIG-START
DMRS-DownlinkConfig ::= SEQUENCE {
   dmrs-Type [0] ENUMERATED { type2(0) } OPTIONAL, -- Need S
   dmrs-AdditionalPosition [1] ENUMERATED { pos0(0), pos1(1), pos3(2) }
       OPTIONAL, -- Need S
   maxLength [2] ENUMERATED { len2(0) } OPTIONAL, -- Need S
   scramblingID0 [3] INTEGER (0..65535) OPTIONAL, -- Need S
   scramblingID1 [4] INTEGER (0..65535) OPTIONAL, -- Need S
   phaseTrackingRS [5] EXPLICIT CHOICE {
      release [0] NULL,
      setup [1] EXPLICIT PTRS-DownlinkConfig
   } OPTIONAL,
   ...
}

QCL-Info ::= SEQUENCE {
   cell [0] ServCellIndex OPTIONAL, -- Need R
   bwp-Id [1] BWP-Id OPTIONAL, -- Cond CSI-RS-Indicated
   referenceSignal [2] EXPLICIT CHOICE {
      csi-rs [0] NZP-CSI-RS-ResourceId,
      ssb [1] SSB-Index
   },
   qcl-Type [3] ENUMERATED { typeA(0), typeB(1), typeC(2), typeD(3) },
   ...
}

-- TAG-TAG-CONFIG-STOP
-- TAG-TCI-STATE-START
TCI-State ::= SEQUENCE {
   tci-StateId [0] TCI-StateId,
   qcl-Type1 [1] QCL-Info,
   qcl-Type2 [2] QCL-Info OPTIONAL,
   ...
}

RateMatchPatternGroup ::= SEQUENCE (SIZE (1..maxNrofRateMatchPatternsPerGroup)) OF CHOICE {
   cellLevel [0] RateMatchPatternId,
   bwpLevel [1] RateMatchPatternId
}

-- TAG-CSI-APERIODICTRIGGERSTATELIST-STOP
-- TAG-CSI-FREQUENCYOCCUPATION-START
CSI-FrequencyOccupation ::= SEQUENCE {
   startingRB [0] INTEGER (0..maxNrofPhysicalResourceBlocks-1),
   nrofRBs [1] INTEGER (24..maxNrofPhysicalResourceBlocksPlus1),
   ...
}

-- TAG-CSI-RS-RESOURCECONFIGMOBILITY-STOP
-- TAG-CSI-RS-RESOURCEMAPPING-START
CSI-RS-ResourceMapping ::= SEQUENCE {
   frequencyDomainAllocation [0] EXPLICIT CHOICE {
      row1 [0] BIT STRING  (SIZE (4)),
      row2 [1] BIT STRING  (SIZE (12)),
      row4 [2] BIT STRING  (SIZE (3)),
      other [3] BIT STRING  (SIZE (6))
   },
   nrofPorts [1] ENUMERATED { p1(0), p2(1), p4(2), p8(3), p12(4), p16(5), 
      p24(6), p32(7) },
   firstOFDMSymbolInTimeDomain [2] INTEGER (0..13),
   firstOFDMSymbolInTimeDomain2 [3] INTEGER (2..12) OPTIONAL, -- Need R
   cdm-Type [4] ENUMERATED { noCDM(0), fd-CDM2(1), cdm4-FD2-TD2(2), 
      cdm8-FD2-TD4(3) },
   density [5] EXPLICIT CHOICE {
      dot5 [0] ENUMERATED { evenPRBs(0), oddPRBs(1) },
      one [1] NULL,
      three [2] NULL,
      spare [3] NULL
   },
   freqBand [6] CSI-FrequencyOccupation,
   ...
}

-- TAG-CSI-RESOURCECONFIGID-STOP
-- TAG-CSI-RESOURCEPERIODICITYANDOFFSET-START
CSI-ResourcePeriodicityAndOffset ::= CHOICE {
   slots4 [0] INTEGER (0..3),
   slots5 [1] INTEGER (0..4),
   slots8 [2] INTEGER (0..7),
   slots10 [3] INTEGER (0..9),
   slots16 [4] INTEGER (0..15),
   slots20 [5] INTEGER (0..19),
   slots32 [6] INTEGER (0..31),
   slots40 [7] INTEGER (0..39),
   slots64 [8] INTEGER (0..63),
   slots80 [9] INTEGER (0..79),
   slots160 [10] INTEGER (0..159),
   slots320 [11] INTEGER (0..319),
   slots640 [12] INTEGER (0..639)
}

-- TAG-UPLINKTXDIRECTCURRENTLIST-STOP
-- TAG-ZP-CSI-RS-RESOURCE-START
ZP-CSI-RS-Resource ::= SEQUENCE {
   zp-CSI-RS-ResourceId [0] ZP-CSI-RS-ResourceId,
   resourceMapping [1] CSI-RS-ResourceMapping,
   periodicityAndOffset [2] EXPLICIT CSI-ResourcePeriodicityAndOffset OPTIONAL,
   ...
}

-- TAG-ZP-CSI-RS-RESOURCE-STOP
-- TAG-ZP-CSI-RS-RESOURCESET-START
ZP-CSI-RS-ResourceSet ::= SEQUENCE {
   zp-CSI-RS-ResourceSetId [0] ZP-CSI-RS-ResourceSetId,
   zp-CSI-RS-ResourceIdList [1] SEQUENCE (SIZE (1..maxNrofZP-CSI-RS-ResourcesPerSet)) OF ZP-CSI-RS-ResourceId,
   ...
}

-- TAG-PDCP-CONFIG-STOP
-- TAG-PDSCH-CONFIG-START
PDSCH-Config ::= SEQUENCE {
   dataScramblingIdentityPDSCH [0] INTEGER (0..1023) OPTIONAL, -- Need S
   dmrs-DownlinkForPDSCH-MappingTypeA [1] EXPLICIT CHOICE {
      release [0] NULL,
      setup [1] EXPLICIT DMRS-DownlinkConfig
   } OPTIONAL, -- Need M
   dmrs-DownlinkForPDSCH-MappingTypeB [2] EXPLICIT CHOICE {
      release [0] NULL,
      setup [1] EXPLICIT DMRS-DownlinkConfig
   } OPTIONAL, -- Need M
   tci-StatesToAddModList [3] SEQUENCE (SIZE (1..maxNrofTCI-States)) OF TCI-State OPTIONAL, -- Need N
   tci-StatesToReleaseList [4] SEQUENCE (SIZE (1..maxNrofTCI-States)) OF TCI-StateId OPTIONAL, -- Need N
   vrb-ToPRB-Interleaver [5] ENUMERATED { n2(0), n4(1) } OPTIONAL, -- Need S
   resourceAllocation [6] ENUMERATED { resourceAllocationType0(0), 
      resourceAllocationType1(1), dynamicSwitch(2) },
   pdsch-TimeDomainAllocationList [7] EXPLICIT CHOICE {
      release [0] NULL,
      setup [1] EXPLICIT PDSCH-TimeDomainResourceAllocationList
   } OPTIONAL, -- Need M
   pdsch-AggregationFactor [8] ENUMERATED { n2(0), n4(1), n8(2) } OPTIONAL, -- Need S
   rateMatchPatternToAddModList [9] SEQUENCE (SIZE (1..maxNrofRateMatchPatterns)) OF RateMatchPattern
       OPTIONAL, -- Need N
   rateMatchPatternToReleaseList [10] SEQUENCE (SIZE (1..maxNrofRateMatchPatterns)) OF 
      RateMatchPatternId OPTIONAL, -- Need N
   rateMatchPatternGroup1 [11] RateMatchPatternGroup OPTIONAL, -- Need R
   rateMatchPatternGroup2 [12] RateMatchPatternGroup OPTIONAL, -- Need R
   rbg-Size [13] ENUMERATED { config1(0), config2(1) },
   mcs-Table [14] ENUMERATED { qam256(0), qam64LowSE(1) } OPTIONAL, -- Need S
   maxNrofCodeWordsScheduledByDCI [15] ENUMERATED { n1(0), n2(1) } OPTIONAL, -- Need R
   prb-BundlingType [16] EXPLICIT CHOICE {
      staticBundling [0] SEQUENCE {
         bundleSize [0] ENUMERATED { n4(0), wideband(1) } OPTIONAL -- Need S
      },
      dynamicBundling [1] SEQUENCE {
         bundleSizeSet1 [0] ENUMERATED { n4(0), wideband(1), n2-wideband(2), 
            n4-wideband(3) } OPTIONAL, -- Need S
         bundleSizeSet2 [1] ENUMERATED { n4(0), wideband(1) } OPTIONAL -- Need S
      }
   },
   zp-CSI-RS-ResourceToAddModList [17] SEQUENCE (SIZE (1..maxNrofZP-CSI-RS-Resources)) OF 
      ZP-CSI-RS-Resource OPTIONAL,
                                                                                                                             -- Need N
   zp-CSI-RS-ResourceToReleaseList [18] SEQUENCE (SIZE (1..maxNrofZP-CSI-RS-Resources)) OF 
      ZP-CSI-RS-ResourceId OPTIONAL,
                                                                                                                             -- Need N
   aperiodic-ZP-CSI-RS-ResourceSetsToAddModList [19] SEQUENCE (SIZE (1..maxNrofZP-CSI-RS-ResourceSets)) OF 
      ZP-CSI-RS-ResourceSet OPTIONAL,
                                                                                                                             -- Need N
   aperiodic-ZP-CSI-RS-ResourceSetsToReleaseList [20] SEQUENCE (SIZE (1..maxNrofZP-CSI-RS-ResourceSets)) OF 
      ZP-CSI-RS-ResourceSetId OPTIONAL,
                                                                                                                             -- Need N
   sp-ZP-CSI-RS-ResourceSetsToAddModList [21] SEQUENCE (SIZE (1..maxNrofZP-CSI-RS-ResourceSets)) OF 
      ZP-CSI-RS-ResourceSet OPTIONAL,
                                                                                                                             -- Need N
   sp-ZP-CSI-RS-ResourceSetsToReleaseList [22] SEQUENCE (SIZE (1..maxNrofZP-CSI-RS-ResourceSets)) OF 
      ZP-CSI-RS-ResourceSetId OPTIONAL,
                                                                                                                             -- Need N
   p-ZP-CSI-RS-ResourceSet [23] EXPLICIT CHOICE {
      release [0] NULL,
      setup [1] EXPLICIT ZP-CSI-RS-ResourceSet
   } OPTIONAL,
   ...
}

-- TAG-SPEEDSTATESCALEFACTORS-STOP
-- TAG-SPS-CONFIG-START
SPS-Config ::= SEQUENCE {
   periodicity [0] ENUMERATED { ms10(0), ms20(1), ms32(2), ms40(3), ms64(4), 
      ms80(5), ms128(6), ms160(7), ms320(8), ms640(9), spare6(10), spare5(11), 
      spare4(12), spare3(13), spare2(14), spare1(15) },
   nrofHARQ-Processes [1] INTEGER (1..8),
   n1PUCCH-AN [2] PUCCH-ResourceId OPTIONAL, -- Need M
   mcs-Table [3] ENUMERATED { qam64LowSE(0) } OPTIONAL,
   ...
}

RadioLinkMonitoringRS ::= SEQUENCE {
   radioLinkMonitoringRS-Id [0] RadioLinkMonitoringRS-Id,
   purpose [1] ENUMERATED { beamFailure(0), rlf(1), both(2) },
   detectionResource [2] EXPLICIT CHOICE {
      ssb-Index [0] SSB-Index,
      csi-RS-Index [1] NZP-CSI-RS-ResourceId
   },
   ...
}

-- TAG-RADIOBEARERCONFIG-STOP
-- TAG-RADIOLINKMONITORINGCONFIG-START
RadioLinkMonitoringConfig ::= SEQUENCE {
   failureDetectionResourcesToAddModList [0] SEQUENCE (SIZE (1..maxNrofFailureDetectionResources)) OF 
      RadioLinkMonitoringRS OPTIONAL,
                                                                                                                             -- Need N
   failureDetectionResourcesToReleaseList [1] SEQUENCE (SIZE (1..maxNrofFailureDetectionResources)) OF 
      RadioLinkMonitoringRS-Id OPTIONAL,
                                                                                                                             -- Need N
   beamFailureInstanceMaxCount [2] ENUMERATED { n1(0), n2(1), n3(2), n4(3), 
      n5(4), n6(5), n8(6), n10(7) } OPTIONAL, -- Need R
   beamFailureDetectionTimer [3] ENUMERATED { pbfd1(0), pbfd2(1), pbfd3(2), 
      pbfd4(3), pbfd5(4), pbfd6(5), pbfd8(6), pbfd10(7) } OPTIONAL,
   ...
}

-- TAG-BWP-DOWNLINKCOMMON-STOP
-- TAG-BWP-DOWNLINKDEDICATED-START
BWP-DownlinkDedicated ::= SEQUENCE {
   pdcch-Config [0] EXPLICIT CHOICE {
      release [0] NULL,
      setup [1] EXPLICIT PDCCH-Config
   } OPTIONAL, -- Need M
   pdsch-Config [1] EXPLICIT CHOICE {
      release [0] NULL,
      setup [1] EXPLICIT PDSCH-Config
   } OPTIONAL, -- Need M
   sps-Config [2] EXPLICIT CHOICE {
      release [0] NULL,
      setup [1] EXPLICIT SPS-Config
   } OPTIONAL, -- Need M
   radioLinkMonitoringConfig [3] EXPLICIT CHOICE {
      release [0] NULL,
      setup [1] EXPLICIT RadioLinkMonitoringConfig
   } OPTIONAL,
   ...
}

-- TAG-BWP-STOP
-- TAG-BWP-DOWNLINK-START
BWP-Downlink ::= SEQUENCE {
   bwp-Id [0] BWP-Id,
   bwp-Common [1] BWP-DownlinkCommon OPTIONAL, -- Cond SetupOtherBWP
   bwp-Dedicated [2] BWP-DownlinkDedicated OPTIONAL,
   ...
}

-- A set with one or more PUCCH resources
PUCCH-ResourceSet ::= SEQUENCE {
   pucch-ResourceSetId [0] PUCCH-ResourceSetId,
   resourceList [1] SEQUENCE (SIZE (1..maxNrofPUCCH-ResourcesPerSet)) OF PUCCH-ResourceId,
   maxPayloadSize [2] INTEGER (4..256) OPTIONAL -- Need R
}

PUCCH-format0 ::= SEQUENCE {
   initialCyclicShift [0] INTEGER (0..11),
   nrofSymbols [1] INTEGER (1..2),
   startingSymbolIndex [2] INTEGER (0..13)
}

PUCCH-format1 ::= SEQUENCE {
   initialCyclicShift [0] INTEGER (0..11),
   nrofSymbols [1] INTEGER (4..14),
   startingSymbolIndex [2] INTEGER (0..10),
   timeDomainOCC [3] INTEGER (0..6)
}

PUCCH-format2 ::= SEQUENCE {
   nrofPRBs [0] INTEGER (1..16),
   nrofSymbols [1] INTEGER (1..2),
   startingSymbolIndex [2] INTEGER (0..13)
}

PUCCH-format3 ::= SEQUENCE {
   nrofPRBs [0] INTEGER (1..16),
   nrofSymbols [1] INTEGER (4..14),
   startingSymbolIndex [2] INTEGER (0..10)
}

PUCCH-format4 ::= SEQUENCE {
   nrofSymbols [0] INTEGER (4..14),
   occ-Length [1] ENUMERATED { n2(0), n4(1) },
   occ-Index [2] ENUMERATED { n0(0), n1(1), n2(2), n3(3) },
   startingSymbolIndex [3] INTEGER (0..10)
}

PUCCH-Resource ::= SEQUENCE {
   pucch-ResourceId [0] PUCCH-ResourceId,
   startingPRB [1] PRB-Id,
   intraSlotFrequencyHopping [2] ENUMERATED { enabled(0) } OPTIONAL, -- Need R
   secondHopPRB [3] PRB-Id OPTIONAL, -- Need R
   format [4] EXPLICIT CHOICE {
      format0 [0] PUCCH-format0,
      format1 [1] PUCCH-format1,
      format2 [2] PUCCH-format2,
      format3 [3] PUCCH-format3,
      format4 [4] PUCCH-format4
   }
}

PUCCH-FormatConfig ::= SEQUENCE {
   interslotFrequencyHopping [0] ENUMERATED { enabled(0) } OPTIONAL, -- Need R
   additionalDMRS [1] ENUMERATED { true(0) } OPTIONAL, -- Need R
   maxCodeRate [2] PUCCH-MaxCodeRate OPTIONAL, -- Need R
   nrofSlots [3] ENUMERATED { n2(0), n4(1), n8(2) } OPTIONAL, -- Need S
   pi2BPSK [4] ENUMERATED { enabled(0) } OPTIONAL, -- Need R
   simultaneousHARQ-ACK-CSI [5] ENUMERATED { true(0) } OPTIONAL -- Need R
}

-- TAG-SCHEDULINGREQUESTID-STOP
-- TAG-SCHEDULINGREQUESTRESOURCECONFIG-START
SchedulingRequestResourceConfig ::= SEQUENCE {
   schedulingRequestResourceId [0] SchedulingRequestResourceId,
   schedulingRequestID [1] SchedulingRequestId,
   periodicityAndOffset [2] EXPLICIT CHOICE {
      sym2 [0] NULL,
      sym6or7 [1] NULL,
      sl1 [2] NULL, -- Recurs in every slot
      sl2 [3] INTEGER (0..1),
      sl4 [4] INTEGER (0..3),
      sl5 [5] INTEGER (0..4),
      sl8 [6] INTEGER (0..7),
      sl10 [7] INTEGER (0..9),
      sl16 [8] INTEGER (0..15),
      sl20 [9] INTEGER (0..19),
      sl40 [10] INTEGER (0..39),
      sl80 [11] INTEGER (0..79),
      sl160 [12] INTEGER (0..159),
      sl320 [13] INTEGER (0..319),
      sl640 [14] INTEGER (0..639)
   } OPTIONAL, -- Need M
   resource [3] PUCCH-ResourceId OPTIONAL -- Need M
}

-- TAG-PUCCH-POWERCONTROL-STOP
-- TAG-PUCCH-SPATIALRELATIONINFO-START
PUCCH-SpatialRelationInfo ::= SEQUENCE {
   pucch-SpatialRelationInfoId [0] PUCCH-SpatialRelationInfoId,
   servingCellId [1] ServCellIndex OPTIONAL, -- Need S
   referenceSignal [2] EXPLICIT CHOICE {
      ssb-Index [0] SSB-Index,
      csi-RS-Index [1] NZP-CSI-RS-ResourceId,
      srs [2] SEQUENCE {
         resource [0] SRS-ResourceId,
         uplinkBWP [1] BWP-Id
      }
   },
   pucch-PathlossReferenceRS-Id [3] PUCCH-PathlossReferenceRS-Id,
   p0-PUCCH-Id [4] P0-PUCCH-Id,
   closedLoopIndex [5] ENUMERATED { i0(0), i1(1) }
}

P0-PUCCH ::= SEQUENCE {
   p0-PUCCH-Id [0] P0-PUCCH-Id,
   p0-PUCCH-Value [1] INTEGER (-16..15)
}

PUCCH-PathlossReferenceRS ::= SEQUENCE {
   pucch-PathlossReferenceRS-Id [0] PUCCH-PathlossReferenceRS-Id,
   referenceSignal [1] EXPLICIT CHOICE {
      ssb-Index [0] SSB-Index,
      csi-RS-Index [1] NZP-CSI-RS-ResourceId
   }
}

-- TAG-PUCCH-PATHLOSSREFERENCERS-ID-STOP
-- TAG-PUCCH-POWERCONTROL-START
PUCCH-PowerControl ::= SEQUENCE {
   deltaF-PUCCH-f0 [0] INTEGER (-16..15) OPTIONAL, -- Need R
   deltaF-PUCCH-f1 [1] INTEGER (-16..15) OPTIONAL, -- Need R
   deltaF-PUCCH-f2 [2] INTEGER (-16..15) OPTIONAL, -- Need R
   deltaF-PUCCH-f3 [3] INTEGER (-16..15) OPTIONAL, -- Need R
   deltaF-PUCCH-f4 [4] INTEGER (-16..15) OPTIONAL, -- Need R
   p0-Set [5] SEQUENCE (SIZE (1..maxNrofPUCCH-P0-PerSet)) OF P0-PUCCH OPTIONAL, -- Need M
   pathlossReferenceRSs [6] SEQUENCE (SIZE (1..maxNrofPUCCH-PathlossReferenceRSs)) OF PUCCH-PathlossReferenceRS
       OPTIONAL,
                                                                                                                           -- Need M
   twoPUCCH-PC-AdjustmentStates [7] ENUMERATED { twoStates(0) } OPTIONAL,
   ...
}

-- TAG-PTRS-UPLINKCONFIG-STOP
-- TAG-PUCCH-CONFIG-START
PUCCH-Config ::= SEQUENCE {
   resourceSetToAddModList [0] SEQUENCE (SIZE (1..maxNrofPUCCH-ResourceSets)) OF PUCCH-ResourceSet
       OPTIONAL, -- Need N
   resourceSetToReleaseList [1] SEQUENCE (SIZE (1..maxNrofPUCCH-ResourceSets)) OF PUCCH-ResourceSetId
       OPTIONAL, -- Need N
   resourceToAddModList [2] SEQUENCE (SIZE (1..maxNrofPUCCH-Resources)) OF PUCCH-Resource OPTIONAL, -- Need N
   resourceToReleaseList [3] SEQUENCE (SIZE (1..maxNrofPUCCH-Resources)) OF PUCCH-ResourceId OPTIONAL,
       -- Need N
   format1 [4] EXPLICIT CHOICE {
      release [0] NULL,
      setup [1] EXPLICIT PUCCH-FormatConfig
   } OPTIONAL, -- Need M
   format2 [5] EXPLICIT CHOICE {
      release [0] NULL,
      setup [1] EXPLICIT PUCCH-FormatConfig
   } OPTIONAL, -- Need M
   format3 [6] EXPLICIT CHOICE {
      release [0] NULL,
      setup [1] EXPLICIT PUCCH-FormatConfig
   } OPTIONAL, -- Need M
   format4 [7] EXPLICIT CHOICE {
      release [0] NULL,
      setup [1] EXPLICIT PUCCH-FormatConfig
   } OPTIONAL, -- Need M
   schedulingRequestResourceToAddModList [8] SEQUENCE (SIZE (1..maxNrofSR-Resources)) OF 
      SchedulingRequestResourceConfig OPTIONAL,
                                                                                                                             -- Need N
   schedulingRequestResourceToReleaseList [9] SEQUENCE (SIZE (1..maxNrofSR-Resources)) OF 
      SchedulingRequestResourceId OPTIONAL,
                                                                                                                             -- Need N
   multi-CSI-PUCCH-ResourceList [10] SEQUENCE (SIZE (1..2)) OF PUCCH-ResourceId
       OPTIONAL, -- Need M
   dl-DataToUL-ACK [11] SEQUENCE (SIZE (1..8)) OF INTEGER (0..15) OPTIONAL, -- Need M
   spatialRelationInfoToAddModList [12] SEQUENCE (SIZE (1..maxNrofSpatialRelationInfos)) OF 
      PUCCH-SpatialRelationInfo OPTIONAL,
                                                                                                                             -- Need N
   spatialRelationInfoToReleaseList [13] SEQUENCE (SIZE (1..maxNrofSpatialRelationInfos)) OF 
      PUCCH-SpatialRelationInfoId OPTIONAL,
                                                                                                                             -- Need N
   pucch-PowerControl [14] PUCCH-PowerControl OPTIONAL,
   ...
}

-- TAG-PTRS-DOWNLINKCONFIG-STOP
-- TAG-PTRS-UPLINKCONFIG-START
PTRS-UplinkConfig ::= SEQUENCE {
   transformPrecoderDisabled [0] SEQUENCE {
      frequencyDensity [0] SEQUENCE (SIZE (2)) OF INTEGER (1..276) OPTIONAL, -- Need S
      timeDensity [1] SEQUENCE (SIZE (3)) OF INTEGER (0..29) OPTIONAL, -- Need S
      maxNrofPorts [2] ENUMERATED { n1(0), n2(1) },
      resourceElementOffset [3] ENUMERATED { offset01(0), offset10(1), 
         offset11(2) } OPTIONAL, -- Need S
      ptrs-Power [4] ENUMERATED { p00(0), p01(1), p10(2), p11(3) }
   } OPTIONAL, -- Need R
   transformPrecoderEnabled [1] SEQUENCE {
      sampleDensity [0] SEQUENCE (SIZE (5)) OF INTEGER (1..276),
      timeDensityTransformPrecoding [1] ENUMERATED { d2(0) } OPTIONAL -- Need S
   } OPTIONAL,
   ...
}

-- TAG-DMRS-DOWNLINKCONFIG-STOP
-- TAG-DMRS-UPLINKCONFIG-START
DMRS-UplinkConfig ::= SEQUENCE {
   dmrs-Type [0] ENUMERATED { type2(0) } OPTIONAL, -- Need S
   dmrs-AdditionalPosition [1] ENUMERATED { pos0(0), pos1(1), pos3(2) }
       OPTIONAL, -- Need S
   phaseTrackingRS [2] EXPLICIT CHOICE {
      release [0] NULL,
      setup [1] EXPLICIT PTRS-UplinkConfig
   } OPTIONAL, -- Need M
   maxLength [3] ENUMERATED { len2(0) } OPTIONAL, -- Need S
   transformPrecodingDisabled [4] SEQUENCE {
      scramblingID0 [0] INTEGER (0..65535) OPTIONAL, -- Need S
      scramblingID1 [1] INTEGER (0..65535) OPTIONAL,
      ...
   } OPTIONAL, -- Need R
   transformPrecodingEnabled [5] SEQUENCE {
      nPUSCH-Identity [0] INTEGER (0..1007) OPTIONAL, -- Need S
      sequenceGroupHopping [1] ENUMERATED { disabled(0) } OPTIONAL, -- Need S
      sequenceHopping [2] ENUMERATED { enabled(0) } OPTIONAL,
      ...
   } OPTIONAL,
   ...
}

P0-PUSCH-AlphaSet ::= SEQUENCE {
   p0-PUSCH-AlphaSetId [0] P0-PUSCH-AlphaSetId,
   p0 [1] INTEGER (-16..15) OPTIONAL, -- Need S
   alpha [2] Alpha OPTIONAL -- Need S
}

PUSCH-PathlossReferenceRS ::= SEQUENCE {
   pusch-PathlossReferenceRS-Id [0] PUSCH-PathlossReferenceRS-Id,
   referenceSignal [1] EXPLICIT CHOICE {
      ssb-Index [0] SSB-Index,
      csi-RS-Index [1] NZP-CSI-RS-ResourceId
   }
}

SRI-PUSCH-PowerControl ::= SEQUENCE {
   sri-PUSCH-PowerControlId [0] SRI-PUSCH-PowerControlId,
   sri-PUSCH-PathlossReferenceRS-Id [1] PUSCH-PathlossReferenceRS-Id,
   sri-P0-PUSCH-AlphaSetId [2] P0-PUSCH-AlphaSetId,
   sri-PUSCH-ClosedLoopIndex [3] ENUMERATED { i0(0), i1(1) }
}

-- TAG-PUSCH-CONFIGCOMMON-STOP
-- TAG-PUSCH-POWERCONTROL-START
PUSCH-PowerControl ::= SEQUENCE {
   tpc-Accumulation [0] ENUMERATED { disabled(0) } OPTIONAL, -- Need S
   msg3-Alpha [1] Alpha OPTIONAL, -- Need S
   p0-NominalWithoutGrant [2] INTEGER (-202..24) OPTIONAL, -- Need M
   p0-AlphaSets [3] SEQUENCE (SIZE (1..maxNrofP0-PUSCH-AlphaSets)) OF P0-PUSCH-AlphaSet OPTIONAL, -- Need M
   pathlossReferenceRSToAddModList [4] SEQUENCE (SIZE (1..maxNrofPUSCH-PathlossReferenceRSs)) OF 
      PUSCH-PathlossReferenceRS OPTIONAL,
                                                                                                                           -- Need N
   pathlossReferenceRSToReleaseList [5] SEQUENCE (SIZE (1..maxNrofPUSCH-PathlossReferenceRSs)) OF 
      PUSCH-PathlossReferenceRS-Id OPTIONAL,
                                                                                                                            -- Need N
   twoPUSCH-PC-AdjustmentStates [6] ENUMERATED { twoStates(0) } OPTIONAL, -- Need S
   deltaMCS [7] ENUMERATED { enabled(0) } OPTIONAL, -- Need S
   sri-PUSCH-MappingToAddModList [8] SEQUENCE (SIZE (1..maxNrofSRI-PUSCH-Mappings)) OF 
      SRI-PUSCH-PowerControl OPTIONAL,
                                                                                                                           -- Need N
   sri-PUSCH-MappingToReleaseList [9] SEQUENCE (SIZE (1..maxNrofSRI-PUSCH-Mappings)) OF 
      SRI-PUSCH-PowerControlId OPTIONAL
                                                                                                                           -- Need N
}

-- TAG-BEAMFAILURERECOVERYCONFIG-STOP
-- TAG-BETAOFFSETS-START
BetaOffsets ::= SEQUENCE {
   betaOffsetACK-Index1 [0] INTEGER (0..31) OPTIONAL, -- Need S
   betaOffsetACK-Index2 [1] INTEGER (0..31) OPTIONAL, -- Need S
   betaOffsetACK-Index3 [2] INTEGER (0..31) OPTIONAL, -- Need S
   betaOffsetCSI-Part1-Index1 [3] INTEGER (0..31) OPTIONAL, -- Need S
   betaOffsetCSI-Part1-Index2 [4] INTEGER (0..31) OPTIONAL, -- Need S
   betaOffsetCSI-Part2-Index1 [5] INTEGER (0..31) OPTIONAL, -- Need S
   betaOffsetCSI-Part2-Index2 [6] INTEGER (0..31) OPTIONAL -- Need S
}

UCI-OnPUSCH ::= SEQUENCE {
   betaOffsets [0] EXPLICIT CHOICE {
      dynamic [0] SEQUENCE (SIZE (4)) OF BetaOffsets,
      semiStatic [1] BetaOffsets
   } OPTIONAL, -- Need M
   scaling [1] ENUMERATED { f0p5(0), f0p65(1), f0p8(2), f1(3) }
}

-- TAG-PUCCH-TPC-COMMANDCONFIG-STOP
-- TAG-PUSCH-CONFIG-START
PUSCH-Config ::= SEQUENCE {
   dataScramblingIdentityPUSCH [0] INTEGER (0..1023) OPTIONAL, -- Need S
   txConfig [1] ENUMERATED { codebook(0), nonCodebook(1) } OPTIONAL, -- Need S
   dmrs-UplinkForPUSCH-MappingTypeA [2] EXPLICIT CHOICE {
      release [0] NULL,
      setup [1] EXPLICIT DMRS-UplinkConfig
   } OPTIONAL, -- Need M
   dmrs-UplinkForPUSCH-MappingTypeB [3] EXPLICIT CHOICE {
      release [0] NULL,
      setup [1] EXPLICIT DMRS-UplinkConfig
   } OPTIONAL, -- Need M
   pusch-PowerControl [4] PUSCH-PowerControl OPTIONAL, -- Need M
   frequencyHopping [5] ENUMERATED { intraSlot(0), interSlot(1) } OPTIONAL, -- Need S
   frequencyHoppingOffsetLists [6] SEQUENCE (SIZE (1..4)) OF INTEGER (1..maxNrofPhysicalResourceBlocks-1)
       OPTIONAL,
                                                                                                                             -- Need M
   resourceAllocation [7] ENUMERATED { resourceAllocationType0(0), 
      resourceAllocationType1(1), dynamicSwitch(2) },
   pusch-TimeDomainAllocationList [8] EXPLICIT CHOICE {
      release [0] NULL,
      setup [1] EXPLICIT PUSCH-TimeDomainResourceAllocationList
   } OPTIONAL, -- Need M
   pusch-AggregationFactor [9] ENUMERATED { n2(0), n4(1), n8(2) } OPTIONAL, -- Need S
   mcs-Table [10] ENUMERATED { qam256(0), qam64LowSE(1) } OPTIONAL, -- Need S
   mcs-TableTransformPrecoder [11] ENUMERATED { qam256(0), qam64LowSE(1) }
       OPTIONAL, -- Need S
   transformPrecoder [12] ENUMERATED { enabled(0), disabled(1) } OPTIONAL, -- Need S
   codebookSubset [13] ENUMERATED { fullyAndPartialAndNonCoherent(0), 
      partialAndNonCoherent(1), nonCoherent(2) } OPTIONAL,
                                                                                                                 -- Cond codebookBased
   maxRank [14] INTEGER (1..4) OPTIONAL, -- Cond codebookBased
   rbg-Size [15] ENUMERATED { config2(0) } OPTIONAL, -- Need S
   uci-OnPUSCH [16] EXPLICIT CHOICE {
      release [0] NULL,
      setup [1] EXPLICIT UCI-OnPUSCH
   } OPTIONAL, -- Need M
   tp-pi2BPSK [17] ENUMERATED { enabled(0) } OPTIONAL,
   ...
}

CG-UCI-OnPUSCH ::= CHOICE {
   dynamic [0] SEQUENCE (SIZE (1..4)) OF BetaOffsets,
   semiStatic [1] BetaOffsets
}

-- TAG-CODEBOOKCONFIG-STOP
-- TAG-CONFIGUREDGRANTCONFIG-START
ConfiguredGrantConfig ::= SEQUENCE {
   frequencyHopping [0] ENUMERATED { intraSlot(0), interSlot(1) } OPTIONAL, -- Need S
   cg-DMRS-Configuration [1] DMRS-UplinkConfig,
   mcs-Table [2] ENUMERATED { qam256(0), qam64LowSE(1) } OPTIONAL, -- Need S
   mcs-TableTransformPrecoder [3] ENUMERATED { qam256(0), qam64LowSE(1) }
       OPTIONAL, -- Need S
   uci-OnPUSCH [4] EXPLICIT CHOICE {
      release [0] NULL,
      setup [1] EXPLICIT CG-UCI-OnPUSCH
   } OPTIONAL, -- Need M
   resourceAllocation [5] ENUMERATED { resourceAllocationType0(0), 
      resourceAllocationType1(1), dynamicSwitch(2) },
   rbg-Size [6] ENUMERATED { config2(0) } OPTIONAL, -- Need S
   powerControlLoopToUse [7] ENUMERATED { n0(0), n1(1) },
   p0-PUSCH-Alpha [8] P0-PUSCH-AlphaSetId,
   transformPrecoder [9] ENUMERATED { enabled(0), disabled(1) } OPTIONAL, -- Need S
   nrofHARQ-Processes [10] INTEGER (1..16),
   repK [11] ENUMERATED { n1(0), n2(1), n4(2), n8(3) },
   repK-RV [12] ENUMERATED { s1-0231(0), s2-0303(1), s3-0000(2) } OPTIONAL, -- Need R
   periodicity [13] ENUMERATED { sym2(0), sym7(1), sym1x14(2), sym2x14(3), 
      sym4x14(4), sym5x14(5), sym8x14(6), sym10x14(7), sym16x14(8), sym20x14(9)
      , sym32x14(10), sym40x14(11), sym64x14(12), sym80x14(13), sym128x14(14), 
      sym160x14(15), sym256x14(16), sym320x14(17), sym512x14(18), sym640x14(19)
      , sym1024x14(20), sym1280x14(21), sym2560x14(22), sym5120x14(23), 
      sym6(24), sym1x12(25), sym2x12(26), sym4x12(27), sym5x12(28), sym8x12(29)
      , sym10x12(30), sym16x12(31), sym20x12(32), sym32x12(33), sym40x12(34), 
      sym64x12(35), sym80x12(36), sym128x12(37), sym160x12(38), sym256x12(39), 
      sym320x12(40), sym512x12(41), sym640x12(42), sym1280x12(43), 
      sym2560x12(44) },
   configuredGrantTimer [14] INTEGER (1..64) OPTIONAL, -- Need R
   rrc-ConfiguredUplinkGrant [15] SEQUENCE {
      timeDomainOffset [0] INTEGER (0..5119),
      timeDomainAllocation [1] INTEGER (0..15),
      frequencyDomainAllocation [2] BIT STRING  (SIZE (18)),
      antennaPort [3] INTEGER (0..31),
      dmrs-SeqInitialization [4] INTEGER (0..1) OPTIONAL, -- Need R
      precodingAndNumberOfLayers [5] INTEGER (0..63),
      srs-ResourceIndicator [6] INTEGER (0..15) OPTIONAL, -- Need R
      mcsAndTBS [7] INTEGER (0..31),
      frequencyHoppingOffset [8] INTEGER (1..maxNrofPhysicalResourceBlocks-1) OPTIONAL, -- Need R
      pathlossReferenceIndex [9] INTEGER (0..maxNrofPUSCH-PathlossReferenceRSs-1),
      ...
   } OPTIONAL,
   ...
}

SRS-ResourceSet ::= SEQUENCE {
   srs-ResourceSetId [0] SRS-ResourceSetId,
   srs-ResourceIdList [1] SEQUENCE (SIZE (1..maxNrofSRS-ResourcesPerSet)) OF SRS-ResourceId OPTIONAL, -- Cond Setup
   resourceType [2] EXPLICIT CHOICE {
      aperiodic [0] SEQUENCE {
         aperiodicSRS-ResourceTrigger [0] INTEGER (1..maxNrofSRS-TriggerStates-1),
         csi-RS [1] NZP-CSI-RS-ResourceId OPTIONAL, -- Cond NonCodebook
         slotOffset [2] INTEGER (1..32) OPTIONAL,
         ...,
         [[
            aperiodicSRS-ResourceTriggerList [3] SEQUENCE (SIZE (1..maxNrofSRS-TriggerStates-2)) OF 
               INTEGER (1..maxNrofSRS-TriggerStates-1) OPTIONAL
         ]]
      },
      semi-persistent [1] SEQUENCE {
         associatedCSI-RS [0] NZP-CSI-RS-ResourceId OPTIONAL,
         ...
      },
      periodic [2] SEQUENCE {
         associatedCSI-RS [0] NZP-CSI-RS-ResourceId OPTIONAL,
         ...
      }
   },
   usage [3] ENUMERATED { beamManagement(0), codebook(1), nonCodebook(2), 
      antennaSwitching(3) },
   alpha [4] Alpha OPTIONAL, -- Need S
   p0 [5] INTEGER (-202..24) OPTIONAL, -- Cond Setup
   pathlossReferenceRS [6] EXPLICIT CHOICE {
      ssb-Index [0] SSB-Index,
      csi-RS-Index [1] NZP-CSI-RS-ResourceId
   } OPTIONAL, -- Need M
   srs-PowerControlAdjustmentStates [7] ENUMERATED { sameAsFci2(0), 
      separateClosedLoop(1) } OPTIONAL,
   ...
}

SRS-PeriodicityAndOffset ::= CHOICE {
   sl1 [0] NULL,
   sl2 [1] INTEGER (0..1),
   sl4 [2] INTEGER (0..3),
   sl5 [3] INTEGER (0..4),
   sl8 [4] INTEGER (0..7),
   sl10 [5] INTEGER (0..9),
   sl16 [6] INTEGER (0..15),
   sl20 [7] INTEGER (0..19),
   sl32 [8] INTEGER (0..31),
   sl40 [9] INTEGER (0..39),
   sl64 [10] INTEGER (0..63),
   sl80 [11] INTEGER (0..79),
   sl160 [12] INTEGER (0..159),
   sl320 [13] INTEGER (0..319),
   sl640 [14] INTEGER (0..639),
   sl1280 [15] INTEGER (0..1279),
   sl2560 [16] INTEGER (0..2559)
}

SRS-SpatialRelationInfo ::= SEQUENCE {
   servingCellId [0] ServCellIndex OPTIONAL, -- Need S
   referenceSignal [1] EXPLICIT CHOICE {
      ssb-Index [0] SSB-Index,
      csi-RS-Index [1] NZP-CSI-RS-ResourceId,
      srs [2] SEQUENCE {
         resourceId [0] SRS-ResourceId,
         uplinkBWP [1] BWP-Id
      }
   }
}

SRS-Resource ::= SEQUENCE {
   srs-ResourceId [0] SRS-ResourceId,
   nrofSRS-Ports [1] ENUMERATED { port1(0), ports2(1), ports4(2) },
   ptrs-PortIndex [2] ENUMERATED { n0(0), n1(1) } OPTIONAL, -- Need R
   transmissionComb [3] EXPLICIT CHOICE {
      n2 [0] SEQUENCE {
         combOffset-n2 [0] INTEGER (0..1),
         cyclicShift-n2 [1] INTEGER (0..7)
      },
      n4 [1] SEQUENCE {
         combOffset-n4 [0] INTEGER (0..3),
         cyclicShift-n4 [1] INTEGER (0..11)
      }
   },
   resourceMapping [4] SEQUENCE {
      startPosition [0] INTEGER (0..5),
      nrofSymbols [1] ENUMERATED { n1(0), n2(1), n4(2) },
      repetitionFactor [2] ENUMERATED { n1(0), n2(1), n4(2) }
   },
   freqDomainPosition [5] INTEGER (0..67),
   freqDomainShift [6] INTEGER (0..268),
   freqHopping [7] SEQUENCE {
      c-SRS [0] INTEGER (0..63),
      b-SRS [1] INTEGER (0..3),
      b-hop [2] INTEGER (0..3)
   },
   groupOrSequenceHopping [8] ENUMERATED { neither(0), groupHopping(1), 
      sequenceHopping(2) },
   resourceType [9] EXPLICIT CHOICE {
      aperiodic [0] SEQUENCE {

         ...
      },
      semi-persistent [1] SEQUENCE {
         periodicityAndOffset-sp [0] EXPLICIT SRS-PeriodicityAndOffset,
         ...
      },
      periodic [2] SEQUENCE {
         periodicityAndOffset-p [0] EXPLICIT SRS-PeriodicityAndOffset,
         ...
      }
   },
   sequenceId [10] INTEGER (0..1023),
   spatialRelationInfo [11] SRS-SpatialRelationInfo OPTIONAL,
   ...
}

-- TAG-SRS-CARRIERSWITCHING-STOP
-- TAG-SRS-CONFIG-START
SRS-Config ::= SEQUENCE {
   srs-ResourceSetToReleaseList [0] SEQUENCE (SIZE (1..maxNrofSRS-ResourceSets)) OF SRS-ResourceSetId
       OPTIONAL, -- Need N
   srs-ResourceSetToAddModList [1] SEQUENCE (SIZE (1..maxNrofSRS-ResourceSets)) OF SRS-ResourceSet
       OPTIONAL, -- Need N
   srs-ResourceToReleaseList [2] SEQUENCE (SIZE (1..maxNrofSRS-Resources)) OF SRS-ResourceId
       OPTIONAL, -- Need N
   srs-ResourceToAddModList [3] SEQUENCE (SIZE (1..maxNrofSRS-Resources)) OF SRS-Resource OPTIONAL, -- Need N
   tpc-Accumulation [4] ENUMERATED { disabled(0) } OPTIONAL,
   ...
}

BFR-SSB-Resource ::= SEQUENCE {
   ssb [0] SSB-Index,
   ra-PreambleIndex [1] INTEGER (0..63),
   ...
}

BFR-CSIRS-Resource ::= SEQUENCE {
   csi-RS [0] NZP-CSI-RS-ResourceId,
   ra-OccasionList [1] SEQUENCE (SIZE (1..maxRA-OccasionsPerCSIRS)) OF INTEGER (0..maxRA-Occasions-1) OPTIONAL, -- Need R
   ra-PreambleIndex [2] INTEGER (0..63) OPTIONAL,
   ...
}

PRACH-ResourceDedicatedBFR ::= CHOICE {
   ssb [0] BFR-SSB-Resource,
   csi-RS [1] BFR-CSIRS-Resource
}

-- TAG-ARFCN-VALUENR-STOP
-- TAG-BEAMFAILURERECOVERYCONFIG-START
BeamFailureRecoveryConfig ::= SEQUENCE {
   rootSequenceIndex-BFR [0] INTEGER (0..137) OPTIONAL, -- Need M
   rach-ConfigBFR [1] RACH-ConfigGeneric OPTIONAL, -- Need M
   rsrp-ThresholdSSB [2] RSRP-Range OPTIONAL, -- Need M
   candidateBeamRSList [3] SEQUENCE (SIZE (1..maxNrofCandidateBeams)) OF PRACH-ResourceDedicatedBFR
       OPTIONAL, -- Need M
   ssb-perRACH-Occasion [4] ENUMERATED { oneEighth(0), oneFourth(1), oneHalf(2)
      , one(3), two(4), four(5), eight(6), sixteen(7) } OPTIONAL, -- Need M
   ra-ssb-OccasionMaskIndex [5] INTEGER (0..15) OPTIONAL, -- Need M
   recoverySearchSpaceId [6] SearchSpaceId OPTIONAL, -- Need R
   ra-Prioritization [7] RA-Prioritization OPTIONAL, -- Need R
   beamFailureRecoveryTimer [8] ENUMERATED { ms10(0), ms20(1), ms40(2), ms60(3)
      , ms80(4), ms100(5), ms150(6), ms200(7) } OPTIONAL,
   ...,
   [[
      msg1-SubcarrierSpacing [9] SubcarrierSpacing OPTIONAL
   ]]
}

-- TAG-BWP-UPLINKCOMMON-STOP
-- TAG-BWP-UPLINKDEDICATED-START
BWP-UplinkDedicated ::= SEQUENCE {
   pucch-Config [0] EXPLICIT CHOICE {
      release [0] NULL,
      setup [1] EXPLICIT PUCCH-Config
   } OPTIONAL, -- Need M
   pusch-Config [1] EXPLICIT CHOICE {
      release [0] NULL,
      setup [1] EXPLICIT PUSCH-Config
   } OPTIONAL, -- Need M
   configuredGrantConfig [2] EXPLICIT CHOICE {
      release [0] NULL,
      setup [1] EXPLICIT ConfiguredGrantConfig
   } OPTIONAL, -- Need M
   srs-Config [3] EXPLICIT CHOICE {
      release [0] NULL,
      setup [1] EXPLICIT SRS-Config
   } OPTIONAL, -- Need M
   beamFailureRecoveryConfig [4] EXPLICIT CHOICE {
      release [0] NULL,
      setup [1] EXPLICIT BeamFailureRecoveryConfig
   } OPTIONAL,
   ...
}

-- TAG-BWP-ID-STOP
-- TAG-BWP-UPLINK-START
BWP-Uplink ::= SEQUENCE {
   bwp-Id [0] BWP-Id,
   bwp-Common [1] BWP-UplinkCommon OPTIONAL, -- Cond SetupOtherBWP
   bwp-Dedicated [2] BWP-UplinkDedicated OPTIONAL,
   ...
}

PUSCH-CodeBlockGroupTransmission ::= SEQUENCE {
   maxCodeBlockGroupsPerTransportBlock [0] ENUMERATED { n2(0), n4(1), n6(2), 
      n8(3) },
   ...
}

-- TAG-PUSCH-POWERCONTROL-STOP
-- TAG-PUSCH-SERVINGCELLCONFIG-START
PUSCH-ServingCellConfig ::= SEQUENCE {
   codeBlockGroupTransmission [0] EXPLICIT CHOICE {
      release [0] NULL,
      setup [1] EXPLICIT PUSCH-CodeBlockGroupTransmission
   } OPTIONAL, -- Need M
   rateMatching [1] ENUMERATED { limitedBufferRM(0) } OPTIONAL, -- Need S
   xOverhead [2] ENUMERATED { xoh6(0), xoh12(1), xoh18(2) } OPTIONAL,
   ...,
   [[
      maxMIMO-Layers [3] INTEGER (1..4) OPTIONAL,
      processingType2Enabled [4] BOOLEAN OPTIONAL
   ]]
}

SRS-CC-SetIndex ::= SEQUENCE {
   cc-SetIndex [0] INTEGER (0..3) OPTIONAL, -- Need M
   cc-IndexInOneCC-Set [1] INTEGER (0..7) OPTIONAL -- Need M
}

SRS-TPC-PDCCH-Config ::= SEQUENCE {
   srs-CC-SetIndexlist [0] SEQUENCE (SIZE (1..4)) OF SRS-CC-SetIndex OPTIONAL -- Need M
}

-- TAG-SRB-IDENTITY-STOP
-- TAG-SRS-CARRIERSWITCHING-START
SRS-CarrierSwitching ::= SEQUENCE {
   srs-SwitchFromServCellIndex [0] INTEGER (0..31) OPTIONAL, -- Need M
   srs-SwitchFromCarrier [1] ENUMERATED { sUL(0), nUL(1) },
   srs-TPC-PDCCH-Group [2] EXPLICIT CHOICE {
      typeA [0] SEQUENCE (SIZE (1..32)) OF SRS-TPC-PDCCH-Config,
      typeB [1] SRS-TPC-PDCCH-Config
   } OPTIONAL, -- Need M
   monitoringCells [3] SEQUENCE (SIZE (1..maxNrofServingCells)) OF ServCellIndex OPTIONAL,
   ...
}

UplinkConfig ::= SEQUENCE {
   initialUplinkBWP [0] BWP-UplinkDedicated OPTIONAL, -- Need M
   uplinkBWP-ToReleaseList [1] SEQUENCE (SIZE (1..maxNrofBWPs)) OF BWP-Id OPTIONAL, -- Need N
   uplinkBWP-ToAddModList [2] SEQUENCE (SIZE (1..maxNrofBWPs)) OF BWP-Uplink OPTIONAL, -- Need N
   firstActiveUplinkBWP-Id [3] BWP-Id OPTIONAL, -- Cond SyncAndCellAdd
   pusch-ServingCellConfig [4] EXPLICIT CHOICE {
      release [0] NULL,
      setup [1] EXPLICIT PUSCH-ServingCellConfig
   } OPTIONAL, -- Need M
   carrierSwitching [5] EXPLICIT CHOICE {
      release [0] NULL,
      setup [1] EXPLICIT SRS-CarrierSwitching
   } OPTIONAL,
   ...,
   [[
      powerBoostPi2BPSK [6] BOOLEAN OPTIONAL,
      uplinkChannelBW-PerSCS-List [7] SEQUENCE (SIZE (1..maxSCSs)) OF 
         SCS-SpecificCarrier OPTIONAL
   ]]
}

SlotFormatCombination ::= SEQUENCE {
   slotFormatCombinationId [0] SlotFormatCombinationId,
   slotFormats [1] SEQUENCE (SIZE (1..maxNrofSlotFormatsPerCombination)) OF INTEGER (0..255)
}

-- TAG-SKCOUNTER-STOP
-- TAG-SLOTFORMATCOMBINATIONSPERCELL-START
SlotFormatCombinationsPerCell ::= SEQUENCE {
   servingCellId [0] ServCellIndex,
   subcarrierSpacing [1] SubcarrierSpacing,
   subcarrierSpacing2 [2] SubcarrierSpacing OPTIONAL, -- Need R
   slotFormatCombinations [3] SEQUENCE (SIZE (1..maxNrofSlotFormatCombinationsPerSet)) OF SlotFormatCombination
       OPTIONAL,
                                                                                                                             -- Need M
   positionInDCI [4] INTEGER (0..maxSFI-DCI-PayloadSize-1) OPTIONAL,
   ...
}

-- TAG-SLOTFORMATCOMBINATIONSPERCELL-STOP
-- TAG-SLOTFORMATINDICATOR-START
SlotFormatIndicator ::= SEQUENCE {
   sfi-RNTI [0] RNTI-Value,
   dci-PayloadSize [1] INTEGER (1..maxSFI-DCI-PayloadSize),
   slotFormatCombToAddModList [2] SEQUENCE (SIZE (1..maxNrofAggregatedCellsPerCellGroup)) OF 
      SlotFormatCombinationsPerCell OPTIONAL,
                                                                                                                                   -- Need N
   slotFormatCombToReleaseList [3] SEQUENCE (SIZE (1..maxNrofAggregatedCellsPerCellGroup)) OF ServCellIndex
       OPTIONAL,
   ...
}

-- TAG-PDCCH-CONFIGSIB1-STOP
-- TAG-PDCCH-SERVINGCELLCONFIG-START
PDCCH-ServingCellConfig ::= SEQUENCE {
   slotFormatIndicator [0] EXPLICIT CHOICE {
      release [0] NULL,
      setup [1] EXPLICIT SlotFormatIndicator
   } OPTIONAL,
   ...
}

PDSCH-CodeBlockGroupTransmission ::= SEQUENCE {
   maxCodeBlockGroupsPerTransportBlock [0] ENUMERATED { n2(0), n4(1), n6(2), 
      n8(3) },
   codeBlockGroupFlushIndicator [1] BOOLEAN,
   ...
}

-- TAG-PDSCH-CONFIGCOMMON-STOP
-- TAG-PDSCH-SERVINGCELLCONFIG-START
PDSCH-ServingCellConfig ::= SEQUENCE {
   codeBlockGroupTransmission [0] EXPLICIT CHOICE {
      release [0] NULL,
      setup [1] EXPLICIT PDSCH-CodeBlockGroupTransmission
   } OPTIONAL, -- Need M
   xOverhead [1] ENUMERATED { xOh6(0), xOh12(1), xOh18(2) } OPTIONAL, -- Need S
   nrofHARQ-ProcessesForPDSCH [2] ENUMERATED { n2(0), n4(1), n6(2), n10(3), 
      n12(4), n16(5) } OPTIONAL, -- Need S
   pucch-Cell [3] ServCellIndex OPTIONAL,
   ...,
   [[
      maxMIMO-Layers [4] INTEGER (1..8) OPTIONAL,
      processingType2Enabled [5] BOOLEAN OPTIONAL
   ]]
}

-- TAG-NR-NS-PMAXLIST-STOP
-- TAG-NZP-CSI-RS-RESOURCE-START
NZP-CSI-RS-Resource ::= SEQUENCE {
   nzp-CSI-RS-ResourceId [0] NZP-CSI-RS-ResourceId,
   resourceMapping [1] CSI-RS-ResourceMapping,
   powerControlOffset [2] INTEGER (-8..15),
   powerControlOffsetSS [3] ENUMERATED { db-3(0), db0(1), db3(2), db6(3) }
       OPTIONAL, -- Need R
   scramblingID [4] ScramblingId,
   periodicityAndOffset [5] EXPLICIT CSI-ResourcePeriodicityAndOffset OPTIONAL,
       -- Cond PeriodicOrSemiPersistent
   qcl-InfoPeriodicCSI-RS [6] TCI-StateId OPTIONAL,
   ...
}

-- TAG-NZP-CSI-RS-RESOURCEID-STOP
-- TAG-NZP-CSI-RS-RESOURCESET-START
NZP-CSI-RS-ResourceSet ::= SEQUENCE {
   nzp-CSI-ResourceSetId [0] NZP-CSI-RS-ResourceSetId,
   nzp-CSI-RS-Resources [1] SEQUENCE (SIZE (1..maxNrofNZP-CSI-RS-ResourcesPerSet)) OF NZP-CSI-RS-ResourceId,
   repetition [2] ENUMERATED { on(0), off(1) } OPTIONAL, -- Need S
   aperiodicTriggeringOffset [3] INTEGER (0..6) OPTIONAL, -- Need S
   trs-Info [4] ENUMERATED { true(0) } OPTIONAL,
   ...
}

-- TAG-CSI-FREQUENCYOCCUPATION-STOP
-- TAG-CSI-IM-RESOURCE-START
CSI-IM-Resource ::= SEQUENCE {
   csi-IM-ResourceId [0] CSI-IM-ResourceId,
   csi-IM-ResourceElementPattern [1] EXPLICIT CHOICE {
      pattern0 [0] SEQUENCE {
         subcarrierLocation-p0 [0] ENUMERATED { s0(0), s2(1), s4(2), s6(3), 
            s8(4), s10(5) },
         symbolLocation-p0 [1] INTEGER (0..12)
      },
      pattern1 [1] SEQUENCE {
         subcarrierLocation-p1 [0] ENUMERATED { s0(0), s4(1), s8(2) },
         symbolLocation-p1 [1] INTEGER (0..13)
      }
   } OPTIONAL, -- Need M
   freqBand [2] CSI-FrequencyOccupation OPTIONAL, -- Need M
   periodicityAndOffset [3] EXPLICIT CSI-ResourcePeriodicityAndOffset OPTIONAL,
   ...
}

-- TAG-CSI-IM-RESOURCEID-STOP
-- TAG-CSI-IM-RESOURCESET-START
CSI-IM-ResourceSet ::= SEQUENCE {
   csi-IM-ResourceSetId [0] CSI-IM-ResourceSetId,
   csi-IM-Resources [1] SEQUENCE (SIZE (1..maxNrofCSI-IM-ResourcesPerSet)) OF CSI-IM-ResourceId,
   ...
}

-- TAG-CSI-SEMIPERSISTENTONPUSCHTRIGGERSTATELIST-STOP
-- TAG-CSI-SSB-RESOURCESET-START
CSI-SSB-ResourceSet ::= SEQUENCE {
   csi-SSB-ResourceSetId [0] CSI-SSB-ResourceSetId,
   csi-SSB-ResourceList [1] SEQUENCE (SIZE (1..maxNrofCSI-SSB-ResourcePerSet)) OF SSB-Index,
   ...
}

-- TAG-CSI-REPORTCONFIGID-STOP
-- TAG-CSI-RESOURCECONFIG-START
CSI-ResourceConfig ::= SEQUENCE {
   csi-ResourceConfigId [0] CSI-ResourceConfigId,
   csi-RS-ResourceSetList [1] EXPLICIT CHOICE {
      nzp-CSI-RS-SSB [0] SEQUENCE {
         nzp-CSI-RS-ResourceSetList [0] SEQUENCE (SIZE (1..maxNrofNZP-CSI-RS-ResourceSetsPerConfig)) OF 
            NZP-CSI-RS-ResourceSetId OPTIONAL,
                                                                                                                              -- Need R
         csi-SSB-ResourceSetList [1] SEQUENCE (SIZE (1..maxNrofCSI-SSB-ResourceSetsPerConfig)) OF 
            CSI-SSB-ResourceSetId OPTIONAL
                                                                                                                              -- Need R
      },
      csi-IM-ResourceSetList [1] SEQUENCE (SIZE (1..maxNrofCSI-IM-ResourceSetsPerConfig)) OF CSI-IM-ResourceSetId
   },
   bwp-Id [2] BWP-Id,
   resourceType [3] ENUMERATED { aperiodic(0), semiPersistent(1), periodic(2) }
      ,
   ...
}

CSI-ReportPeriodicityAndOffset ::= CHOICE {
   slots4 [0] INTEGER (0..3),
   slots5 [1] INTEGER (0..4),
   slots8 [2] INTEGER (0..7),
   slots10 [3] INTEGER (0..9),
   slots16 [4] INTEGER (0..15),
   slots20 [5] INTEGER (0..19),
   slots40 [6] INTEGER (0..39),
   slots80 [7] INTEGER (0..79),
   slots160 [8] INTEGER (0..159),
   slots320 [9] INTEGER (0..319)
}

PUCCH-CSI-Resource ::= SEQUENCE {
   uplinkBandwidthPartId [0] BWP-Id,
   pucch-Resource [1] PUCCH-ResourceId
}

-- TAG-CGI-INFO-NR-STOP
-- TAG-CODEBOOKCONFIG-START
CodebookConfig ::= SEQUENCE {
   codebookType [0] EXPLICIT CHOICE {
      type1 [0] SEQUENCE {
         subType [0] EXPLICIT CHOICE {
            typeI-SinglePanel [0] SEQUENCE {
               nrOfAntennaPorts [0] EXPLICIT CHOICE {
                  two [0] SEQUENCE {
                     twoTX-CodebookSubsetRestriction [0] BIT STRING  (SIZE (6))
                  },
                  moreThanTwo [1] SEQUENCE {
                     n1-n2 [0] EXPLICIT CHOICE {
                        two-one-TypeI-SinglePanel-Restriction [0] BIT STRING  (
                           SIZE (8)),
                        two-two-TypeI-SinglePanel-Restriction [1] BIT STRING  (
                           SIZE (64)),
                        four-one-TypeI-SinglePanel-Restriction [2] BIT STRING 
                            (SIZE (16)),
                        three-two-TypeI-SinglePanel-Restriction [3] BIT STRING 
                            (SIZE (96)),
                        six-one-TypeI-SinglePanel-Restriction [4] BIT STRING  (
                           SIZE (24)),
                        four-two-TypeI-SinglePanel-Restriction [5] BIT STRING 
                            (SIZE (128)),
                        eight-one-TypeI-SinglePanel-Restriction [6] BIT STRING 
                            (SIZE (32)),
                        four-three-TypeI-SinglePanel-Restriction [7] 
                           BIT STRING  (SIZE (192)),
                        six-two-TypeI-SinglePanel-Restriction [8] BIT STRING  (
                           SIZE (192)),
                        twelve-one-TypeI-SinglePanel-Restriction [9] 
                           BIT STRING  (SIZE (48)),
                        four-four-TypeI-SinglePanel-Restriction [10] 
                           BIT STRING  (SIZE (256)),
                        eight-two-TypeI-SinglePanel-Restriction [11] 
                           BIT STRING  (SIZE (256)),
                        sixteen-one-TypeI-SinglePanel-Restriction [12] 
                           BIT STRING  (SIZE (64))
                     },
                     typeI-SinglePanel-codebookSubsetRestriction-i2 [1] 
                        BIT STRING  (SIZE (16)) OPTIONAL -- Need R
                  }
               },
               typeI-SinglePanel-ri-Restriction [1] BIT STRING  (SIZE (8))
            },
            typeI-MultiPanel [1] SEQUENCE {
               ng-n1-n2 [0] EXPLICIT CHOICE {
                  two-two-one-TypeI-MultiPanel-Restriction [0] BIT STRING  (
                     SIZE (8)),
                  two-four-one-TypeI-MultiPanel-Restriction [1] BIT STRING  (
                     SIZE (16)),
                  four-two-one-TypeI-MultiPanel-Restriction [2] BIT STRING  (
                     SIZE (8)),
                  two-two-two-TypeI-MultiPanel-Restriction [3] BIT STRING  (
                     SIZE (64)),
                  two-eight-one-TypeI-MultiPanel-Restriction [4] BIT STRING  (
                     SIZE (32)),
                  four-four-one-TypeI-MultiPanel-Restriction [5] BIT STRING  (
                     SIZE (16)),
                  two-four-two-TypeI-MultiPanel-Restriction [6] BIT STRING  (
                     SIZE (128)),
                  four-two-two-TypeI-MultiPanel-Restriction [7] BIT STRING  (
                     SIZE (64))
               },
               ri-Restriction [1] BIT STRING  (SIZE (4))
            }
         },
         codebookMode [1] INTEGER (1..2)
      },
      type2 [1] SEQUENCE {
         subType [0] EXPLICIT CHOICE {
            typeII [0] SEQUENCE {
               n1-n2-codebookSubsetRestriction [0] EXPLICIT CHOICE {
                  two-one [0] BIT STRING  (SIZE (16)),
                  two-two [1] BIT STRING  (SIZE (43)),
                  four-one [2] BIT STRING  (SIZE (32)),
                  three-two [3] BIT STRING  (SIZE (59)),
                  six-one [4] BIT STRING  (SIZE (48)),
                  four-two [5] BIT STRING  (SIZE (75)),
                  eight-one [6] BIT STRING  (SIZE (64)),
                  four-three [7] BIT STRING  (SIZE (107)),
                  six-two [8] BIT STRING  (SIZE (107)),
                  twelve-one [9] BIT STRING  (SIZE (96)),
                  four-four [10] BIT STRING  (SIZE (139)),
                  eight-two [11] BIT STRING  (SIZE (139)),
                  sixteen-one [12] BIT STRING  (SIZE (128))
               },
               typeII-RI-Restriction [1] BIT STRING  (SIZE (2))
            },
            typeII-PortSelection [1] SEQUENCE {
               portSelectionSamplingSize [0] ENUMERATED { n1(0), n2(1), n3(2), 
                  n4(3) } OPTIONAL, -- Need R
               typeII-PortSelectionRI-Restriction [1] BIT STRING  (SIZE (2))
            }
         },
         phaseAlphabetSize [1] ENUMERATED { n4(0), n8(1) },
         subbandAmplitude [2] BOOLEAN,
         numberOfBeams [3] ENUMERATED { two(0), three(1), four(2) }
      }
   }
}

PortIndexFor8Ranks ::= CHOICE {
   portIndex8 [0] SEQUENCE {
      rank1-8 [0] PortIndex8 OPTIONAL, -- Need R
      rank2-8 [1] SEQUENCE (SIZE (2)) OF PortIndex8 OPTIONAL, -- Need R
      rank3-8 [2] SEQUENCE (SIZE (3)) OF PortIndex8 OPTIONAL, -- Need R
      rank4-8 [3] SEQUENCE (SIZE (4)) OF PortIndex8 OPTIONAL, -- Need R
      rank5-8 [4] SEQUENCE (SIZE (5)) OF PortIndex8 OPTIONAL, -- Need R
      rank6-8 [5] SEQUENCE (SIZE (6)) OF PortIndex8 OPTIONAL, -- Need R
      rank7-8 [6] SEQUENCE (SIZE (7)) OF PortIndex8 OPTIONAL, -- Need R
      rank8-8 [7] SEQUENCE (SIZE (8)) OF PortIndex8 OPTIONAL -- Need R
   },
   portIndex4 [1] SEQUENCE {
      rank1-4 [0] PortIndex4 OPTIONAL, -- Need R
      rank2-4 [1] SEQUENCE (SIZE (2)) OF PortIndex4 OPTIONAL, -- Need R
      rank3-4 [2] SEQUENCE (SIZE (3)) OF PortIndex4 OPTIONAL, -- Need R
      rank4-4 [3] SEQUENCE (SIZE (4)) OF PortIndex4 OPTIONAL -- Need R
   },
   portIndex2 [2] SEQUENCE {
      rank1-2 [0] PortIndex2 OPTIONAL, -- Need R
      rank2-2 [1] SEQUENCE (SIZE (2)) OF PortIndex2 OPTIONAL -- Need R
   },
   portIndex1 [3] NULL
}

-- TAG-CSI-MEASCONFIG-STOP
-- TAG-CSI-REPORTCONFIG-START
CSI-ReportConfig ::= SEQUENCE {
   reportConfigId [0] CSI-ReportConfigId,
   carrier [1] ServCellIndex OPTIONAL, -- Need S
   resourcesForChannelMeasurement [2] CSI-ResourceConfigId,
   csi-IM-ResourcesForInterference [3] CSI-ResourceConfigId OPTIONAL, -- Need R
   nzp-CSI-RS-ResourcesForInterference [4] CSI-ResourceConfigId OPTIONAL, -- Need R
   reportConfigType [5] EXPLICIT CHOICE {
      periodic [0] SEQUENCE {
         reportSlotConfig [0] EXPLICIT CSI-ReportPeriodicityAndOffset,
         pucch-CSI-ResourceList [1] SEQUENCE (SIZE (1..maxNrofBWPs)) OF PUCCH-CSI-Resource
      },
      semiPersistentOnPUCCH [1] SEQUENCE {
         reportSlotConfig [0] EXPLICIT CSI-ReportPeriodicityAndOffset,
         pucch-CSI-ResourceList [1] SEQUENCE (SIZE (1..maxNrofBWPs)) OF PUCCH-CSI-Resource
      },
      semiPersistentOnPUSCH [2] SEQUENCE {
         reportSlotConfig [0] ENUMERATED { sl5(0), sl10(1), sl20(2), sl40(3), 
            sl80(4), sl160(5), sl320(6) },
         reportSlotOffsetList [1] SEQUENCE (SIZE (1..maxNrofUL-Allocations)) OF INTEGER (0..32),
         p0alpha [2] P0-PUSCH-AlphaSetId
      },
      aperiodic [3] SEQUENCE {
         reportSlotOffsetList [0] SEQUENCE (SIZE (1..maxNrofUL-Allocations)) OF INTEGER (0..32)
      }
   },
   reportQuantity [6] EXPLICIT CHOICE {
      none [0] NULL,
      cri-RI-PMI-CQI [1] NULL,
      cri-RI-i1 [2] NULL,
      cri-RI-i1-CQI [3] SEQUENCE {
         pdsch-BundleSizeForCSI [0] ENUMERATED { n2(0), n4(1) } OPTIONAL -- Need S
      },
      cri-RI-CQI [4] NULL,
      cri-RSRP [5] NULL,
      ssb-Index-RSRP [6] NULL,
      cri-RI-LI-PMI-CQI [7] NULL
   },
   reportFreqConfiguration [7] SEQUENCE {
      cqi-FormatIndicator [0] ENUMERATED { widebandCQI(0), subbandCQI(1) }
          OPTIONAL, -- Need R
      pmi-FormatIndicator [1] ENUMERATED { widebandPMI(0), subbandPMI(1) }
          OPTIONAL, -- Need R
      csi-ReportingBand [2] EXPLICIT CHOICE {
         subbands3 [0] BIT STRING  (SIZE (3)),
         subbands4 [1] BIT STRING  (SIZE (4)),
         subbands5 [2] BIT STRING  (SIZE (5)),
         subbands6 [3] BIT STRING  (SIZE (6)),
         subbands7 [4] BIT STRING  (SIZE (7)),
         subbands8 [5] BIT STRING  (SIZE (8)),
         subbands9 [6] BIT STRING  (SIZE (9)),
         subbands10 [7] BIT STRING  (SIZE (10)),
         subbands11 [8] BIT STRING  (SIZE (11)),
         subbands12 [9] BIT STRING  (SIZE (12)),
         subbands13 [10] BIT STRING  (SIZE (13)),
         subbands14 [11] BIT STRING  (SIZE (14)),
         subbands15 [12] BIT STRING  (SIZE (15)),
         subbands16 [13] BIT STRING  (SIZE (16)),
         subbands17 [14] BIT STRING  (SIZE (17)),
         subbands18 [15] BIT STRING  (SIZE (18)),
         ...,
         subbands19-v1530 [16] BIT STRING  (SIZE (19))
      } OPTIONAL -- Need S
   } OPTIONAL, -- Need R
   timeRestrictionForChannelMeasurements [8] ENUMERATED { configured(0), 
      notConfigured(1) },
   timeRestrictionForInterferenceMeasurements [9] ENUMERATED { configured(0), 
      notConfigured(1) },
   codebookConfig [10] CodebookConfig OPTIONAL, -- Need R
   dummy [11] ENUMERATED { n1(0), n2(1) } OPTIONAL, -- Need R
   groupBasedBeamReporting [12] EXPLICIT CHOICE {
      enabled [0] NULL,
      disabled [1] SEQUENCE {
         nrofReportedRS [0] ENUMERATED { n1(0), n2(1), n3(2), n4(3) } OPTIONAL -- Need S
      }
   },
   cqi-Table [13] ENUMERATED { table1(0), table2(1), table3(2), spare1(3) }
       OPTIONAL, -- Need R
   subbandSize [14] ENUMERATED { value1(0), value2(1) },
   non-PMI-PortIndication [15] SEQUENCE (SIZE (1..maxNrofNZP-CSI-RS-ResourcesPerConfig)) OF PortIndexFor8Ranks
       OPTIONAL,
   ...,
   [[
      semiPersistentOnPUSCH-v1530 [16] SEQUENCE {
         reportSlotConfig-v1530 [0] ENUMERATED { sl4(0), sl8(1), sl16(2) }
      } OPTIONAL
   ]]
}

CSI-AssociatedReportConfigInfo ::= SEQUENCE {
   reportConfigId [0] CSI-ReportConfigId,
   resourcesForChannel [1] EXPLICIT CHOICE {
      nzp-CSI-RS [0] SEQUENCE {
         resourceSet [0] INTEGER (1..maxNrofNZP-CSI-RS-ResourceSetsPerConfig),
         qcl-info [1] SEQUENCE (SIZE (1..maxNrofAP-CSI-RS-ResourcesPerSet)) OF TCI-StateId OPTIONAL
                                                                                                     -- Cond Aperiodic
      },
      csi-SSB-ResourceSet [1] INTEGER (1..maxNrofCSI-SSB-ResourceSetsPerConfig)
   },
   csi-IM-ResourcesForInterference [2] INTEGER (1..maxNrofCSI-IM-ResourceSetsPerConfig) OPTIONAL,
                                                                                                   -- Cond CSI-IM-ForInterference
   nzp-CSI-RS-ResourcesForInterference [3] INTEGER (1..maxNrofNZP-CSI-RS-ResourceSetsPerConfig) OPTIONAL,
   ...
}

CSI-AperiodicTriggerState ::= SEQUENCE {
   associatedReportConfigInfoList [0] SEQUENCE (SIZE (1..maxNrofReportConfigPerAperiodicTrigger)) OF 
      CSI-AssociatedReportConfigInfo,
   ...
}

-- TAG-CrossCarrierSchedulingConfig-STOP
-- TAG-CSI-APERIODICTRIGGERSTATELIST-START
CSI-AperiodicTriggerStateList ::= SEQUENCE (SIZE (1..maxNrOfCSI-AperiodicTriggers)) OF 
   CSI-AperiodicTriggerState

CSI-SemiPersistentOnPUSCH-TriggerState ::= SEQUENCE {
   associatedReportConfigInfo [0] CSI-ReportConfigId,
   ...
}

-- TAG-CSI-RS-RESOURCEMAPPING-STOP
-- TAG-CSI-SEMIPERSISTENTONPUSCHTRIGGERSTATELIST-START
CSI-SemiPersistentOnPUSCH-TriggerStateList ::= SEQUENCE (SIZE (1..maxNrOfSemiPersistentPUSCH-Triggers)) OF 
   CSI-SemiPersistentOnPUSCH-TriggerState

-- TAG-CSI-IM-RESOURCESETID-STOP
-- TAG-CSI-MEASCONFIG-START
CSI-MeasConfig ::= SEQUENCE {
   nzp-CSI-RS-ResourceToAddModList [0] SEQUENCE (SIZE (1..maxNrofNZP-CSI-RS-Resources)) OF 
      NZP-CSI-RS-Resource OPTIONAL, -- Need N
   nzp-CSI-RS-ResourceToReleaseList [1] SEQUENCE (SIZE (1..maxNrofNZP-CSI-RS-Resources)) OF 
      NZP-CSI-RS-ResourceId OPTIONAL, -- Need N
   nzp-CSI-RS-ResourceSetToAddModList [2] SEQUENCE (SIZE (1..maxNrofNZP-CSI-RS-ResourceSets)) OF 
      NZP-CSI-RS-ResourceSet OPTIONAL,
                                                                                                                             -- Need N
   nzp-CSI-RS-ResourceSetToReleaseList [3] SEQUENCE (SIZE (1..maxNrofNZP-CSI-RS-ResourceSets)) OF 
      NZP-CSI-RS-ResourceSetId OPTIONAL,
                                                                                                                             -- Need N
   csi-IM-ResourceToAddModList [4] SEQUENCE (SIZE (1..maxNrofCSI-IM-Resources)) OF CSI-IM-Resource
       OPTIONAL, -- Need N
   csi-IM-ResourceToReleaseList [5] SEQUENCE (SIZE (1..maxNrofCSI-IM-Resources)) OF CSI-IM-ResourceId
       OPTIONAL, -- Need N
   csi-IM-ResourceSetToAddModList [6] SEQUENCE (SIZE (1..maxNrofCSI-IM-ResourceSets)) OF 
      CSI-IM-ResourceSet OPTIONAL, -- Need N
   csi-IM-ResourceSetToReleaseList [7] SEQUENCE (SIZE (1..maxNrofCSI-IM-ResourceSets)) OF 
      CSI-IM-ResourceSetId OPTIONAL, -- Need N
   csi-SSB-ResourceSetToAddModList [8] SEQUENCE (SIZE (1..maxNrofCSI-SSB-ResourceSets)) OF 
      CSI-SSB-ResourceSet OPTIONAL, -- Need N
   csi-SSB-ResourceSetToReleaseList [9] SEQUENCE (SIZE (1..maxNrofCSI-SSB-ResourceSets)) OF 
      CSI-SSB-ResourceSetId OPTIONAL, -- Need N
   csi-ResourceConfigToAddModList [10] SEQUENCE (SIZE (1..maxNrofCSI-ResourceConfigurations)) OF 
      CSI-ResourceConfig OPTIONAL,
                                                                                                                             -- Need N
   csi-ResourceConfigToReleaseList [11] SEQUENCE (SIZE (1..maxNrofCSI-ResourceConfigurations)) OF 
      CSI-ResourceConfigId OPTIONAL,
                                                                                                                             -- Need N
   csi-ReportConfigToAddModList [12] SEQUENCE (SIZE (1..maxNrofCSI-ReportConfigurations)) OF CSI-ReportConfig
       OPTIONAL, -- Need N
   csi-ReportConfigToReleaseList [13] SEQUENCE (SIZE (1..maxNrofCSI-ReportConfigurations)) OF 
      CSI-ReportConfigId OPTIONAL,
                                                                                                                             -- Need N
   reportTriggerSize [14] INTEGER (0..6) OPTIONAL, -- Need M
   aperiodicTriggerStateList [15] EXPLICIT CHOICE {
      release [0] NULL,
      setup [1] EXPLICIT CSI-AperiodicTriggerStateList
   } OPTIONAL, -- Need M
   semiPersistentOnPUSCH-TriggerStateList [16] EXPLICIT CHOICE {
      release [0] NULL,
      setup [1] EXPLICIT CSI-SemiPersistentOnPUSCH-TriggerStateList
   } OPTIONAL,
   ...
}

-- TAG-CONTROLRESOURCESETZERO-STOP
-- TAG-CrossCarrierSchedulingConfig-START
CrossCarrierSchedulingConfig ::= SEQUENCE {
   schedulingCellInfo [0] EXPLICIT CHOICE {
      own [0] SEQUENCE {
                                                                               -- Cross carrier scheduling: scheduling cell
         cif-Presence [0] BOOLEAN
      },
      other [1] SEQUENCE {
                                                                               -- Cross carrier scheduling: scheduled cell
         schedulingCellId [0] ServCellIndex,
         cif-InSchedulingCell [1] INTEGER (1..7)
      }
   },
   ...
}

-- TAG-SERVCELLINDEX-STOP
-- TAG-SERVINGCELLCONFIG-START
ServingCellConfig ::= SEQUENCE {
   tdd-UL-DL-ConfigurationDedicated [0] TDD-UL-DL-ConfigDedicated OPTIONAL, -- Cond TDD
   initialDownlinkBWP [1] BWP-DownlinkDedicated OPTIONAL, -- Need M
   downlinkBWP-ToReleaseList [2] SEQUENCE (SIZE (1..maxNrofBWPs)) OF BWP-Id OPTIONAL, -- Need N
   downlinkBWP-ToAddModList [3] SEQUENCE (SIZE (1..maxNrofBWPs)) OF BWP-Downlink OPTIONAL, -- Need N
   firstActiveDownlinkBWP-Id [4] BWP-Id OPTIONAL, -- Cond SyncAndCellAdd
   bwp-InactivityTimer [5] ENUMERATED { ms2(0), ms3(1), ms4(2), ms5(3), ms6(4)
      , ms8(5), ms10(6), ms20(7), ms30(8), ms40(9), ms50(10), ms60(11), 
      ms80(12), ms100(13), ms200(14), ms300(15), ms500(16), ms750(17), 
      ms1280(18), ms1920(19), ms2560(20), spare10(21), spare9(22), spare8(23), 
      spare7(24), spare6(25), spare5(26), spare4(27), spare3(28), spare2(29), 
      spare1(30) } OPTIONAL, --Need R
   defaultDownlinkBWP-Id [6] BWP-Id OPTIONAL, -- Need S
   uplinkConfig [7] UplinkConfig OPTIONAL, -- Need M
   supplementaryUplink [8] UplinkConfig OPTIONAL, -- Need M
   pdcch-ServingCellConfig [9] EXPLICIT CHOICE {
      release [0] NULL,
      setup [1] EXPLICIT PDCCH-ServingCellConfig
   } OPTIONAL, -- Need M
   pdsch-ServingCellConfig [10] EXPLICIT CHOICE {
      release [0] NULL,
      setup [1] EXPLICIT PDSCH-ServingCellConfig
   } OPTIONAL, -- Need M
   csi-MeasConfig [11] EXPLICIT CHOICE {
      release [0] NULL,
      setup [1] EXPLICIT CSI-MeasConfig
   } OPTIONAL, -- Need M
   sCellDeactivationTimer [12] ENUMERATED { ms20(0), ms40(1), ms80(2), ms160(3)
      , ms200(4), ms240(5), ms320(6), ms400(7), ms480(8), ms520(9), ms640(10), 
      ms720(11), ms840(12), ms1280(13), spare2(14), spare1(15) } OPTIONAL, -- Cond ServingCellWithoutPUCCH
   crossCarrierSchedulingConfig [13] CrossCarrierSchedulingConfig OPTIONAL, -- Need M
   tag-Id [14] TAG-Id,
   dummy [15] ENUMERATED { enabled(0) } OPTIONAL, -- Need R
   pathlossReferenceLinking [16] ENUMERATED { spCell(0), sCell(1) } OPTIONAL, -- Cond SCellOnly
   servingCellMO [17] MeasObjectId OPTIONAL,
   ...,
   [[
      lte-CRS-ToMatchAround [18] EXPLICIT CHOICE {
         release [0] NULL,
         setup [1] EXPLICIT RateMatchPatternLTE-CRS
      } OPTIONAL,
      rateMatchPatternToAddModList [19] SEQUENCE (SIZE (1..maxNrofRateMatchPatterns)) OF 
         RateMatchPattern OPTIONAL,
      rateMatchPatternToReleaseList [20] SEQUENCE (SIZE (1..maxNrofRateMatchPatterns)) OF 
         RateMatchPatternId OPTIONAL,
      downlinkChannelBW-PerSCS-List [21] SEQUENCE (SIZE (1..maxSCSs)) OF 
         SCS-SpecificCarrier OPTIONAL
   ]]
}

-- Serving cell specific MAC and PHY parameters for a SpCell:
SpCellConfig ::= SEQUENCE {
   servCellIndex [0] ServCellIndex OPTIONAL, -- Cond SCG
   reconfigurationWithSync [1] ReconfigurationWithSync OPTIONAL, -- Cond ReconfWithSync
   rlf-TimersAndConstants [2] EXPLICIT CHOICE {
      release [0] NULL,
      setup [1] EXPLICIT RLF-TimersAndConstants
   } OPTIONAL, -- Need M
   rlmInSyncOutOfSyncThreshold [3] ENUMERATED { n1(0) } OPTIONAL, -- Need S
   spCellConfigDedicated [4] ServingCellConfig OPTIONAL,
   ...
}

SCellConfig ::= SEQUENCE {
   sCellIndex [0] SCellIndex,
   sCellConfigCommon [1] ServingCellConfigCommon OPTIONAL, -- Cond SCellAdd
   sCellConfigDedicated [2] ServingCellConfig OPTIONAL,
   ...,
   [[
      smtc [3] SSB-MTC OPTIONAL
   ]]
}

-- TAG-CELLACCESSRELATEDINFOEUTRA-EPC-STOP
-- TAG-CELLGROUPCONFIG-START
-- Configuration of one Cell-Group:
CellGroupConfig ::= SEQUENCE {
   cellGroupId [0] CellGroupId,
   rlc-BearerToAddModList [1] SEQUENCE (SIZE (1..maxLC-ID)) OF RLC-BearerConfig OPTIONAL
      , -- Need N
   rlc-BearerToReleaseList [2] SEQUENCE (SIZE (1..maxLC-ID)) OF LogicalChannelIdentity
       OPTIONAL, -- Need N
   mac-CellGroupConfig [3] MAC-CellGroupConfig OPTIONAL, -- Need M
   physicalCellGroupConfig [4] PhysicalCellGroupConfig OPTIONAL, -- Need M
   spCellConfig [5] SpCellConfig OPTIONAL, -- Need M
   sCellToAddModList [6] SEQUENCE (SIZE (1..maxNrofSCells)) OF SCellConfig OPTIONAL, -- Need N
   sCellToReleaseList [7] SEQUENCE (SIZE (1..maxNrofSCells)) OF SCellIndex OPTIONAL,
   ...,
   [[
      reportUplinkTxDirectCurrent [8] ENUMERATED { true(0) } OPTIONAL
   ]]
}

RRCSetup-IEs ::= SEQUENCE {
   radioBearerConfig [0] RadioBearerConfig,
   masterCellGroup [1] OCTET STRING (CONTAINING CellGroupConfig),
   lateNonCriticalExtension [2] OCTET STRING OPTIONAL,
   nonCriticalExtension [3] SEQUENCE {

   } OPTIONAL
}

-- TAG-RRCRESUMEREQUEST1-STOP
-- TAG-RRCSETUP-START
RRCSetup ::= SEQUENCE {
   rrc-TransactionIdentifier [0] RRC-TransactionIdentifier,
   criticalExtensions [1] EXPLICIT CHOICE {
      rrcSetup [0] RRCSetup-IEs,
      criticalExtensionsFuture [1] SEQUENCE {

      }
   }
}

DL-CCCH-MessageType ::= CHOICE {
   c1 [0] EXPLICIT CHOICE {
      rrcReject [0] RRCReject,
      rrcSetup [1] RRCSetup,
      spare2 [2] NULL,
      spare1 [3] NULL
   },
   messageClassExtension [1] SEQUENCE {

   }
}

-- TAG-BCCH-DL-SCH-MESSAGE-STOP
-- TAG-DL-CCCH-MESSAGE-START
DL-CCCH-Message ::= SEQUENCE {
   message [0] EXPLICIT DL-CCCH-MessageType
}

MeasObjectToRemoveList ::= SEQUENCE (SIZE (1..maxNrofObjectId)) OF MeasObjectId

SSB-MTC2 ::= SEQUENCE {
   pci-List [0] SEQUENCE (SIZE (1..maxNrofPCIsPerSMTC)) OF PhysCellId OPTIONAL, -- Need M
   periodicity [1] ENUMERATED { sf5(0), sf10(1), sf20(2), sf40(3), sf80(4), 
      spare3(5), spare2(6), spare1(7) }
}

SSB-ConfigMobility ::= SEQUENCE {
   ssb-ToMeasure [0] EXPLICIT CHOICE {
      release [0] NULL,
      setup [1] EXPLICIT SSB-ToMeasure
   } OPTIONAL, -- Need M
   deriveSSB-IndexFromCell [1] BOOLEAN,
   ss-RSSI-Measurement [2] SS-RSSI-Measurement OPTIONAL,
   ...
}

CSI-RS-Resource-Mobility ::= SEQUENCE {
   csi-RS-Index [0] CSI-RS-Index,
   slotConfig [1] EXPLICIT CHOICE {
      ms4 [0] INTEGER (0..31),
      ms5 [1] INTEGER (0..39),
      ms10 [2] INTEGER (0..79),
      ms20 [3] INTEGER (0..159),
      ms40 [4] INTEGER (0..319)
   },
   associatedSSB [2] SEQUENCE {
      ssb-Index [0] SSB-Index,
      isQuasiColocated [1] BOOLEAN
   } OPTIONAL, -- Need R
   frequencyDomainAllocation [3] EXPLICIT CHOICE {
      row1 [0] BIT STRING  (SIZE (4)),
      row2 [1] BIT STRING  (SIZE (12))
   },
   firstOFDMSymbolInTimeDomain [4] INTEGER (0..13),
   sequenceGenerationConfig [5] INTEGER (0..1023),
   ...
}

CSI-RS-CellMobility ::= SEQUENCE {
   cellId [0] PhysCellId,
   csi-rs-MeasurementBW [1] SEQUENCE {
      nrofPRBs [0] ENUMERATED { size24(0), size48(1), size96(2), size192(3), 
         size264(4) },
      startPRB [1] INTEGER (0..2169)
   },
   density [2] ENUMERATED { d1(0), d3(1) } OPTIONAL, -- Need R
   csi-rs-ResourceList-Mobility [3] SEQUENCE (SIZE (1..maxNrofCSI-RS-ResourcesRRM)) OF 
      CSI-RS-Resource-Mobility
}

-- TAG-CSI-RESOURCEPERIODICITYANDOFFSET-STOP
-- TAG-CSI-RS-RESOURCECONFIGMOBILITY-START
CSI-RS-ResourceConfigMobility ::= SEQUENCE {
   subcarrierSpacing [0] SubcarrierSpacing,
   csi-RS-CellList-Mobility [1] SEQUENCE (SIZE (1..maxNrofCSI-RS-CellsRRM)) OF CSI-RS-CellMobility,
   ...,
   [[
      refServCellIndex [2] ServCellIndex OPTIONAL
   ]]
}

ReferenceSignalConfig ::= SEQUENCE {
   ssb-ConfigMobility [0] SSB-ConfigMobility OPTIONAL, -- Need M
   csi-rs-ResourceConfigMobility [1] EXPLICIT CHOICE {
      release [0] NULL,
      setup [1] EXPLICIT CSI-RS-ResourceConfigMobility
   } OPTIONAL -- Need M
}

Q-OffsetRangeList ::= SEQUENCE {
   rsrpOffsetSSB [0] Q-OffsetRange DEFAULT dB0,
   rsrqOffsetSSB [1] Q-OffsetRange DEFAULT dB0,
   sinrOffsetSSB [2] Q-OffsetRange DEFAULT dB0,
   rsrpOffsetCSI-RS [3] Q-OffsetRange DEFAULT dB0,
   rsrqOffsetCSI-RS [4] Q-OffsetRange DEFAULT dB0,
   sinrOffsetCSI-RS [5] Q-OffsetRange DEFAULT dB0
}

-- TAG-P-MAX-STOP
-- TAG-PCI-LIST-START
PCI-List ::= SEQUENCE (SIZE (1..maxNrofCellMeas)) OF PhysCellId

CellsToAddMod ::= SEQUENCE {
   physCellId [0] PhysCellId,
   cellIndividualOffset [1] Q-OffsetRangeList
}

CellsToAddModList ::= SEQUENCE (SIZE (1..maxNrofCellMeas)) OF CellsToAddMod

-- TAG-PCI-RANGEINDEX-STOP
-- TAG-PCI-RANGEINDEXLIST-START
PCI-RangeIndexList ::= SEQUENCE (SIZE (1..maxNrofPCI-Ranges)) OF PCI-RangeIndex

-- TAG-PCI-RANGE-STOP
-- TAG-PCI-RANGEELEMENT-START
PCI-RangeElement ::= SEQUENCE {
   pci-RangeIndex [0] PCI-RangeIndex,
   pci-Range [1] PCI-Range
}

-- TAG-MEASOBJECTID-STOP
-- TAG-MEASOBJECTNR-START
MeasObjectNR ::= SEQUENCE {
   ssbFrequency [0] ARFCN-ValueNR OPTIONAL, -- Cond SSBorAssociatedSSB
   ssbSubcarrierSpacing [1] SubcarrierSpacing OPTIONAL, -- Cond SSBorAssociatedSSB
   smtc1 [2] SSB-MTC OPTIONAL, -- Cond SSBorAssociatedSSB
   smtc2 [3] SSB-MTC2 OPTIONAL, -- Cond IntraFreqConnected
   refFreqCSI-RS [4] ARFCN-ValueNR OPTIONAL, -- Cond CSI-RS
   referenceSignalConfig [5] ReferenceSignalConfig,
   absThreshSS-BlocksConsolidation [6] ThresholdNR OPTIONAL, -- Need R
   absThreshCSI-RS-Consolidation [7] ThresholdNR OPTIONAL, -- Need R
   nrofSS-BlocksToAverage [8] INTEGER (2..maxNrofSS-BlocksToAverage) OPTIONAL, -- Need R
   nrofCSI-RS-ResourcesToAverage [9] INTEGER (2..maxNrofCSI-RS-ResourcesToAverage) OPTIONAL, -- Need R
   quantityConfigIndex [10] INTEGER (1..maxNrofQuantityConfig),
   offsetMO [11] Q-OffsetRangeList,
   cellsToRemoveList [12] PCI-List OPTIONAL, -- Need N
   cellsToAddModList [13] CellsToAddModList OPTIONAL, -- Need N
   blackCellsToRemoveList [14] PCI-RangeIndexList OPTIONAL, -- Need N
   blackCellsToAddModList [15] SEQUENCE (SIZE (1..maxNrofPCI-Ranges)) OF PCI-RangeElement
       OPTIONAL, -- Need N
   whiteCellsToRemoveList [16] PCI-RangeIndexList OPTIONAL, -- Need N
   whiteCellsToAddModList [17] SEQUENCE (SIZE (1..maxNrofPCI-Ranges)) OF PCI-RangeElement
       OPTIONAL,
   ...,
   [[
      freqBandIndicatorNR [18] FreqBandIndicatorNR OPTIONAL,
      measCycleSCell [19] ENUMERATED { sf160(0), sf256(1), sf320(2), sf512(3), 
         sf640(4), sf1024(5), sf1280(6) } OPTIONAL
   ]]
}

EUTRA-CellIndexList ::= SEQUENCE (SIZE (1..maxCellMeasEUTRA)) OF EUTRA-CellIndex

EUTRA-Cell ::= SEQUENCE {
   cellIndexEUTRA [0] EUTRA-CellIndex,
   physCellId [1] EUTRA-PhysCellId,
   cellIndividualOffset [2] EUTRA-Q-OffsetRange
}

EUTRA-BlackCell ::= SEQUENCE {
   cellIndexEUTRA [0] EUTRA-CellIndex,
   physCellIdRange [1] EUTRA-PhysCellIdRange
}

-- TAG-MEASIDTOADDMODLIST-STOP
-- TAG-MEASOBJECTEUTRA-START
MeasObjectEUTRA ::= SEQUENCE {
   carrierFreq [0] ARFCN-ValueEUTRA,
   allowedMeasBandwidth [1] EUTRA-AllowedMeasBandwidth,
   cellsToRemoveListEUTRAN [2] EUTRA-CellIndexList OPTIONAL, -- Need N
   cellsToAddModListEUTRAN [3] SEQUENCE (SIZE (1..maxCellMeasEUTRA)) OF EUTRA-Cell OPTIONAL, -- Need N
   blackCellsToRemoveListEUTRAN [4] EUTRA-CellIndexList OPTIONAL, -- Need N
   blackCellsToAddModListEUTRAN [5] SEQUENCE (SIZE (1..maxCellMeasEUTRA)) OF EUTRA-BlackCell
       OPTIONAL, -- Need N
   eutra-PresenceAntennaPort1 [6] EUTRA-PresenceAntennaPort1,
   eutra-Q-OffsetRange [7] EUTRA-Q-OffsetRange OPTIONAL, -- Need R
   widebandRSRQ-Meas [8] BOOLEAN,
   ...
}

MeasObjectToAddMod ::= SEQUENCE {
   measObjectId [0] MeasObjectId,
   measObject [1] EXPLICIT CHOICE {
      measObjectNR [0] MeasObjectNR,
      ...,
      measObjectEUTRA [1] MeasObjectEUTRA
   }
}

-- TAG-MEASOBJECTNR-STOP
-- TAG-MEASOBJECTTOADDMODLIST-START
MeasObjectToAddModList ::= SEQUENCE (SIZE (1..maxNrofObjectId)) OF MeasObjectToAddMod

ReportConfigToRemoveList ::= SEQUENCE (SIZE (1..maxReportConfigId)) OF ReportConfigId

MeasReportQuantity ::= SEQUENCE {
   rsrp [0] BOOLEAN,
   rsrq [1] BOOLEAN,
   sinr [2] BOOLEAN
}

PeriodicalReportConfig ::= SEQUENCE {
   rsType [0] NR-RS-Type,
   reportInterval [1] ReportInterval,
   reportAmount [2] ENUMERATED { r1(0), r2(1), r4(2), r8(3), r16(4), r32(5), 
      r64(6), infinity(7) },
   reportQuantityCell [3] MeasReportQuantity,
   maxReportCells [4] INTEGER (1..maxCellReport),
   reportQuantityRS-Indexes [5] MeasReportQuantity OPTIONAL, -- Need R
   maxNrofRS-IndexesToReport [6] INTEGER (1..maxNrofIndexesToReport) OPTIONAL, -- Need R
   includeBeamMeasurements [7] BOOLEAN,
   useWhiteCellList [8] BOOLEAN,
   ...
}

MeasTriggerQuantity ::= CHOICE {
   rsrp [0] RSRP-Range,
   rsrq [1] RSRQ-Range,
   sinr [2] SINR-Range
}

MeasTriggerQuantityOffset ::= CHOICE {
   rsrp [0] INTEGER (-30..30),
   rsrq [1] INTEGER (-30..30),
   sinr [2] INTEGER (-30..30)
}

EventTriggerConfig ::= SEQUENCE {
   eventId [0] EXPLICIT CHOICE {
      eventA1 [0] SEQUENCE {
         a1-Threshold [0] EXPLICIT MeasTriggerQuantity,
         reportOnLeave [1] BOOLEAN,
         hysteresis [2] Hysteresis,
         timeToTrigger [3] TimeToTrigger
      },
      eventA2 [1] SEQUENCE {
         a2-Threshold [0] EXPLICIT MeasTriggerQuantity,
         reportOnLeave [1] BOOLEAN,
         hysteresis [2] Hysteresis,
         timeToTrigger [3] TimeToTrigger
      },
      eventA3 [2] SEQUENCE {
         a3-Offset [0] EXPLICIT MeasTriggerQuantityOffset,
         reportOnLeave [1] BOOLEAN,
         hysteresis [2] Hysteresis,
         timeToTrigger [3] TimeToTrigger,
         useWhiteCellList [4] BOOLEAN
      },
      eventA4 [3] SEQUENCE {
         a4-Threshold [0] EXPLICIT MeasTriggerQuantity,
         reportOnLeave [1] BOOLEAN,
         hysteresis [2] Hysteresis,
         timeToTrigger [3] TimeToTrigger,
         useWhiteCellList [4] BOOLEAN
      },
      eventA5 [4] SEQUENCE {
         a5-Threshold1 [0] EXPLICIT MeasTriggerQuantity,
         a5-Threshold2 [1] EXPLICIT MeasTriggerQuantity,
         reportOnLeave [2] BOOLEAN,
         hysteresis [3] Hysteresis,
         timeToTrigger [4] TimeToTrigger,
         useWhiteCellList [5] BOOLEAN
      },
      eventA6 [5] SEQUENCE {
         a6-Offset [0] EXPLICIT MeasTriggerQuantityOffset,
         reportOnLeave [1] BOOLEAN,
         hysteresis [2] Hysteresis,
         timeToTrigger [3] TimeToTrigger,
         useWhiteCellList [4] BOOLEAN
      },
      ...
   },
   rsType [1] NR-RS-Type,
   reportInterval [2] ReportInterval,
   reportAmount [3] ENUMERATED { r1(0), r2(1), r4(2), r8(3), r16(4), r32(5), 
      r64(6), infinity(7) },
   reportQuantityCell [4] MeasReportQuantity,
   maxReportCells [5] INTEGER (1..maxCellReport),
   reportQuantityRS-Indexes [6] MeasReportQuantity OPTIONAL, -- Need R
   maxNrofRS-IndexesToReport [7] INTEGER (1..maxNrofIndexesToReport) OPTIONAL, -- Need R
   includeBeamMeasurements [8] BOOLEAN,
   reportAddNeighMeas [9] ENUMERATED { setup(0) } OPTIONAL,
   ...
}

ReportCGI ::= SEQUENCE {
   cellForWhichToReportCGI [0] PhysCellId,
   ...
}

ReportSFTD-NR ::= SEQUENCE {
   reportSFTD-Meas [0] BOOLEAN,
   reportRSRP [1] BOOLEAN,
   ...,
   [[
      reportSFTD-NeighMeas [2] ENUMERATED { true(0) } OPTIONAL,
      drx-SFTD-NeighMeas [3] ENUMERATED { true(0) } OPTIONAL,
      cellsForWhichToReportSFTD [4] SEQUENCE (SIZE (1..maxCellSFTD)) OF PhysCellId OPTIONAL
   ]]
}

-- TAG-REPORTCONFIGINTERRAT-STOP
-- TAG-REPORTCONFIGNR-START
ReportConfigNR ::= SEQUENCE {
   reportType [0] EXPLICIT CHOICE {
      periodical [0] PeriodicalReportConfig,
      eventTriggered [1] EventTriggerConfig,
      ...,
      reportCGI [2] ReportCGI,
      reportSFTD [3] ReportSFTD-NR
   }
}

PeriodicalReportConfigInterRAT ::= SEQUENCE {
   reportInterval [0] ReportInterval,
   reportAmount [1] ENUMERATED { r1(0), r2(1), r4(2), r8(3), r16(4), r32(5), 
      r64(6), infinity(7) },
   reportQuantity [2] MeasReportQuantity,
   maxReportCells [3] INTEGER (1..maxCellReport),
   ...
}

-- TAG-MEASRESULTSCG-FAILURE-STOP
-- TAG-MEASTRIGGERQUANTITYEUTRA-START
MeasTriggerQuantityEUTRA ::= CHOICE {
   rsrp [0] RSRP-RangeEUTRA,
   rsrq [1] RSRQ-RangeEUTRA,
   sinr [2] SINR-RangeEUTRA
}

EventTriggerConfigInterRAT ::= SEQUENCE {
   eventId [0] EXPLICIT CHOICE {
      eventB1 [0] SEQUENCE {
         b1-ThresholdEUTRA [0] EXPLICIT MeasTriggerQuantityEUTRA,
         reportOnLeave [1] BOOLEAN,
         hysteresis [2] Hysteresis,
         timeToTrigger [3] TimeToTrigger,
         ...
      },
      eventB2 [1] SEQUENCE {
         b2-Threshold1 [0] EXPLICIT MeasTriggerQuantity,
         b2-Threshold2EUTRA [1] EXPLICIT MeasTriggerQuantityEUTRA,
         reportOnLeave [2] BOOLEAN,
         hysteresis [3] Hysteresis,
         timeToTrigger [4] TimeToTrigger,
         ...
      },
      ...
   },
   rsType [1] NR-RS-Type,
   reportInterval [2] ReportInterval,
   reportAmount [3] ENUMERATED { r1(0), r2(1), r4(2), r8(3), r16(4), r32(5), 
      r64(6), infinity(7) },
   reportQuantity [4] MeasReportQuantity,
   maxReportCells [5] INTEGER (1..maxCellReport),
   ...
}

ReportCGI-EUTRA ::= SEQUENCE {
   cellForWhichToReportCGI [0] EUTRA-PhysCellId,
   ...
}

ReportSFTD-EUTRA ::= SEQUENCE {
   reportSFTD-Meas [0] BOOLEAN,
   reportRSRP [1] BOOLEAN,
   ...
}

-- TAG-REPORTCONFIGID-STOP
-- TAG-REPORTCONFIGINTERRAT-START
ReportConfigInterRAT ::= SEQUENCE {
   reportType [0] EXPLICIT CHOICE {
      periodical [0] PeriodicalReportConfigInterRAT,
      eventTriggered [1] EventTriggerConfigInterRAT,
      reportCGI [2] ReportCGI-EUTRA,
      ...,
      reportSFTD [3] ReportSFTD-EUTRA
   }
}

ReportConfigToAddMod ::= SEQUENCE {
   reportConfigId [0] ReportConfigId,
   reportConfig [1] EXPLICIT CHOICE {
      reportConfigNR [0] ReportConfigNR,
      ...,
      reportConfigInterRAT [1] ReportConfigInterRAT
   }
}

-- TAG-REPORTCONFIGNR-STOP
-- TAG-REPORTCONFIGTOADDMODLIST-START
ReportConfigToAddModList ::= SEQUENCE (SIZE (1..maxReportConfigId)) OF ReportConfigToAddMod

MeasIdToRemoveList ::= SEQUENCE (SIZE (1..maxNrofMeasId)) OF MeasId

MeasIdToAddMod ::= SEQUENCE {
   measId [0] MeasId,
   measObjectId [1] MeasObjectId,
   reportConfigId [2] ReportConfigId
}

-- TAG-MEASID-STOP
-- TAG-MEASIDTOADDMODLIST-START
MeasIdToAddModList ::= SEQUENCE (SIZE (1..maxNrofMeasId)) OF MeasIdToAddMod

FilterConfig ::= SEQUENCE {
   filterCoefficientRSRP [0] FilterCoefficient DEFAULT fc4,
   filterCoefficientRSRQ [1] FilterCoefficient DEFAULT fc4,
   filterCoefficientRS-SINR [2] FilterCoefficient DEFAULT fc4
}

QuantityConfigRS ::= SEQUENCE {
   ssb-FilterConfig [0] FilterConfig,
   csi-RS-FilterConfig [1] FilterConfig
}

QuantityConfigNR ::= SEQUENCE {
   quantityConfigCell [0] QuantityConfigRS,
   quantityConfigRS-Index [1] QuantityConfigRS OPTIONAL -- Need M
}

-- TAG-Q-RXLEVMIN-STOP
-- TAG-QUANTITYCONFIG-START
QuantityConfig ::= SEQUENCE {
   quantityConfigNR-List [0] SEQUENCE (SIZE (1..maxNrofQuantityConfig)) OF QuantityConfigNR OPTIONAL,
   ...,
   [[
      quantityConfigEUTRA [1] FilterConfig OPTIONAL
   ]]
}

GapConfig ::= SEQUENCE {
   gapOffset [0] INTEGER (0..159),
   mgl [1] ENUMERATED { ms1dot5(0), ms3(1), ms3dot5(2), ms4(3), ms5dot5(4), 
      ms6(5) },
   mgrp [2] ENUMERATED { ms20(0), ms40(1), ms80(2), ms160(3) },
   mgta [3] ENUMERATED { ms0(0), ms0dot25(1), ms0dot5(2) },
   ...,
   [[
      refServCellIndicator [4] ENUMERATED { pCell(0), pSCell(1), mcg-FR2(2) }
          OPTIONAL
   ]]
}

-- TAG-MEASCONFIG-STOP
-- TAG-MEASGAPCONFIG-START
MeasGapConfig ::= SEQUENCE {
   gapFR2 [0] EXPLICIT CHOICE {
      release [0] NULL,
      setup [1] EXPLICIT GapConfig
   } OPTIONAL,
   ...,
   [[
      gapFR1 [1] EXPLICIT CHOICE {
         release [0] NULL,
         setup [1] EXPLICIT GapConfig
      } OPTIONAL,
      gapUE [2] EXPLICIT CHOICE {
         release [0] NULL,
         setup [1] EXPLICIT GapConfig
      } OPTIONAL
   ]]
}

-- TAG-MEASGAPCONFIG-STOP
-- TAG-MEASGAPSHARINGCONFIG-START
MeasGapSharingConfig ::= SEQUENCE {
   gapSharingFR2 [0] EXPLICIT CHOICE {
      release [0] NULL,
      setup [1] EXPLICIT MeasGapSharingScheme
   } OPTIONAL,
   ...,
   [[
      gapSharingFR1 [1] EXPLICIT CHOICE {
         release [0] NULL,
         setup [1] EXPLICIT MeasGapSharingScheme
      } OPTIONAL,
      gapSharingUE [2] EXPLICIT CHOICE {
         release [0] NULL,
         setup [1] EXPLICIT MeasGapSharingScheme
      } OPTIONAL
   ]]
}

-- TAG-MAC-CELLGROUPCONFIG-STOP
-- TAG-MEASCONFIG-START
MeasConfig ::= SEQUENCE {
   measObjectToRemoveList [0] MeasObjectToRemoveList OPTIONAL, -- Need N
   measObjectToAddModList [1] MeasObjectToAddModList OPTIONAL, -- Need N
   reportConfigToRemoveList [2] ReportConfigToRemoveList OPTIONAL, -- Need N
   reportConfigToAddModList [3] ReportConfigToAddModList OPTIONAL, -- Need N
   measIdToRemoveList [4] MeasIdToRemoveList OPTIONAL, -- Need N
   measIdToAddModList [5] MeasIdToAddModList OPTIONAL, -- Need N
   s-MeasureConfig [6] EXPLICIT CHOICE {
      ssb-RSRP [0] RSRP-Range,
      csi-RSRP [1] RSRP-Range
   } OPTIONAL, -- Need M
   quantityConfig [7] QuantityConfig OPTIONAL, -- Need M
   measGapConfig [8] MeasGapConfig OPTIONAL, -- Need M
   measGapSharingConfig [9] MeasGapSharingConfig OPTIONAL,
   ...
}

MasterKeyUpdate ::= SEQUENCE {
   keySetChangeIndicator [0] BOOLEAN,
   nextHopChainingCount [1] NextHopChainingCount,
   nas-Container [2] OCTET STRING OPTIONAL,
   ...
}

-- TAG-EUTRA-Q-OFFSETRANGE-STOP
-- TAG-OTHERCONFIG-START
OtherConfig ::= SEQUENCE {
   delayBudgetReportingConfig [0] EXPLICIT CHOICE {
      release [0] NULL,
      setup [1] SEQUENCE {
         delayBudgetReportingProhibitTimer [0] ENUMERATED { s0(0), s0dot4(1), 
            s0dot8(2), s1dot6(3), s3(4), s6(5), s12(6), s30(7) }
      }
   } OPTIONAL -- Need M
}

OverheatingAssistanceConfig ::= SEQUENCE {
   overheatingIndicationProhibitTimer [0] ENUMERATED { s0(0), s0dot5(1), s1(2)
      , s2(3), s5(4), s10(5), s20(6), s30(7), s60(8), s90(9), s120(10), 
      s300(11), s600(12), spare3(13), spare2(14), spare1(15) }
}

OtherConfig-v1540 ::= SEQUENCE {
   overheatingAssistanceConfig [0] EXPLICIT CHOICE {
      release [0] NULL,
      setup [1] EXPLICIT OverheatingAssistanceConfig
   } OPTIONAL,
   ...
}

MRDC-SecondaryCellGroupConfig ::= SEQUENCE {
   mrdc-ReleaseAndAdd [0] ENUMERATED { true(0) } OPTIONAL, -- Need N
   mrdc-SecondaryCellGroup [1] EXPLICIT CHOICE {
      nr-SCG [0] OCTET STRING (CONTAINING RRCReconfiguration),
      eutra-SCG [1] OCTET STRING
   }
}

RRCReconfiguration-v1560-IEs ::= SEQUENCE {
   mrdc-SecondaryCellGroupConfig [0] EXPLICIT CHOICE {
      release [0] NULL,
      setup [1] EXPLICIT MRDC-SecondaryCellGroupConfig
   } OPTIONAL, -- Need M
   radioBearerConfig2 [1] OCTET STRING (CONTAINING RadioBearerConfig) OPTIONAL,
       -- Need M
   sk-Counter [2] SK-Counter OPTIONAL, -- Need N
   nonCriticalExtension [3] SEQUENCE {

   } OPTIONAL
}

RRCReconfiguration-v1540-IEs ::= SEQUENCE {
   otherConfig-v1540 [0] OtherConfig-v1540 OPTIONAL, -- Need M
   nonCriticalExtension [1] RRCReconfiguration-v1560-IEs OPTIONAL
}

RRCReconfiguration-v1530-IEs ::= SEQUENCE {
   masterCellGroup [0] OCTET STRING (CONTAINING CellGroupConfig) OPTIONAL, -- Need M
   fullConfig [1] ENUMERATED { true(0) } OPTIONAL, -- Cond FullConfig
   dedicatedNAS-MessageList [2] SEQUENCE (SIZE (1..maxDRB)) OF DedicatedNAS-Message
       OPTIONAL, -- Cond nonHO
   masterKeyUpdate [3] MasterKeyUpdate OPTIONAL, -- Cond MasterKeyChange
   dedicatedSIB1-Delivery [4] OCTET STRING (CONTAINING SIB1) OPTIONAL, -- Need N
   dedicatedSystemInformationDelivery [5] OCTET STRING (CONTAINING 
      SystemInformation) OPTIONAL, -- Need N
   otherConfig [6] OtherConfig OPTIONAL, -- Need M
   nonCriticalExtension [7] RRCReconfiguration-v1540-IEs OPTIONAL
}

RRCReconfiguration-IEs ::= SEQUENCE {
   radioBearerConfig [0] RadioBearerConfig OPTIONAL, -- Need M
   secondaryCellGroup [1] OCTET STRING (CONTAINING CellGroupConfig) OPTIONAL, -- Need M
   measConfig [2] MeasConfig OPTIONAL, -- Need M
   lateNonCriticalExtension [3] OCTET STRING OPTIONAL,
   nonCriticalExtension [4] RRCReconfiguration-v1530-IEs OPTIONAL
}

-- TAG-RRCREESTABLISHMENTREQUEST-STOP
-- TAG-RRCRECONFIGURATION-START
RRCReconfiguration ::= SEQUENCE {
   rrc-TransactionIdentifier [0] RRC-TransactionIdentifier,
   criticalExtensions [1] EXPLICIT CHOICE {
      rrcReconfiguration [0] RRCReconfiguration-IEs,
      criticalExtensionsFuture [1] SEQUENCE {

      }
   }
}

RRCResume-v1560-IEs ::= SEQUENCE {
   radioBearerConfig2 [0] OCTET STRING (CONTAINING RadioBearerConfig) OPTIONAL,
       -- Need M
   sk-Counter [1] SK-Counter OPTIONAL, -- Need N
   nonCriticalExtension [2] SEQUENCE {

   } OPTIONAL
}

RRCResume-IEs ::= SEQUENCE {
   radioBearerConfig [0] RadioBearerConfig OPTIONAL, -- Need M
   masterCellGroup [1] OCTET STRING (CONTAINING CellGroupConfig) OPTIONAL, -- Need M
   measConfig [2] MeasConfig OPTIONAL, -- Need M
   fullConfig [3] ENUMERATED { true(0) } OPTIONAL, -- Need N
   lateNonCriticalExtension [4] OCTET STRING OPTIONAL,
   nonCriticalExtension [5] RRCResume-v1560-IEs OPTIONAL
}

-- TAG-RRCRELEASE-STOP
-- TAG-RRCRESUME-START
RRCResume ::= SEQUENCE {
   rrc-TransactionIdentifier [0] RRC-TransactionIdentifier,
   criticalExtensions [1] EXPLICIT CHOICE {
      rrcResume [0] RRCResume-IEs,
      criticalExtensionsFuture [1] SEQUENCE {

      }
   }
}

CarrierInfoNR ::= SEQUENCE {
   carrierFreq [0] ARFCN-ValueNR,
   ssbSubcarrierSpacing [1] SubcarrierSpacing,
   smtc [2] SSB-MTC OPTIONAL,
   ...
}

RedirectedCarrierInfo-EUTRA ::= SEQUENCE {
   eutraFrequency [0] ARFCN-ValueEUTRA,
   cnType [1] ENUMERATED { epc(0), fiveGC(1) } OPTIONAL -- Need N
}

RedirectedCarrierInfo ::= CHOICE {
   nr [0] CarrierInfoNR,
   eutra [1] RedirectedCarrierInfo-EUTRA,
   ...
}

FreqPriorityEUTRA ::= SEQUENCE {
   carrierFreq [0] ARFCN-ValueEUTRA,
   cellReselectionPriority [1] CellReselectionPriority,
   cellReselectionSubPriority [2] CellReselectionSubPriority OPTIONAL -- Need R
}

FreqPriorityListEUTRA ::= SEQUENCE (SIZE (1..maxFreq)) OF FreqPriorityEUTRA

FreqPriorityNR ::= SEQUENCE {
   carrierFreq [0] ARFCN-ValueNR,
   cellReselectionPriority [1] CellReselectionPriority,
   cellReselectionSubPriority [2] CellReselectionSubPriority OPTIONAL -- Need R
}

FreqPriorityListNR ::= SEQUENCE (SIZE (1..maxFreq)) OF FreqPriorityNR

CellReselectionPriorities ::= SEQUENCE {
   freqPriorityListEUTRA [0] FreqPriorityListEUTRA OPTIONAL, -- Need M
   freqPriorityListNR [1] FreqPriorityListNR OPTIONAL, -- Need M
   t320 [2] ENUMERATED { min5(0), min10(1), min20(2), min30(3), min60(4), 
      min120(5), min180(6), spare1(7) } OPTIONAL,
   ...
}

PLMN-RAN-AreaCell ::= SEQUENCE {
   plmn-Identity [0] PLMN-Identity OPTIONAL, -- Need S
   ran-AreaCells [1] SEQUENCE (SIZE (1..32)) OF CellIdentity
}

PLMN-RAN-AreaCellList ::= SEQUENCE (SIZE (1..maxPLMNIdentities)) OF PLMN-RAN-AreaCell

RAN-AreaConfig ::= SEQUENCE {
   trackingAreaCode [0] TrackingAreaCode,
   ran-AreaCodeList [1] SEQUENCE (SIZE (1..32)) OF RAN-AreaCode OPTIONAL -- Need R
}

PLMN-RAN-AreaConfig ::= SEQUENCE {
   plmn-Identity [0] PLMN-Identity OPTIONAL, -- Need S
   ran-Area [1] SEQUENCE (SIZE (1..16)) OF RAN-AreaConfig
}

PLMN-RAN-AreaConfigList ::= SEQUENCE (SIZE (1..maxPLMNIdentities)) OF PLMN-RAN-AreaConfig

RAN-NotificationAreaInfo ::= CHOICE {
   cellList [0] PLMN-RAN-AreaCellList,
   ran-AreaConfigList [1] PLMN-RAN-AreaConfigList,
   ...
}

SuspendConfig ::= SEQUENCE {
   fullI-RNTI [0] I-RNTI-Value,
   shortI-RNTI [1] ShortI-RNTI-Value,
   ran-PagingCycle [2] PagingCycle,
   ran-NotificationAreaInfo [3] EXPLICIT RAN-NotificationAreaInfo OPTIONAL, -- Need M
   t380 [4] PeriodicRNAU-TimerValue OPTIONAL, -- Need R
   nextHopChainingCount [5] NextHopChainingCount,
   ...
}

RRCRelease-v1540-IEs ::= SEQUENCE {
   waitTime [0] RejectWaitTime OPTIONAL, -- Need N
   nonCriticalExtension [1] SEQUENCE {

   } OPTIONAL
}

RRCRelease-IEs ::= SEQUENCE {
   redirectedCarrierInfo [0] EXPLICIT RedirectedCarrierInfo OPTIONAL, -- Need N
   cellReselectionPriorities [1] CellReselectionPriorities OPTIONAL, -- Need R
   suspendConfig [2] SuspendConfig OPTIONAL, -- Need R
   deprioritisationReq [3] SEQUENCE {
      deprioritisationType [0] ENUMERATED { frequency(0), nr(1) },
      deprioritisationTimer [1] ENUMERATED { min5(0), min10(1), min15(2), 
         min30(3) }
   } OPTIONAL, -- Need N
   lateNonCriticalExtension [4] OCTET STRING OPTIONAL,
   nonCriticalExtension [5] RRCRelease-v1540-IEs OPTIONAL
}

-- TAG-RRCREJECT-STOP
-- TAG-RRCRELEASE-START
RRCRelease ::= SEQUENCE {
   rrc-TransactionIdentifier [0] RRC-TransactionIdentifier,
   criticalExtensions [1] EXPLICIT CHOICE {
      rrcRelease [0] RRCRelease-IEs,
      criticalExtensionsFuture [1] SEQUENCE {

      }
   }
}

RRCReestablishment-IEs ::= SEQUENCE {
   nextHopChainingCount [0] NextHopChainingCount,
   lateNonCriticalExtension [1] OCTET STRING OPTIONAL,
   nonCriticalExtension [2] SEQUENCE {

   } OPTIONAL
}

-- TAG-PAGING-STOP
-- TAG-RRCREESTABLISHMENT-START
RRCReestablishment ::= SEQUENCE {
   rrc-TransactionIdentifier [0] RRC-TransactionIdentifier,
   criticalExtensions [1] EXPLICIT CHOICE {
      rrcReestablishment [0] RRCReestablishment-IEs,
      criticalExtensionsFuture [1] SEQUENCE {

      }
   }
}

SecurityConfigSMC ::= SEQUENCE {
   securityAlgorithmConfig [0] SecurityAlgorithmConfig,
   ...
}

SecurityModeCommand-IEs ::= SEQUENCE {
   securityConfigSMC [0] SecurityConfigSMC,
   lateNonCriticalExtension [1] OCTET STRING OPTIONAL,
   nonCriticalExtension [2] SEQUENCE {

   } OPTIONAL
}

-- TAG-SCGFAILUREINFORMATIONEUTRA-STOP
-- TAG-SECURITYMODECOMMAND-START
SecurityModeCommand ::= SEQUENCE {
   rrc-TransactionIdentifier [0] RRC-TransactionIdentifier,
   criticalExtensions [1] EXPLICIT CHOICE {
      securityModeCommand [0] SecurityModeCommand-IEs,
      criticalExtensionsFuture [1] SEQUENCE {

      }
   }
}

DLInformationTransfer-IEs ::= SEQUENCE {
   dedicatedNAS-Message [0] DedicatedNAS-Message OPTIONAL, -- Need N
   lateNonCriticalExtension [1] OCTET STRING OPTIONAL,
   nonCriticalExtension [2] SEQUENCE {

   } OPTIONAL
}

-- TAG-COUNTERCHECKRESPONSE-STOP
-- TAG-DLINFORMATIONTRANSFER-START
DLInformationTransfer ::= SEQUENCE {
   rrc-TransactionIdentifier [0] RRC-TransactionIdentifier,
   criticalExtensions [1] EXPLICIT CHOICE {
      dlInformationTransfer [0] DLInformationTransfer-IEs,
      criticalExtensionsFuture [1] SEQUENCE {

      }
   }
}

UE-CapabilityRAT-Request ::= SEQUENCE {
   rat-Type [0] RAT-Type,
   capabilityRequestFilter [1] OCTET STRING OPTIONAL,
   ...
}

-- TAG-UE-CAPABILITYRAT-CONTAINERLIST-STOP
-- TAG-UE-CAPABILITYRAT-REQUESTLIST-START
UE-CapabilityRAT-RequestList ::= SEQUENCE (SIZE (1..maxRAT-CapabilityContainers)) OF 
   UE-CapabilityRAT-Request

-- TAG-UE-CAPABILITYRAT-REQUESTLIST-STOP
-- TAG-UE-CAPABILITYREQUESTFILTERCOMMON-START
UE-CapabilityRequestFilterCommon ::= SEQUENCE {
   mrdc-Request [0] SEQUENCE {
      omitEN-DC [0] ENUMERATED { true(0) } OPTIONAL, -- Need N
      includeNR-DC [1] ENUMERATED { true(0) } OPTIONAL, -- Need N
      includeNE-DC [2] ENUMERATED { true(0) } OPTIONAL -- Need N
   } OPTIONAL,
   ...
}

UECapabilityEnquiry-v1560-IEs ::= SEQUENCE {
   capabilityRequestFilterCommon [0] UE-CapabilityRequestFilterCommon OPTIONAL,
       -- Need N
   nonCriticalExtension [1] SEQUENCE {

   } OPTIONAL
}

UECapabilityEnquiry-IEs ::= SEQUENCE {
   ue-CapabilityRAT-RequestList [0] UE-CapabilityRAT-RequestList,
   lateNonCriticalExtension [1] OCTET STRING OPTIONAL,
   ue-CapabilityEnquiryExt [2] OCTET STRING (CONTAINING 
      UECapabilityEnquiry-v1560-IEs) OPTIONAL
}

-- TAG-UEASSISTANCEINFORMATION-STOP
-- TAG-UECAPABILITYENQUIRY-START
UECapabilityEnquiry ::= SEQUENCE {
   rrc-TransactionIdentifier [0] RRC-TransactionIdentifier,
   criticalExtensions [1] EXPLICIT CHOICE {
      ueCapabilityEnquiry [0] UECapabilityEnquiry-IEs,
      criticalExtensionsFuture [1] SEQUENCE {

      }
   }
}

DRB-CountMSB-Info ::= SEQUENCE {
   drb-Identity [0] DRB-Identity,
   countMSB-Uplink [1] INTEGER (0..33554431),
   countMSB-Downlink [2] INTEGER (0..33554431)
}

DRB-CountMSB-InfoList ::= SEQUENCE (SIZE (1..maxDRB)) OF DRB-CountMSB-Info

CounterCheck-IEs ::= SEQUENCE {
   drb-CountMSB-InfoList [0] DRB-CountMSB-InfoList,
   lateNonCriticalExtension [1] OCTET STRING OPTIONAL,
   nonCriticalExtension [2] SEQUENCE {

   } OPTIONAL
}

-- TAG-UL-DCCH-MESSAGE-STOP
-- TAG-COUNTERCHECK-START
CounterCheck ::= SEQUENCE {
   rrc-TransactionIdentifier [0] RRC-TransactionIdentifier,
   criticalExtensions [1] EXPLICIT CHOICE {
      counterCheck [0] CounterCheck-IEs,
      criticalExtensionsFuture [1] SEQUENCE {

      }
   }
}

MobilityFromNRCommand-IEs ::= SEQUENCE {
   targetRAT-Type [0] ENUMERATED { eutra(0), spare3(1), spare2(2), spare1(3)
      , ... },
   targetRAT-MessageContainer [1] OCTET STRING,
   nas-SecurityParamFromNR [2] OCTET STRING OPTIONAL, -- Cond HO-ToEPC
   lateNonCriticalExtension [3] OCTET STRING OPTIONAL,
   nonCriticalExtension [4] SEQUENCE {

   } OPTIONAL
}

-- TAG-MIB-STOP
-- TAG-MOBILITYFROMNRCOMMAND-START
MobilityFromNRCommand ::= SEQUENCE {
   rrc-TransactionIdentifier [0] RRC-TransactionIdentifier,
   criticalExtensions [1] EXPLICIT CHOICE {
      mobilityFromNRCommand [0] MobilityFromNRCommand-IEs,
      criticalExtensionsFuture [1] SEQUENCE {

      }
   }
}

DL-DCCH-MessageType ::= CHOICE {
   c1 [0] EXPLICIT CHOICE {
      rrcReconfiguration [0] RRCReconfiguration,
      rrcResume [1] RRCResume,
      rrcRelease [2] RRCRelease,
      rrcReestablishment [3] RRCReestablishment,
      securityModeCommand [4] SecurityModeCommand,
      dlInformationTransfer [5] DLInformationTransfer,
      ueCapabilityEnquiry [6] UECapabilityEnquiry,
      counterCheck [7] CounterCheck,
      mobilityFromNRCommand [8] MobilityFromNRCommand,
      spare7 [9] NULL,
      spare6 [10] NULL,
      spare5 [11] NULL,
      spare4 [12] NULL,
      spare3 [13] NULL,
      spare2 [14] NULL,
      spare1 [15] NULL
   },
   messageClassExtension [1] SEQUENCE {

   }
}

-- TAG-DL-CCCH-MESSAGE-STOP
-- TAG-DL-DCCH-MESSAGE-START
DL-DCCH-Message ::= SEQUENCE {
   message [0] EXPLICIT DL-DCCH-MessageType
}

PagingUE-Identity ::= CHOICE {
   ng-5G-S-TMSI [0] NG-5G-S-TMSI,
   fullI-RNTI [1] I-RNTI-Value,
   ...
}

PagingRecord ::= SEQUENCE {
   ue-Identity [0] EXPLICIT PagingUE-Identity,
   accessType [1] ENUMERATED { non3GPP(0) } OPTIONAL,
   ...
}

PagingRecordList ::= SEQUENCE (SIZE (1..maxNrofPageRec)) OF PagingRecord

-- TAG-MOBILITYFROMNRCOMMAND-STOP
-- TAG-PAGING-START
Paging ::= SEQUENCE {
   pagingRecordList [0] PagingRecordList OPTIONAL, -- Need N
   lateNonCriticalExtension [1] OCTET STRING OPTIONAL,
   nonCriticalExtension [2] SEQUENCE {

   } OPTIONAL
}

PCCH-MessageType ::= CHOICE {
   c1 [0] EXPLICIT CHOICE {
      paging [0] Paging,
      spare1 [1] NULL
   },
   messageClassExtension [1] SEQUENCE {

   }
}

-- TAG-DL-DCCH-MESSAGE-STOP
-- TAG-PCCH-PCH-MESSAGE-START
PCCH-Message ::= SEQUENCE {
   message [0] EXPLICIT PCCH-MessageType
}

InitialUE-Identity ::= CHOICE {
   ng-5G-S-TMSI-Part1 [0] BIT STRING  (SIZE (39)),
   randomValue [1] BIT STRING  (SIZE (39))
}

RRCSetupRequest-IEs ::= SEQUENCE {
   ue-Identity [0] EXPLICIT InitialUE-Identity,
   establishmentCause [1] EstablishmentCause,
   spare [2] BIT STRING  (SIZE (1))
}

-- TAG-RRCSETUPCOMPLETE-STOP
-- TAG-RRCSETUPREQUEST-START
RRCSetupRequest ::= SEQUENCE {
   rrcSetupRequest [0] RRCSetupRequest-IEs
}

RRCResumeRequest-IEs ::= SEQUENCE {
   resumeIdentity [0] ShortI-RNTI-Value,
   resumeMAC-I [1] BIT STRING  (SIZE (16)),
   resumeCause [2] ResumeCause,
   spare [3] BIT STRING  (SIZE (1))
}

-- TAG-RRCRESUMECOMPLETE-STOP
-- TAG-RRCRESUMEREQUEST-START
RRCResumeRequest ::= SEQUENCE {
   rrcResumeRequest [0] RRCResumeRequest-IEs
}

ReestabUE-Identity ::= SEQUENCE {
   c-RNTI [0] RNTI-Value,
   physCellId [1] PhysCellId,
   shortMAC-I [2] ShortMAC-I
}

RRCReestablishmentRequest-IEs ::= SEQUENCE {
   ue-Identity [0] ReestabUE-Identity,
   reestablishmentCause [1] ReestablishmentCause,
   spare [2] BIT STRING  (SIZE (1))
}

-- TAG-RRCREESTABLISHMENTCOMPLETE-STOP
-- TAG-RRCREESTABLISHMENTREQUEST-START
RRCReestablishmentRequest ::= SEQUENCE {
   rrcReestablishmentRequest [0] RRCReestablishmentRequest-IEs
}

RRCSystemInfoRequest-IEs ::= SEQUENCE {
   requested-SI-List [0] BIT STRING  (SIZE (maxSI-Message)), --32bits
   spare [1] BIT STRING  (SIZE (12))
}

-- TAG-RRCSETUPREQUEST-STOP
-- TAG-RRCSYSTEMINFOREQUEST-START
RRCSystemInfoRequest ::= SEQUENCE {
   criticalExtensions [0] EXPLICIT CHOICE {
      rrcSystemInfoRequest [0] RRCSystemInfoRequest-IEs,
      criticalExtensionsFuture [1] SEQUENCE {

      }
   }
}

UL-CCCH-MessageType ::= CHOICE {
   c1 [0] EXPLICIT CHOICE {
      rrcSetupRequest [0] RRCSetupRequest,
      rrcResumeRequest [1] RRCResumeRequest,
      rrcReestablishmentRequest [2] RRCReestablishmentRequest,
      rrcSystemInfoRequest [3] RRCSystemInfoRequest
   },
   messageClassExtension [1] SEQUENCE {

   }
}

-- TAG-PCCH-PCH-MESSAGE-STOP
-- TAG-UL-CCCH-MESSAGE-START
UL-CCCH-Message ::= SEQUENCE {
   message [0] EXPLICIT UL-CCCH-MessageType
}

RRCResumeRequest1-IEs ::= SEQUENCE {
   resumeIdentity [0] I-RNTI-Value,
   resumeMAC-I [1] BIT STRING  (SIZE (16)),
   resumeCause [2] ResumeCause,
   spare [3] BIT STRING  (SIZE (1))
}

-- TAG-RRCRESUMEREQUEST-STOP
-- TAG-RRCRESUMEREQUEST1-START
RRCResumeRequest1 ::= SEQUENCE {
   rrcResumeRequest1 [0] RRCResumeRequest1-IEs
}

UL-CCCH1-MessageType ::= CHOICE {
   c1 [0] EXPLICIT CHOICE {
      rrcResumeRequest1 [0] RRCResumeRequest1,
      spare3 [1] NULL,
      spare2 [2] NULL,
      spare1 [3] NULL
   },
   messageClassExtension [1] SEQUENCE {

   }
}

-- TAG-UL-CCCH-MESSAGE-STOP
-- TAG-UL-CCCH1-MESSAGE-START
UL-CCCH1-Message ::= SEQUENCE {
   message [0] EXPLICIT UL-CCCH1-MessageType
}

MeasQuantityResults ::= SEQUENCE {
   rsrp [0] RSRP-Range OPTIONAL,
   rsrq [1] RSRQ-Range OPTIONAL,
   sinr [2] SINR-Range OPTIONAL
}

ResultsPerSSB-Index ::= SEQUENCE {
   ssb-Index [0] SSB-Index,
   ssb-Results [1] MeasQuantityResults OPTIONAL
}

ResultsPerSSB-IndexList ::= SEQUENCE (SIZE (1..maxNrofIndexesToReport2)) OF ResultsPerSSB-Index

ResultsPerCSI-RS-Index ::= SEQUENCE {
   csi-RS-Index [0] CSI-RS-Index,
   csi-RS-Results [1] MeasQuantityResults OPTIONAL
}

ResultsPerCSI-RS-IndexList ::= SEQUENCE (SIZE (1..maxNrofIndexesToReport2)) OF ResultsPerCSI-RS-Index

-- TAG-CGI-INFOEUTRA-STOP
-- TAG-CGI-INFO-NR-START
CGI-InfoNR ::= SEQUENCE {
   plmn-IdentityInfoList [0] PLMN-IdentityInfoList OPTIONAL,
   frequencyBandList [1] MultiFrequencyBandListNR OPTIONAL,
   noSIB1 [2] SEQUENCE {
      ssb-SubcarrierOffset [0] INTEGER (0..15),
      pdcch-ConfigSIB1 [1] PDCCH-ConfigSIB1
   } OPTIONAL,
   ...
}

MeasResultNR ::= SEQUENCE {
   physCellId [0] PhysCellId OPTIONAL,
   measResult [1] SEQUENCE {
      cellResults [0] SEQUENCE {
         resultsSSB-Cell [0] MeasQuantityResults OPTIONAL,
         resultsCSI-RS-Cell [1] MeasQuantityResults OPTIONAL
      },
      rsIndexResults [1] SEQUENCE {
         resultsSSB-Indexes [0] ResultsPerSSB-IndexList OPTIONAL,
         resultsCSI-RS-Indexes [1] ResultsPerCSI-RS-IndexList OPTIONAL
      } OPTIONAL
   },
   ...,
   [[
      cgi-Info [2] CGI-InfoNR OPTIONAL
   ]]
}

MeasResultServMO ::= SEQUENCE {
   servCellId [0] ServCellIndex,
   measResultServingCell [1] MeasResultNR,
   measResultBestNeighCell [2] MeasResultNR OPTIONAL,
   ...
}

MeasResultServMOList ::= SEQUENCE (SIZE (1..maxNrofServingCells)) OF MeasResultServMO

MeasResultListNR ::= SEQUENCE (SIZE (1..maxCellReport)) OF MeasResultNR

MeasQuantityResultsEUTRA ::= SEQUENCE {
   rsrp [0] RSRP-RangeEUTRA OPTIONAL,
   rsrq [1] RSRQ-RangeEUTRA OPTIONAL,
   sinr [2] SINR-RangeEUTRA OPTIONAL
}

PLMN-IdentityList-EUTRA-EPC ::= SEQUENCE (SIZE (1..maxPLMN)) OF PLMN-Identity

-- TAG-CELLACCESSRELATEDINFOEUTRA-5GC-STOP
-- TAG-CELLACCESSRELATEDINFOEUTRA-EPC-START
CellAccessRelatedInfo-EUTRA-EPC ::= SEQUENCE {
   plmn-IdentityList-eutra-epc [0] PLMN-IdentityList-EUTRA-EPC,
   trackingAreaCode-eutra-epc [1] BIT STRING  (SIZE (16)),
   cellIdentity-eutra-epc [2] BIT STRING  (SIZE (28))
}

PLMN-Identity-EUTRA-5GC ::= CHOICE {
   plmn-Identity-EUTRA-5GC [0] PLMN-Identity,
   plmn-index [1] INTEGER (1..maxPLMN)
}

PLMN-IdentityList-EUTRA-5GC ::= SEQUENCE (SIZE (1..maxPLMN)) OF PLMN-Identity-EUTRA-5GC
   

CellIdentity-EUTRA-5GC ::= CHOICE {
   cellIdentity-EUTRA [0] BIT STRING  (SIZE (28)),
   cellId-index [1] INTEGER (1..maxPLMN)
}

-- TAG-CELLACCESSRELATEDINFO-STOP
-- TAG-CELLACCESSRELATEDINFOEUTRA-5GC-START
CellAccessRelatedInfo-EUTRA-5GC ::= SEQUENCE {
   plmn-IdentityList-eutra-5gc [0] PLMN-IdentityList-EUTRA-5GC,
   trackingAreaCode-eutra-5gc [1] TrackingAreaCode,
   ranac-5gc [2] RAN-AreaCode OPTIONAL,
   cellIdentity-eutra-5gc [3] EXPLICIT CellIdentity-EUTRA-5GC
}

MultiBandInfoListEUTRA ::= SEQUENCE (SIZE (1..maxMultiBands)) OF FreqBandIndicatorEUTRA

-- TAG-CELLRESELECTIONSUBPRIORITY-STOP
-- TAG-CGI-INFOEUTRA-START
CGI-InfoEUTRA ::= SEQUENCE {
   cgi-info-EPC [0] SEQUENCE {
      cgi-info-EPC-legacy [0] CellAccessRelatedInfo-EUTRA-EPC,
      cgi-info-EPC-list [1] SEQUENCE (SIZE (1..maxPLMN)) OF 
         CellAccessRelatedInfo-EUTRA-EPC OPTIONAL
   } OPTIONAL,
   cgi-info-5GC [1] SEQUENCE (SIZE (1..maxPLMN)) OF CellAccessRelatedInfo-EUTRA-5GC
       OPTIONAL,
   freqBandIndicator [2] FreqBandIndicatorEUTRA,
   multiBandInfoList [3] MultiBandInfoListEUTRA OPTIONAL,
   freqBandIndicatorPriority [4] ENUMERATED { true(0) } OPTIONAL
}

MeasResultEUTRA ::= SEQUENCE {
   eutra-PhysCellId [0] PhysCellId,
   measResult [1] MeasQuantityResultsEUTRA,
   cgi-Info [2] CGI-InfoEUTRA OPTIONAL,
   ...
}

MeasResultListEUTRA ::= SEQUENCE (SIZE (1..maxCellReport)) OF MeasResultEUTRA

-- TAG-MEASRESULTS-STOP
-- TAG-MEASRESULT2EUTRA-START
MeasResult2EUTRA ::= SEQUENCE {
   carrierFreq [0] ARFCN-ValueEUTRA,
   measResultServingCell [1] MeasResultEUTRA OPTIONAL,
   measResultBestNeighCell [2] MeasResultEUTRA OPTIONAL,
   ...
}

MeasResultServFreqListEUTRA-SCG ::= SEQUENCE (SIZE (1..maxNrofServingCellsEUTRA)) OF MeasResult2EUTRA

-- TAG-MEASRESULT2EUTRA-STOP
-- TAG-MEASRESULT2NR-START
MeasResult2NR ::= SEQUENCE {
   ssbFrequency [0] ARFCN-ValueNR OPTIONAL,
   refFreqCSI-RS [1] ARFCN-ValueNR OPTIONAL,
   measResultServingCell [2] MeasResultNR OPTIONAL,
   measResultNeighCellListNR [3] MeasResultListNR OPTIONAL,
   ...
}

MeasResultServFreqListNR-SCG ::= SEQUENCE (SIZE (1..maxNrofServingCells)) OF MeasResult2NR

MeasResultSFTD-EUTRA ::= SEQUENCE {
   eutra-PhysCellId [0] EUTRA-PhysCellId,
   sfn-OffsetResult [1] INTEGER (0..1023),
   frameBoundaryOffsetResult [2] INTEGER (-30720..30719),
   rsrp-Result [3] RSRP-Range OPTIONAL
}

MeasResultCellSFTD-NR ::= SEQUENCE {
   physCellId [0] PhysCellId,
   sfn-OffsetResult [1] INTEGER (0..1023),
   frameBoundaryOffsetResult [2] INTEGER (-30720..30719),
   rsrp-Result [3] RSRP-Range OPTIONAL
}

-- TAG-MEASOBJECTTOADDMODLIST-STOP
-- TAG-MEASRESULTCELLLISTSFTD-NR-START
MeasResultCellListSFTD-NR ::= SEQUENCE (SIZE (1..maxCellSFTD)) OF MeasResultCellSFTD-NR

-- TAG-MEASRESULTCELLLISTSFTD-EUTRA-STOP
-- TAG-MEASRESULTS-START
MeasResults ::= SEQUENCE {
   measId [0] MeasId,
   measResultServingMOList [1] MeasResultServMOList,
   measResultNeighCells [2] EXPLICIT CHOICE {
      measResultListNR [0] MeasResultListNR,
      ...,
      measResultListEUTRA [1] MeasResultListEUTRA
   } OPTIONAL,
   ...,
   [[
      measResultServFreqListEUTRA-SCG [3] MeasResultServFreqListEUTRA-SCG
          OPTIONAL,
      measResultServFreqListNR-SCG [4] MeasResultServFreqListNR-SCG OPTIONAL,
      measResultSFTD-EUTRA [5] MeasResultSFTD-EUTRA OPTIONAL,
      measResultSFTD-NR [6] MeasResultCellSFTD-NR OPTIONAL
   ]],
   [[
      measResultCellListSFTD-NR [7] MeasResultCellListSFTD-NR OPTIONAL
   ]]
}

MeasurementReport-IEs ::= SEQUENCE {
   measResults [0] MeasResults,
   lateNonCriticalExtension [1] OCTET STRING OPTIONAL,
   nonCriticalExtension [2] SEQUENCE {

   } OPTIONAL
}

-- TAG-LOCATIONMEASUREMENTINDICATION-STOP
-- TAG-MEASUREMENTREPORT-START
MeasurementReport ::= SEQUENCE {
   criticalExtensions [0] EXPLICIT CHOICE {
      measurementReport [0] MeasurementReport-IEs,
      criticalExtensionsFuture [1] SEQUENCE {

      }
   }
}

UplinkTxDirectCurrentBWP ::= SEQUENCE {
   bwp-Id [0] BWP-Id,
   shift7dot5kHz [1] BOOLEAN,
   txDirectCurrentLocation [2] INTEGER (0..3301)
}

UplinkTxDirectCurrentCell ::= SEQUENCE {
   servCellIndex [0] ServCellIndex,
   uplinkDirectCurrentBWP [1] SEQUENCE (SIZE (1..maxNrofBWPs)) OF UplinkTxDirectCurrentBWP,
   ...,
   [[
      uplinkDirectCurrentBWP-SUL [2] SEQUENCE (SIZE (1..maxNrofBWPs)) OF 
         UplinkTxDirectCurrentBWP OPTIONAL
   ]]
}

-- TAG-UPLINKCONFIGCOMMONSIB-STOP
-- TAG-UPLINKTXDIRECTCURRENTLIST-START
UplinkTxDirectCurrentList ::= SEQUENCE (SIZE (1..maxNrofServingCells)) OF UplinkTxDirectCurrentCell
   

RRCReconfigurationComplete-v1560-IEs ::= SEQUENCE {
   scg-Response [0] EXPLICIT CHOICE {
      nr-SCG-Response [0] OCTET STRING (CONTAINING RRCReconfigurationComplete),
      eutra-SCG-Response [1] OCTET STRING
   } OPTIONAL,
   nonCriticalExtension [1] SEQUENCE {

   } OPTIONAL
}

RRCReconfigurationComplete-v1530-IEs ::= SEQUENCE {
   uplinkTxDirectCurrentList [0] UplinkTxDirectCurrentList OPTIONAL,
   nonCriticalExtension [1] RRCReconfigurationComplete-v1560-IEs OPTIONAL
}

RRCReconfigurationComplete-IEs ::= SEQUENCE {
   lateNonCriticalExtension [0] OCTET STRING OPTIONAL,
   nonCriticalExtension [1] RRCReconfigurationComplete-v1530-IEs OPTIONAL
}

-- TAG-RRCRECONFIGURATION-STOP
-- TAG-RRCRECONFIGURATIONCOMPLETE-START
RRCReconfigurationComplete ::= SEQUENCE {
   rrc-TransactionIdentifier [0] RRC-TransactionIdentifier,
   criticalExtensions [1] EXPLICIT CHOICE {
      rrcReconfigurationComplete [0] RRCReconfigurationComplete-IEs,
      criticalExtensionsFuture [1] SEQUENCE {

      }
   }
}

RegisteredAMF ::= SEQUENCE {
   plmn-Identity [0] PLMN-Identity OPTIONAL,
   amf-Identifier [1] AMF-Identifier
}

-- TAG-SLOTFORMATINDICATOR-STOP
-- TAG-S-NSSAI-START
S-NSSAI ::= CHOICE {
   sst [0] BIT STRING  (SIZE (8)),
   sst-SD [1] BIT STRING  (SIZE (32))
}

RRCSetupComplete-IEs ::= SEQUENCE {
   selectedPLMN-Identity [0] INTEGER (1..maxPLMN),
   registeredAMF [1] RegisteredAMF OPTIONAL,
   guami-Type [2] ENUMERATED { native(0), mapped(1) } OPTIONAL,
   s-NSSAI-List [3] SEQUENCE (SIZE (1..maxNrofS-NSSAI)) OF S-NSSAI OPTIONAL,
   dedicatedNAS-Message [4] DedicatedNAS-Message,
   ng-5G-S-TMSI-Value [5] EXPLICIT CHOICE {
      ng-5G-S-TMSI [0] NG-5G-S-TMSI,
      ng-5G-S-TMSI-Part2 [1] BIT STRING  (SIZE (9))
   } OPTIONAL,
   lateNonCriticalExtension [6] OCTET STRING OPTIONAL,
   nonCriticalExtension [7] SEQUENCE {

   } OPTIONAL
}

-- TAG-RRCSETUP-STOP
-- TAG-RRCSETUPCOMPLETE-START
RRCSetupComplete ::= SEQUENCE {
   rrc-TransactionIdentifier [0] RRC-TransactionIdentifier,
   criticalExtensions [1] EXPLICIT CHOICE {
      rrcSetupComplete [0] RRCSetupComplete-IEs,
      criticalExtensionsFuture [1] SEQUENCE {

      }
   }
}

RRCReestablishmentComplete-IEs ::= SEQUENCE {
   lateNonCriticalExtension [0] OCTET STRING OPTIONAL,
   nonCriticalExtension [1] SEQUENCE {

   } OPTIONAL
}

-- TAG-RRCREESTABLISHMENT-STOP
-- TAG-RRCREESTABLISHMENTCOMPLETE-START
RRCReestablishmentComplete ::= SEQUENCE {
   rrc-TransactionIdentifier [0] RRC-TransactionIdentifier,
   criticalExtensions [1] EXPLICIT CHOICE {
      rrcReestablishmentComplete [0] RRCReestablishmentComplete-IEs,
      criticalExtensionsFuture [1] SEQUENCE {

      }
   }
}

RRCResumeComplete-IEs ::= SEQUENCE {
   dedicatedNAS-Message [0] DedicatedNAS-Message OPTIONAL,
   selectedPLMN-Identity [1] INTEGER (1..maxPLMN) OPTIONAL,
   uplinkTxDirectCurrentList [2] UplinkTxDirectCurrentList OPTIONAL,
   lateNonCriticalExtension [3] OCTET STRING OPTIONAL,
   nonCriticalExtension [4] SEQUENCE {

   } OPTIONAL
}

-- TAG-RRCRESUME-STOP
-- TAG-RRCRESUMECOMPLETE-START
RRCResumeComplete ::= SEQUENCE {
   rrc-TransactionIdentifier [0] RRC-TransactionIdentifier,
   criticalExtensions [1] EXPLICIT CHOICE {
      rrcResumeComplete [0] RRCResumeComplete-IEs,
      criticalExtensionsFuture [1] SEQUENCE {

      }
   }
}

SecurityModeComplete-IEs ::= SEQUENCE {
   lateNonCriticalExtension [0] OCTET STRING OPTIONAL,
   nonCriticalExtension [1] SEQUENCE {

   } OPTIONAL
}

-- TAG-SECURITYMODECOMMAND-STOP
-- TAG-SECURITYMODECOMPLETE-START
SecurityModeComplete ::= SEQUENCE {
   rrc-TransactionIdentifier [0] RRC-TransactionIdentifier,
   criticalExtensions [1] EXPLICIT CHOICE {
      securityModeComplete [0] SecurityModeComplete-IEs,
      criticalExtensionsFuture [1] SEQUENCE {

      }
   }
}

SecurityModeFailure-IEs ::= SEQUENCE {
   lateNonCriticalExtension [0] OCTET STRING OPTIONAL,
   nonCriticalExtension [1] SEQUENCE {

   } OPTIONAL
}

-- TAG-SECURITYMODECOMPLETE-STOP
-- TAG-SECURITYMODEFAILURE-START
SecurityModeFailure ::= SEQUENCE {
   rrc-TransactionIdentifier [0] RRC-TransactionIdentifier,
   criticalExtensions [1] EXPLICIT CHOICE {
      securityModeFailure [0] SecurityModeFailure-IEs,
      criticalExtensionsFuture [1] SEQUENCE {

      }
   }
}

ULInformationTransfer-IEs ::= SEQUENCE {
   dedicatedNAS-Message [0] DedicatedNAS-Message OPTIONAL,
   lateNonCriticalExtension [1] OCTET STRING OPTIONAL,
   nonCriticalExtension [2] SEQUENCE {

   } OPTIONAL
}

-- TAG-UECAPABILITYINFORMATION-STOP
-- TAG-ULINFORMATIONTRANSFER-START
ULInformationTransfer ::= SEQUENCE {
   criticalExtensions [0] EXPLICIT CHOICE {
      ulInformationTransfer [0] ULInformationTransfer-IEs,
      criticalExtensionsFuture [1] SEQUENCE {

      }
   }
}

EUTRA-RSTD-Info ::= SEQUENCE {
   carrierFreq [0] ARFCN-ValueEUTRA,
   measPRS-Offset [1] INTEGER (0..39),
   ...
}

EUTRA-RSTD-InfoList ::= SEQUENCE (SIZE (1..maxInterRAT-RSTD-Freq)) OF EUTRA-RSTD-Info

-- TAG-I-RNTI-VALUE-STOP
-- TAG-LOCATIONMEASUREMENTINFO-START
LocationMeasurementInfo ::= CHOICE {
   eutra-RSTD [0] EUTRA-RSTD-InfoList,
   ...,
   eutra-FineTimingDetection [1] NULL
}

LocationMeasurementIndication-IEs ::= SEQUENCE {
   measurementIndication [0] EXPLICIT CHOICE {
      release [0] NULL,
      setup [1] EXPLICIT LocationMeasurementInfo
   },
   lateNonCriticalExtension [1] OCTET STRING OPTIONAL,
   nonCriticalExtension [2] SEQUENCE {

   } OPTIONAL
}

-- TAG-FAILUREINFORMATION-STOP
-- TAG-LOCATIONMEASUREMENTINDICATION-START
LocationMeasurementIndication ::= SEQUENCE {
   criticalExtensions [0] EXPLICIT CHOICE {
      locationMeasurementIndication [0] LocationMeasurementIndication-IEs,
      criticalExtensionsFuture [1] SEQUENCE {

      }
   }
}

UE-CapabilityRAT-Container ::= SEQUENCE {
   rat-Type [0] RAT-Type,
   ue-CapabilityRAT-Container [1] OCTET STRING
}

-- TAG-SUPPORTEDBANDWIDTH-STOP
-- TAG-UE-CAPABILITYRAT-CONTAINERLIST-START
UE-CapabilityRAT-ContainerList ::= SEQUENCE (SIZE (0..maxRAT-CapabilityContainers)) OF 
   UE-CapabilityRAT-Container

UECapabilityInformation-IEs ::= SEQUENCE {
   ue-CapabilityRAT-ContainerList [0] UE-CapabilityRAT-ContainerList OPTIONAL,
   lateNonCriticalExtension [1] OCTET STRING OPTIONAL,
   nonCriticalExtension [2] SEQUENCE {

   } OPTIONAL
}

-- TAG-UECAPABILITYENQUIRY-STOP
-- TAG-UECAPABILITYINFORMATION-START
UECapabilityInformation ::= SEQUENCE {
   rrc-TransactionIdentifier [0] RRC-TransactionIdentifier,
   criticalExtensions [1] EXPLICIT CHOICE {
      ueCapabilityInformation [0] UECapabilityInformation-IEs,
      criticalExtensionsFuture [1] SEQUENCE {

      }
   }
}

DRB-CountInfo ::= SEQUENCE {
   drb-Identity [0] DRB-Identity,
   count-Uplink [1] INTEGER (0..4294967295),
   count-Downlink [2] INTEGER (0..4294967295)
}

DRB-CountInfoList ::= SEQUENCE (SIZE (0..maxDRB)) OF DRB-CountInfo

CounterCheckResponse-IEs ::= SEQUENCE {
   drb-CountInfoList [0] DRB-CountInfoList,
   lateNonCriticalExtension [1] OCTET STRING OPTIONAL,
   nonCriticalExtension [2] SEQUENCE {

   } OPTIONAL
}

-- TAG-COUNTERCHECK-STOP
-- TAG-COUNTERCHECKRESPONSE-START
CounterCheckResponse ::= SEQUENCE {
   rrc-TransactionIdentifier [0] RRC-TransactionIdentifier,
   criticalExtensions [1] EXPLICIT CHOICE {
      counterCheckResponse [0] CounterCheckResponse-IEs,
      criticalExtensionsFuture [1] SEQUENCE {

      }
   }
}

DelayBudgetReport ::= CHOICE {
   type1 [0] ENUMERATED { msMinus1280(0), msMinus640(1), msMinus320(2), 
      msMinus160(3), msMinus80(4), msMinus60(5), msMinus40(6), msMinus20(7), 
      ms0(8), ms20(9), ms40(10), ms60(11), ms80(12), ms160(13), ms320(14), 
      ms640(15), ms1280(16) },
   ...
}

OverheatingAssistance ::= SEQUENCE {
   reducedMaxCCs [0] SEQUENCE {
      reducedCCsDL [0] INTEGER (0..31),
      reducedCCsUL [1] INTEGER (0..31)
   } OPTIONAL,
   reducedMaxBW-FR1 [1] SEQUENCE {
      reducedBW-FR1-DL [0] ReducedAggregatedBandwidth,
      reducedBW-FR1-UL [1] ReducedAggregatedBandwidth
   } OPTIONAL,
   reducedMaxBW-FR2 [2] SEQUENCE {
      reducedBW-FR2-DL [0] ReducedAggregatedBandwidth,
      reducedBW-FR2-UL [1] ReducedAggregatedBandwidth
   } OPTIONAL,
   reducedMaxMIMO-LayersFR1 [3] SEQUENCE {
      reducedMIMO-LayersFR1-DL [0] MIMO-LayersDL,
      reducedMIMO-LayersFR1-UL [1] MIMO-LayersUL
   } OPTIONAL,
   reducedMaxMIMO-LayersFR2 [4] SEQUENCE {
      reducedMIMO-LayersFR2-DL [0] MIMO-LayersDL,
      reducedMIMO-LayersFR2-UL [1] MIMO-LayersUL
   } OPTIONAL
}

UEAssistanceInformation-v1540-IEs ::= SEQUENCE {
   overheatingAssistance [0] OverheatingAssistance OPTIONAL,
   nonCriticalExtension [1] SEQUENCE {

   } OPTIONAL
}

UEAssistanceInformation-IEs ::= SEQUENCE {
   delayBudgetReport [0] EXPLICIT DelayBudgetReport OPTIONAL,
   lateNonCriticalExtension [1] OCTET STRING OPTIONAL,
   nonCriticalExtension [2] UEAssistanceInformation-v1540-IEs OPTIONAL
}

-- TAG-SYSTEMINFORMATION-STOP
-- TAG-UEASSISTANCEINFORMATION-START
UEAssistanceInformation ::= SEQUENCE {
   criticalExtensions [0] EXPLICIT CHOICE {
      ueAssistanceInformation [0] UEAssistanceInformation-IEs,
      criticalExtensionsFuture [1] SEQUENCE {

      }
   }
}

FailureInfoRLC-Bearer ::= SEQUENCE {
   cellGroupId [0] CellGroupId,
   logicalChannelIdentity [1] LogicalChannelIdentity,
   failureType [2] ENUMERATED { rlc-failure(0), spare3(1), spare2(2), spare1(3)
       }
}

FailureInformation-IEs ::= SEQUENCE {
   failureInfoRLC-Bearer [0] FailureInfoRLC-Bearer OPTIONAL,
   lateNonCriticalExtension [1] OCTET STRING OPTIONAL,
   nonCriticalExtension [2] SEQUENCE {

   } OPTIONAL
}

-- TAG-DLINFORMATIONTRANSFER-STOP
-- TAG-FAILUREINFORMATION-START
FailureInformation ::= SEQUENCE {
   criticalExtensions [0] EXPLICIT CHOICE {
      failureInformation [0] FailureInformation-IEs,
      criticalExtensionsFuture [1] SEQUENCE {

      }
   }
}

ULInformationTransferMRDC-IEs ::= SEQUENCE {
   ul-DCCH-MessageNR [0] OCTET STRING OPTIONAL,
   ul-DCCH-MessageEUTRA [1] OCTET STRING OPTIONAL,
   lateNonCriticalExtension [2] OCTET STRING OPTIONAL,
   nonCriticalExtension [3] SEQUENCE {

   } OPTIONAL
}

-- TAG-ULINFORMATIONTRANSFER-STOP
-- TAG-ULINFORMATIONTRANSFERMRDC-START
ULInformationTransferMRDC ::= SEQUENCE {
   criticalExtensions [0] EXPLICIT CHOICE {
      c1 [0] EXPLICIT CHOICE {
         ulInformationTransferMRDC [0] ULInformationTransferMRDC-IEs,
         spare3 [1] NULL,
         spare2 [2] NULL,
         spare1 [3] NULL
      },
      criticalExtensionsFuture [1] SEQUENCE {

      }
   }
}

MeasResultFreqList ::= SEQUENCE (SIZE (1..maxFreq)) OF MeasResult2NR

MeasResultList2NR ::= SEQUENCE (SIZE (1..maxFreq)) OF MeasResult2NR

-- TAG-MEASRESULT2NR-STOP
-- TAG-MEASRESULTSCG-FAILURE-START
MeasResultSCG-Failure ::= SEQUENCE {
   measResultPerMOList [0] MeasResultList2NR,
   ...
}

FailureReportSCG ::= SEQUENCE {
   failureType [0] ENUMERATED { t310-Expiry(0), randomAccessProblem(1), 
      rlc-MaxNumRetx(2), synchReconfigFailureSCG(3), scg-ReconfigFailure(4), 
      srb3-IntegrityFailure(5), spare2(6), spare1(7) },
   measResultFreqList [1] MeasResultFreqList OPTIONAL,
   measResultSCG-Failure [2] OCTET STRING (CONTAINING MeasResultSCG-Failure)
       OPTIONAL,
   ...
}

SCGFailureInformation-IEs ::= SEQUENCE {
   failureReportSCG [0] FailureReportSCG OPTIONAL,
   nonCriticalExtension [1] SEQUENCE {

   } OPTIONAL
}

-- TAG-RRCSYSTEMINFOREQUEST-STOP
-- TAG-SCGFAILUREINFORMATION-START
SCGFailureInformation ::= SEQUENCE {
   criticalExtensions [0] EXPLICIT CHOICE {
      scgFailureInformation [0] SCGFailureInformation-IEs,
      criticalExtensionsFuture [1] SEQUENCE {

      }
   }
}

MeasResultFreqListFailMRDC ::= SEQUENCE (SIZE (1..maxFreq)) OF MeasResult2EUTRA

FailureReportSCG-EUTRA ::= SEQUENCE {
   failureType [0] ENUMERATED { t313-Expiry(0), randomAccessProblem(1), 
      rlc-MaxNumRetx(2), scg-ChangeFailure(3), spare4(4), spare3(5), spare2(6)
      , spare1(7) },
   measResultFreqListMRDC [1] MeasResultFreqListFailMRDC OPTIONAL,
   measResultSCG-FailureMRDC [2] OCTET STRING OPTIONAL,
   ...
}

SCGFailureInformationEUTRA-IEs ::= SEQUENCE {
   failureReportSCG-EUTRA [0] FailureReportSCG-EUTRA OPTIONAL,
   nonCriticalExtension [1] SEQUENCE {

   } OPTIONAL
}

-- TAG-SCGFAILUREINFORMATION-STOP
-- TAG-SCGFAILUREINFORMATIONEUTRA-START
SCGFailureInformationEUTRA ::= SEQUENCE {
   criticalExtensions [0] EXPLICIT CHOICE {
      scgFailureInformationEUTRA [0] SCGFailureInformationEUTRA-IEs,
      criticalExtensionsFuture [1] SEQUENCE {

      }
   }
}

UL-DCCH-MessageType ::= CHOICE {
   c1 [0] EXPLICIT CHOICE {
      measurementReport [0] MeasurementReport,
      rrcReconfigurationComplete [1] RRCReconfigurationComplete,
      rrcSetupComplete [2] RRCSetupComplete,
      rrcReestablishmentComplete [3] RRCReestablishmentComplete,
      rrcResumeComplete [4] RRCResumeComplete,
      securityModeComplete [5] SecurityModeComplete,
      securityModeFailure [6] SecurityModeFailure,
      ulInformationTransfer [7] ULInformationTransfer,
      locationMeasurementIndication [8] LocationMeasurementIndication,
      ueCapabilityInformation [9] UECapabilityInformation,
      counterCheckResponse [10] CounterCheckResponse,
      ueAssistanceInformation [11] UEAssistanceInformation,
      failureInformation [12] FailureInformation,
      ulInformationTransferMRDC [13] ULInformationTransferMRDC,
      scgFailureInformation [14] SCGFailureInformation,
      scgFailureInformationEUTRA [15] SCGFailureInformationEUTRA
   },
   messageClassExtension [1] SEQUENCE {

   }
}

-- TAG-UL-CCCH1-MESSAGE-STOP
-- TAG-UL-DCCH-MESSAGE-START
UL-DCCH-Message ::= SEQUENCE {
   message [0] EXPLICIT UL-DCCH-MessageType
}

-- TAG-MEASRESULTCELLLISTSFTD-NR-STOP
-- TAG-MEASRESULTCELLLISTSFTD-EUTRA-START
MeasResultCellListSFTD-EUTRA ::= SEQUENCE (SIZE (1..maxCellSFTD)) OF MeasResultSFTD-EUTRA

BandParameters ::= CHOICE {
   eutra [0] SEQUENCE {
      bandEUTRA [0] FreqBandIndicatorEUTRA,
      ca-BandwidthClassDL-EUTRA [1] CA-BandwidthClassEUTRA OPTIONAL,
      ca-BandwidthClassUL-EUTRA [2] CA-BandwidthClassEUTRA OPTIONAL
   },
   nr [1] SEQUENCE {
      bandNR [0] FreqBandIndicatorNR,
      ca-BandwidthClassDL-NR [1] CA-BandwidthClassNR OPTIONAL,
      ca-BandwidthClassUL-NR [2] CA-BandwidthClassNR OPTIONAL
   }
}

-- TAG-CA-BANDWIDTHCLASSNR-STOP
-- TAG-CA-PARAMETERSEUTRA-START
CA-ParametersEUTRA ::= SEQUENCE {
   multipleTimingAdvance [0] ENUMERATED { supported(0) } OPTIONAL,
   simultaneousRx-Tx [1] ENUMERATED { supported(0) } OPTIONAL,
   supportedNAICS-2CRS-AP [2] BIT STRING  (SIZE (1..8)) OPTIONAL,
   additionalRx-Tx-PerformanceReq [3] ENUMERATED { supported(0) } OPTIONAL,
   ue-CA-PowerClass-N [4] ENUMERATED { class2(0) } OPTIONAL,
   supportedBandwidthCombinationSetEUTRA-v1530 [5] BIT STRING  (SIZE (1..32))
       OPTIONAL,
   ...
}

-- TAG-CA-PARAMETERSEUTRA-STOP
-- TAG-CA-PARAMETERSNR-START
CA-ParametersNR ::= SEQUENCE {
   dummy [0] ENUMERATED { supported(0) } OPTIONAL,
   parallelTxSRS-PUCCH-PUSCH [1] ENUMERATED { supported(0) } OPTIONAL,
   parallelTxPRACH-SRS-PUCCH-PUSCH [2] ENUMERATED { supported(0) } OPTIONAL,
   simultaneousRxTxInterBandCA [3] ENUMERATED { supported(0) } OPTIONAL,
   simultaneousRxTxSUL [4] ENUMERATED { supported(0) } OPTIONAL,
   diffNumerologyAcrossPUCCH-Group [5] ENUMERATED { supported(0) } OPTIONAL,
   diffNumerologyWithinPUCCH-GroupSmallerSCS [6] ENUMERATED { supported(0) }
       OPTIONAL,
   supportedNumberTAG [7] ENUMERATED { n2(0), n3(1), n4(2) } OPTIONAL,
   ...
}

-- TAG-MODULATIONORDER-STOP
-- TAG-MRDC-PARAMETERS-START
MRDC-Parameters ::= SEQUENCE {
   singleUL-Transmission [0] ENUMERATED { supported(0) } OPTIONAL,
   dynamicPowerSharingENDC [1] ENUMERATED { supported(0) } OPTIONAL,
   tdm-Pattern [2] ENUMERATED { supported(0) } OPTIONAL,
   ul-SharingEUTRA-NR [3] ENUMERATED { tdm(0), fdm(1), both(2) } OPTIONAL,
   ul-SwitchingTimeEUTRA-NR [4] ENUMERATED { type1(0), type2(1) } OPTIONAL,
   simultaneousRxTxInterBandENDC [5] ENUMERATED { supported(0) } OPTIONAL,
   asyncIntraBandENDC [6] ENUMERATED { supported(0) } OPTIONAL,
   ...,
   [[
      dualPA-Architecture [7] ENUMERATED { supported(0) } OPTIONAL,
      intraBandENDC-Support [8] ENUMERATED { non-contiguous(0), both(1) }
          OPTIONAL,
      ul-TimingAlignmentEUTRA-NR [9] ENUMERATED { required(0) } OPTIONAL
   ]]
}

BandCombination ::= SEQUENCE {
   bandList [0] SEQUENCE (SIZE (1..maxSimultaneousBands)) OF BandParameters,
   featureSetCombination [1] FeatureSetCombinationId,
   ca-ParametersEUTRA [2] CA-ParametersEUTRA OPTIONAL,
   ca-ParametersNR [3] CA-ParametersNR OPTIONAL,
   mrdc-Parameters [4] MRDC-Parameters OPTIONAL,
   supportedBandwidthCombinationSet [5] BIT STRING  (SIZE (1..32)) OPTIONAL,
   powerClass-v1530 [6] ENUMERATED { pc2(0) } OPTIONAL
}

-- TAG-ACCESSSTRATUMRELEASE-STOP
-- TAG-BANDCOMBINATIONLIST-START
BandCombinationList ::= SEQUENCE (SIZE (1..maxBandComb)) OF BandCombination

-- TAG-SDAP-PARAMETERS-STOP
-- TAG-SRS-SWITCHINGTIMENR-START
SRS-SwitchingTimeNR ::= SEQUENCE {
   switchingTimeDL [0] ENUMERATED { n0us(0), n30us(1), n100us(2), n140us(3), 
      n200us(4), n300us(5), n500us(6), n900us(7) } OPTIONAL,
   switchingTimeUL [1] ENUMERATED { n0us(0), n30us(1), n100us(2), n140us(3), 
      n200us(4), n300us(5), n500us(6), n900us(7) } OPTIONAL
}

-- TAG-SRS-SWITCHINGTIMENR-STOP
-- TAG-SRS-SWITCHINGTIMEEUTRA-START
SRS-SwitchingTimeEUTRA ::= SEQUENCE {
   switchingTimeDL [0] ENUMERATED { n0(0), n0dot5(1), n1(2), n1dot5(3), n2(4), 
      n2dot5(5), n3(6), n3dot5(7), n4(8), n4dot5(9), n5(10), n5dot5(11), n6(12)
      , n6dot5(13), n7(14) } OPTIONAL,
   switchingTimeUL [1] ENUMERATED { n0(0), n0dot5(1), n1(2), n1dot5(3), n2(4), 
      n2dot5(5), n3(6), n3dot5(7), n4(8), n4dot5(9), n5(10), n5dot5(11), n6(12)
      , n6dot5(13), n7(14) } OPTIONAL
}

BandParameters-v1540 ::= SEQUENCE {
   srs-CarrierSwitch [0] EXPLICIT CHOICE {
      nr [0] SEQUENCE {
         srs-SwitchingTimesListNR [0] SEQUENCE (SIZE (1..maxSimultaneousBands)) OF 
            SRS-SwitchingTimeNR
      },
      eutra [1] SEQUENCE {
         srs-SwitchingTimesListEUTRA [0] SEQUENCE (SIZE (1..maxSimultaneousBands)) OF 
            SRS-SwitchingTimeEUTRA
      }
   } OPTIONAL,
   srs-TxSwitch [1] SEQUENCE {
      supportedSRS-TxPortSwitch [0] ENUMERATED { t1r2(0), t1r4(1), t2r4(2), 
         t1r4-t2r4(3), t1r1(4), t2r2(5), t4r4(6), notSupported(7) },
      txSwitchImpactToRx [1] INTEGER (1..32) OPTIONAL,
      txSwitchWithAnotherBand [2] INTEGER (1..32) OPTIONAL
   } OPTIONAL
}

CA-ParametersNR-v1540 ::= SEQUENCE {
   simultaneousSRS-AssocCSI-RS-AllCC [0] INTEGER (5..32) OPTIONAL,
   csi-RS-IM-ReceptionForFeedbackPerBandComb [1] SEQUENCE {
      maxNumberSimultaneousNZP-CSI-RS-ActBWP-AllCC [0] INTEGER (1..64) OPTIONAL,
      totalNumberPortsSimultaneousNZP-CSI-RS-ActBWP-AllCC [1] INTEGER (2..256)
          OPTIONAL
   } OPTIONAL,
   simultaneousCSI-ReportsAllCC [2] INTEGER (5..32) OPTIONAL,
   dualPA-Architecture [3] ENUMERATED { supported(0) } OPTIONAL
}

BandCombination-v1540 ::= SEQUENCE {
   bandList-v1540 [0] SEQUENCE (SIZE (1..maxSimultaneousBands)) OF BandParameters-v1540,
   ca-ParametersNR-v1540 [1] CA-ParametersNR-v1540 OPTIONAL
}

BandCombinationList-v1540 ::= SEQUENCE (SIZE (1..maxBandComb)) OF BandCombination-v1540

CA-ParametersNR-v1550 ::= SEQUENCE {
   dummy [0] ENUMERATED { supported(0) } OPTIONAL
}

BandCombination-v1550 ::= SEQUENCE {
   ca-ParametersNR-v1550 [0] CA-ParametersNR-v1550
}

BandCombinationList-v1550 ::= SEQUENCE (SIZE (1..maxBandComb)) OF BandCombination-v1550

CA-ParametersNR-v1560 ::= SEQUENCE {
   diffNumerologyWithinPUCCH-GroupLargerSCS [0] ENUMERATED { supported(0) }
       OPTIONAL
}

-- TAG-CA-PARAMETERSNR-STOP
-- TAG-CA-PARAMETERS-NRDC-START
CA-ParametersNRDC ::= SEQUENCE {
   ca-ParametersNR-ForDC [0] CA-ParametersNR OPTIONAL,
   ca-ParametersNR-ForDC-v1540 [1] CA-ParametersNR-v1540 OPTIONAL,
   ca-ParametersNR-ForDC-v1550 [2] CA-ParametersNR-v1550 OPTIONAL,
   ca-ParametersNR-ForDC-v1560 [3] CA-ParametersNR-v1560 OPTIONAL,
   featureSetCombinationDC [4] FeatureSetCombinationId OPTIONAL
}

CA-ParametersEUTRA-v1560 ::= SEQUENCE {
   fd-MIMO-TotalWeightedLayers [0] INTEGER (2..128) OPTIONAL
}

BandCombination-v1560 ::= SEQUENCE {
   ne-DC-BC [0] ENUMERATED { supported(0) } OPTIONAL,
   ca-ParametersNRDC [1] CA-ParametersNRDC OPTIONAL,
   ca-ParametersEUTRA-v1560 [2] CA-ParametersEUTRA-v1560 OPTIONAL,
   ca-ParametersNR-v1560 [3] CA-ParametersNR-v1560 OPTIONAL
}

BandCombinationList-v1560 ::= SEQUENCE (SIZE (1..maxBandComb)) OF BandCombination-v1560

CA-ParametersEUTRA-v1570 ::= SEQUENCE {
   dl-1024QAM-TotalWeightedLayers [0] INTEGER (0..10) OPTIONAL
}

BandCombination-v1570 ::= SEQUENCE {
   ca-ParametersEUTRA-v1570 [0] CA-ParametersEUTRA-v1570
}

BandCombinationList-v1570 ::= SEQUENCE (SIZE (1..maxBandComb)) OF BandCombination-v1570

MRDC-Parameters-v1580 ::= SEQUENCE {
   dynamicPowerSharingNEDC [0] ENUMERATED { supported(0) } OPTIONAL
}

BandCombination-v1580 ::= SEQUENCE {
   mrdc-Parameters-v1580 [0] MRDC-Parameters-v1580
}

BandCombinationList-v1580 ::= SEQUENCE (SIZE (1..maxBandComb)) OF BandCombination-v1580

SupportedCSI-RS-Resource ::= SEQUENCE {
   maxNumberTxPortsPerResource [0] ENUMERATED { p2(0), p4(1), p8(2), p12(3), 
      p16(4), p24(5), p32(6) },
   maxNumberResourcesPerBand [1] INTEGER (1..64),
   totalNumberTxPortsPerBand [2] INTEGER (2..256)
}

-- TAG-CA-PARAMETERS-NRDC-STOP
-- TAG-CODEBOOKPARAMETERS-START
CodebookParameters ::= SEQUENCE {
   type1 [0] SEQUENCE {
      singlePanel [0] SEQUENCE {
         supportedCSI-RS-ResourceList [0] SEQUENCE (SIZE (1..maxNrofCSI-RS-Resources)) OF 
            SupportedCSI-RS-Resource,
         modes [1] ENUMERATED { mode1(0), mode1andMode2(1) },
         maxNumberCSI-RS-PerResourceSet [2] INTEGER (1..8)
      },
      multiPanel [1] SEQUENCE {
         supportedCSI-RS-ResourceList [0] SEQUENCE (SIZE (1..maxNrofCSI-RS-Resources)) OF 
            SupportedCSI-RS-Resource,
         modes [1] ENUMERATED { mode1(0), mode2(1), both(2) },
         nrofPanels [2] ENUMERATED { n2(0), n4(1) },
         maxNumberCSI-RS-PerResourceSet [3] INTEGER (1..8)
      } OPTIONAL
   },
   type2 [1] SEQUENCE {
      supportedCSI-RS-ResourceList [0] SEQUENCE (SIZE (1..maxNrofCSI-RS-Resources)) OF 
         SupportedCSI-RS-Resource,
      parameterLx [1] INTEGER (2..4),
      amplitudeScalingType [2] ENUMERATED { wideband(0), widebandAndSubband(1)
          },
      amplitudeSubsetRestriction [3] ENUMERATED { supported(0) } OPTIONAL
   } OPTIONAL,
   type2-PortSelection [2] SEQUENCE {
      supportedCSI-RS-ResourceList [0] SEQUENCE (SIZE (1..maxNrofCSI-RS-Resources)) OF 
         SupportedCSI-RS-Resource,
      parameterLx [1] INTEGER (2..4),
      amplitudeScalingType [2] ENUMERATED { wideband(0), widebandAndSubband(1)
          }
   } OPTIONAL
}

FeatureSet ::= CHOICE {
   eutra [0] SEQUENCE {
      downlinkSetEUTRA [0] FeatureSetEUTRA-DownlinkId,
      uplinkSetEUTRA [1] FeatureSetEUTRA-UplinkId
   },
   nr [1] SEQUENCE {
      downlinkSetNR [0] FeatureSetDownlinkId,
      uplinkSetNR [1] FeatureSetUplinkId
   }
}

FeatureSetsPerBand ::= SEQUENCE (SIZE (1..maxFeatureSetsPerBand)) OF FeatureSet

-- TAG-CODEBOOKPARAMETERS-STOP
-- TAG-FEATURESETCOMBINATION-START
FeatureSetCombination ::= SEQUENCE (SIZE (1..maxSimultaneousBands)) OF FeatureSetsPerBand

DummyA ::= SEQUENCE {
   maxNumberNZP-CSI-RS-PerCC [0] INTEGER (1..32),
   maxNumberPortsAcrossNZP-CSI-RS-PerCC [1] ENUMERATED { p2(0), p4(1), p8(2), 
      p12(3), p16(4), p24(5), p32(6), p40(7), p48(8), p56(9), p64(10), p72(11)
      , p80(12), p88(13), p96(14), p104(15), p112(16), p120(17), p128(18), 
      p136(19), p144(20), p152(21), p160(22), p168(23), p176(24), p184(25), 
      p192(26), p200(27), p208(28), p216(29), p224(30), p232(31), p240(32), 
      p248(33), p256(34) },
   maxNumberCS-IM-PerCC [2] ENUMERATED { n1(0), n2(1), n4(2), n8(3), n16(4), 
      n32(5) },
   maxNumberSimultaneousCSI-RS-ActBWP-AllCC [3] ENUMERATED { n5(0), n6(1), 
      n7(2), n8(3), n9(4), n10(5), n12(6), n14(7), n16(8), n18(9), n20(10), 
      n22(11), n24(12), n26(13), n28(14), n30(15), n32(16), n34(17), n36(18), 
      n38(19), n40(20), n42(21), n44(22), n46(23), n48(24), n50(25), n52(26), 
      n54(27), n56(28), n58(29), n60(30), n62(31), n64(32) },
   totalNumberPortsSimultaneousCSI-RS-ActBWP-AllCC [4] ENUMERATED { p8(0), 
      p12(1), p16(2), p24(3), p32(4), p40(5), p48(6), p56(7), p64(8), p72(9), 
      p80(10), p88(11), p96(12), p104(13), p112(14), p120(15), p128(16), 
      p136(17), p144(18), p152(19), p160(20), p168(21), p176(22), p184(23), 
      p192(24), p200(25), p208(26), p216(27), p224(28), p232(29), p240(30), 
      p248(31), p256(32) }
}

DummyB ::= SEQUENCE {
   maxNumberTxPortsPerResource [0] ENUMERATED { p2(0), p4(1), p8(2), p12(3), 
      p16(4), p24(5), p32(6) },
   maxNumberResources [1] INTEGER (1..64),
   totalNumberTxPorts [2] INTEGER (2..256),
   supportedCodebookMode [3] ENUMERATED { mode1(0), mode1AndMode2(1) },
   maxNumberCSI-RS-PerResourceSet [4] INTEGER (1..8)
}

DummyC ::= SEQUENCE {
   maxNumberTxPortsPerResource [0] ENUMERATED { p8(0), p16(1), p32(2) },
   maxNumberResources [1] INTEGER (1..64),
   totalNumberTxPorts [2] INTEGER (2..256),
   supportedCodebookMode [3] ENUMERATED { mode1(0), mode2(1), both(2) },
   supportedNumberPanels [4] ENUMERATED { n2(0), n4(1) },
   maxNumberCSI-RS-PerResourceSet [5] INTEGER (1..8)
}

DummyD ::= SEQUENCE {
   maxNumberTxPortsPerResource [0] ENUMERATED { p4(0), p8(1), p12(2), p16(3), 
      p24(4), p32(5) },
   maxNumberResources [1] INTEGER (1..64),
   totalNumberTxPorts [2] INTEGER (2..256),
   parameterLx [3] INTEGER (2..4),
   amplitudeScalingType [4] ENUMERATED { wideband(0), widebandAndSubband(1) },
   amplitudeSubsetRestriction [5] ENUMERATED { supported(0) } OPTIONAL,
   maxNumberCSI-RS-PerResourceSet [6] INTEGER (1..8)
}

DummyE ::= SEQUENCE {
   maxNumberTxPortsPerResource [0] ENUMERATED { p4(0), p8(1), p12(2), p16(3), 
      p24(4), p32(5) },
   maxNumberResources [1] INTEGER (1..64),
   totalNumberTxPorts [2] INTEGER (2..256),
   parameterLx [3] INTEGER (2..4),
   amplitudeScalingType [4] ENUMERATED { wideband(0), widebandAndSubband(1) },
   maxNumberCSI-RS-PerResourceSet [5] INTEGER (1..8)
}

-- TAG-FEATURESETCOMBINATIONID-STOP
-- TAG-FEATURESETDOWNLINK-START
FeatureSetDownlink ::= SEQUENCE {
   featureSetListPerDownlinkCC [0] SEQUENCE (SIZE (1..maxNrofServingCells)) OF 
      FeatureSetDownlinkPerCC-Id,
   intraBandFreqSeparationDL [1] FreqSeparationClass OPTIONAL,
   scalingFactor [2] ENUMERATED { f0p4(0), f0p75(1), f0p8(2) } OPTIONAL,
   crossCarrierScheduling-OtherSCS [3] ENUMERATED { supported(0) } OPTIONAL,
   scellWithoutSSB [4] ENUMERATED { supported(0) } OPTIONAL,
   csi-RS-MeasSCellWithoutSSB [5] ENUMERATED { supported(0) } OPTIONAL,
   dummy1 [6] ENUMERATED { supported(0) } OPTIONAL,
   type1-3-CSS [7] ENUMERATED { supported(0) } OPTIONAL,
   pdcch-MonitoringAnyOccasions [8] ENUMERATED { withoutDCI-Gap(0), 
      withDCI-Gap(1) } OPTIONAL,
   dummy2 [9] ENUMERATED { supported(0) } OPTIONAL,
   ue-SpecificUL-DL-Assignment [10] ENUMERATED { supported(0) } OPTIONAL,
   searchSpaceSharingCA-DL [11] ENUMERATED { supported(0) } OPTIONAL,
   timeDurationForQCL [12] SEQUENCE {
      scs-60kHz [0] ENUMERATED { s7(0), s14(1), s28(2) } OPTIONAL,
      scs-120kHz [1] ENUMERATED { s14(0), s28(1) } OPTIONAL
   } OPTIONAL,
   pdsch-ProcessingType1-DifferentTB-PerSlot [13] SEQUENCE {
      scs-15kHz [0] ENUMERATED { upto2(0), upto4(1), upto7(2) } OPTIONAL,
      scs-30kHz [1] ENUMERATED { upto2(0), upto4(1), upto7(2) } OPTIONAL,
      scs-60kHz [2] ENUMERATED { upto2(0), upto4(1), upto7(2) } OPTIONAL,
      scs-120kHz [3] ENUMERATED { upto2(0), upto4(1), upto7(2) } OPTIONAL
   } OPTIONAL,
   dummy3 [14] DummyA OPTIONAL,
   dummy4 [15] SEQUENCE (SIZE (1..maxNrofCodebooks)) OF DummyB OPTIONAL,
   dummy5 [16] SEQUENCE (SIZE (1..maxNrofCodebooks)) OF DummyC OPTIONAL,
   dummy6 [17] SEQUENCE (SIZE (1..maxNrofCodebooks)) OF DummyD OPTIONAL,
   dummy7 [18] SEQUENCE (SIZE (1..maxNrofCodebooks)) OF DummyE OPTIONAL
}

-- TAG-PHY-PARAMETERSMRDC-STOP
-- TAG-PROCESSINGPARAMETERS-START
ProcessingParameters ::= SEQUENCE {
   fallback [0] ENUMERATED { sc(0), cap1-only(1) },
   differentTB-PerSlot [1] SEQUENCE {
      upto1 [0] NumberOfCarriers OPTIONAL,
      upto2 [1] NumberOfCarriers OPTIONAL,
      upto4 [2] NumberOfCarriers OPTIONAL,
      upto7 [3] NumberOfCarriers OPTIONAL
   } OPTIONAL
}

FeatureSetDownlink-v1540 ::= SEQUENCE {
   oneFL-DMRS-TwoAdditionalDMRS-DL [0] ENUMERATED { supported(0) } OPTIONAL,
   additionalDMRS-DL-Alt [1] ENUMERATED { supported(0) } OPTIONAL,
   twoFL-DMRS-TwoAdditionalDMRS-DL [2] ENUMERATED { supported(0) } OPTIONAL,
   oneFL-DMRS-ThreeAdditionalDMRS-DL [3] ENUMERATED { supported(0) } OPTIONAL,
   pdcch-MonitoringAnyOccasionsWithSpanGap [4] SEQUENCE {
      scs-15kHz [0] ENUMERATED { set1(0), set2(1), set3(2) } OPTIONAL,
      scs-30kHz [1] ENUMERATED { set1(0), set2(1), set3(2) } OPTIONAL,
      scs-60kHz [2] ENUMERATED { set1(0), set2(1), set3(2) } OPTIONAL,
      scs-120kHz [3] ENUMERATED { set1(0), set2(1), set3(2) } OPTIONAL
   } OPTIONAL,
   pdsch-SeparationWithGap [5] ENUMERATED { supported(0) } OPTIONAL,
   pdsch-ProcessingType2 [6] SEQUENCE {
      scs-15kHz [0] ProcessingParameters OPTIONAL,
      scs-30kHz [1] ProcessingParameters OPTIONAL,
      scs-60kHz [2] ProcessingParameters OPTIONAL
   } OPTIONAL,
   pdsch-ProcessingType2-Limited [7] SEQUENCE {
      differentTB-PerSlot-SCS-30kHz [0] ENUMERATED { upto1(0), upto2(1), 
         upto4(2), upto7(3) }
   } OPTIONAL,
   dl-MCS-TableAlt-DynamicIndication [8] ENUMERATED { supported(0) } OPTIONAL
}

-- TAG-SRS-SWITCHINGTIMEEUTRA-STOP
-- TAG-SUPPORTEDBANDWIDTH-START
SupportedBandwidth ::= CHOICE {
   fr1 [0] ENUMERATED { mhz5(0), mhz10(1), mhz15(2), mhz20(3), mhz25(4), 
      mhz30(5), mhz40(6), mhz50(7), mhz60(8), mhz80(9), mhz100(10) },
   fr2 [1] ENUMERATED { mhz50(0), mhz100(1), mhz200(2), mhz400(3) }
}

-- TAG-FEATURESETDOWNLINKID-STOP
-- TAG-FEATURESETDOWNLINKPERCC-START
FeatureSetDownlinkPerCC ::= SEQUENCE {
   supportedSubcarrierSpacingDL [0] SubcarrierSpacing,
   supportedBandwidthDL [1] EXPLICIT SupportedBandwidth,
   channelBW-90mhz [2] ENUMERATED { supported(0) } OPTIONAL,
   maxNumberMIMO-LayersPDSCH [3] MIMO-LayersDL OPTIONAL,
   supportedModulationOrderDL [4] ModulationOrder OPTIONAL
}

DummyI ::= SEQUENCE {
   supportedSRS-TxPortSwitch [0] ENUMERATED { t1r2(0), t1r4(1), t2r4(2), 
      t1r4-t2r4(3), tr-equal(4) },
   txSwitchImpactToRx [1] ENUMERATED { true(0) } OPTIONAL
}

SRS-Resources ::= SEQUENCE {
   maxNumberAperiodicSRS-PerBWP [0] ENUMERATED { n1(0), n2(1), n4(2), n8(3), 
      n16(4) },
   maxNumberAperiodicSRS-PerBWP-PerSlot [1] INTEGER (1..6),
   maxNumberPeriodicSRS-PerBWP [2] ENUMERATED { n1(0), n2(1), n4(2), n8(3), 
      n16(4) },
   maxNumberPeriodicSRS-PerBWP-PerSlot [3] INTEGER (1..6),
   maxNumberSemiPersistentSRS-PerBWP [4] ENUMERATED { n1(0), n2(1), n4(2), 
      n8(3), n16(4) },
   maxNumberSemiPersistentSRS-PerBWP-PerSlot [5] INTEGER (1..6),
   maxNumberSRS-Ports-PerResource [6] ENUMERATED { n1(0), n2(1), n4(2) }
}

DummyF ::= SEQUENCE {
   maxNumberPeriodicCSI-ReportPerBWP [0] INTEGER (1..4),
   maxNumberAperiodicCSI-ReportPerBWP [1] INTEGER (1..4),
   maxNumberSemiPersistentCSI-ReportPerBWP [2] INTEGER (0..4),
   simultaneousCSI-ReportsAllCC [3] INTEGER (5..32)
}

-- TAG-FEATURESETS-STOP
-- TAG-FEATURESETUPLINK-START
FeatureSetUplink ::= SEQUENCE {
   featureSetListPerUplinkCC [0] SEQUENCE (SIZE (1..maxNrofServingCells)) OF 
      FeatureSetUplinkPerCC-Id,
   scalingFactor [1] ENUMERATED { f0p4(0), f0p75(1), f0p8(2) } OPTIONAL,
   crossCarrierScheduling-OtherSCS [2] ENUMERATED { supported(0) } OPTIONAL,
   intraBandFreqSeparationUL [3] FreqSeparationClass OPTIONAL,
   searchSpaceSharingCA-UL [4] ENUMERATED { supported(0) } OPTIONAL,
   dummy1 [5] DummyI OPTIONAL,
   supportedSRS-Resources [6] SRS-Resources OPTIONAL,
   twoPUCCH-Group [7] ENUMERATED { supported(0) } OPTIONAL,
   dynamicSwitchSUL [8] ENUMERATED { supported(0) } OPTIONAL,
   simultaneousTxSUL-NonSUL [9] ENUMERATED { supported(0) } OPTIONAL,
   pusch-ProcessingType1-DifferentTB-PerSlot [10] SEQUENCE {
      scs-15kHz [0] ENUMERATED { upto2(0), upto4(1), upto7(2) } OPTIONAL,
      scs-30kHz [1] ENUMERATED { upto2(0), upto4(1), upto7(2) } OPTIONAL,
      scs-60kHz [2] ENUMERATED { upto2(0), upto4(1), upto7(2) } OPTIONAL,
      scs-120kHz [3] ENUMERATED { upto2(0), upto4(1), upto7(2) } OPTIONAL
   } OPTIONAL,
   dummy2 [11] DummyF OPTIONAL
}

-- TAG-FEATURESETUPLINKID-STOP
-- TAG-FEATURESETUPLINKPERCC-START
FeatureSetUplinkPerCC ::= SEQUENCE {
   supportedSubcarrierSpacingUL [0] SubcarrierSpacing,
   supportedBandwidthUL [1] EXPLICIT SupportedBandwidth,
   channelBW-90mhz [2] ENUMERATED { supported(0) } OPTIONAL,
   mimo-CB-PUSCH [3] SEQUENCE {
      maxNumberMIMO-LayersCB-PUSCH [0] MIMO-LayersUL OPTIONAL,
      maxNumberSRS-ResourcePerSet [1] INTEGER (1..2)
   } OPTIONAL,
   maxNumberMIMO-LayersNonCB-PUSCH [4] MIMO-LayersUL OPTIONAL,
   supportedModulationOrderUL [5] ModulationOrder OPTIONAL
}

FeatureSetUplink-v1540 ::= SEQUENCE {
   zeroSlotOffsetAperiodicSRS [0] ENUMERATED { supported(0) } OPTIONAL,
   pa-PhaseDiscontinuityImpacts [1] ENUMERATED { supported(0) } OPTIONAL,
   pusch-SeparationWithGap [2] ENUMERATED { supported(0) } OPTIONAL,
   pusch-ProcessingType2 [3] SEQUENCE {
      scs-15kHz [0] ProcessingParameters OPTIONAL,
      scs-30kHz [1] ProcessingParameters OPTIONAL,
      scs-60kHz [2] ProcessingParameters OPTIONAL
   } OPTIONAL,
   ul-MCS-TableAlt-DynamicIndication [4] ENUMERATED { supported(0) } OPTIONAL
}

FeatureSetUplinkPerCC-v1540 ::= SEQUENCE {
   mimo-NonCB-PUSCH [0] SEQUENCE {
      maxNumberSRS-ResourcePerSet [0] INTEGER (1..4),
      maxNumberSimultaneousSRS-ResourceTx [1] INTEGER (1..4)
   } OPTIONAL
}

-- TAG-FEATURESETEUTRAUPLINKID-STOP
-- TAG-FEATURESETS-START
FeatureSets ::= SEQUENCE {
   featureSetsDownlink [0] SEQUENCE (SIZE (1..maxDownlinkFeatureSets)) OF FeatureSetDownlink OPTIONAL,
   featureSetsDownlinkPerCC [1] SEQUENCE (SIZE (1..maxPerCC-FeatureSets)) OF FeatureSetDownlinkPerCC
       OPTIONAL,
   featureSetsUplink [2] SEQUENCE (SIZE (1..maxUplinkFeatureSets)) OF FeatureSetUplink OPTIONAL,
   featureSetsUplinkPerCC [3] SEQUENCE (SIZE (1..maxPerCC-FeatureSets)) OF FeatureSetUplinkPerCC
       OPTIONAL,
   ...,
   [[
      featureSetsDownlink-v1540 [4] SEQUENCE (SIZE (1..maxDownlinkFeatureSets)) OF 
         FeatureSetDownlink-v1540 OPTIONAL,
      featureSetsUplink-v1540 [5] SEQUENCE (SIZE (1..maxUplinkFeatureSets)) OF 
         FeatureSetUplink-v1540 OPTIONAL,
      featureSetsUplinkPerCC-v1540 [6] SEQUENCE (SIZE (1..maxPerCC-FeatureSets)) OF 
         FeatureSetUplinkPerCC-v1540 OPTIONAL
   ]]
}

FreqBandInformationEUTRA ::= SEQUENCE {
   bandEUTRA [0] FreqBandIndicatorEUTRA,
   ca-BandwidthClassDL-EUTRA [1] CA-BandwidthClassEUTRA OPTIONAL, -- Need N
   ca-BandwidthClassUL-EUTRA [2] CA-BandwidthClassEUTRA OPTIONAL -- Need N
}

FreqBandInformationNR ::= SEQUENCE {
   bandNR [0] FreqBandIndicatorNR,
   maxBandwidthRequestedDL [1] AggregatedBandwidth OPTIONAL, -- Need N
   maxBandwidthRequestedUL [2] AggregatedBandwidth OPTIONAL, -- Need N
   maxCarriersRequestedDL [3] INTEGER (1..maxNrofServingCells) OPTIONAL, -- Need N
   maxCarriersRequestedUL [4] INTEGER (1..maxNrofServingCells) OPTIONAL -- Need N
}

FreqBandInformation ::= CHOICE {
   bandInformationEUTRA [0] FreqBandInformationEUTRA,
   bandInformationNR [1] FreqBandInformationNR
}

-- TAG-FREQBANDINDICATOREUTRA-STOP
-- TAG-FREQBANDLIST-START
FreqBandList ::= SEQUENCE (SIZE (1..maxBandsMRDC)) OF FreqBandInformation

IMS-ParametersCommon ::= SEQUENCE {
   voiceOverEUTRA-5GC [0] ENUMERATED { supported(0) } OPTIONAL,
   ...,
   [[
      voiceOverSCG-BearerEUTRA-5GC [1] ENUMERATED { supported(0) } OPTIONAL
   ]]
}

IMS-ParametersFRX-Diff ::= SEQUENCE {
   voiceOverNR [0] ENUMERATED { supported(0) } OPTIONAL,
   ...
}

-- TAG-FREQSEPARATIONCLASS-STOP
-- TAG-IMS-PARAMETERS-START
IMS-Parameters ::= SEQUENCE {
   ims-ParametersCommon [0] IMS-ParametersCommon OPTIONAL,
   ims-ParametersFRX-Diff [1] IMS-ParametersFRX-Diff OPTIONAL,
   ...
}

EUTRA-ParametersCommon ::= SEQUENCE {
   mfbi-EUTRA [0] ENUMERATED { supported(0) } OPTIONAL,
   modifiedMPR-BehaviorEUTRA [1] BIT STRING  (SIZE (32)) OPTIONAL,
   multiNS-Pmax-EUTRA [2] ENUMERATED { supported(0) } OPTIONAL,
   rs-SINR-MeasEUTRA [3] ENUMERATED { supported(0) } OPTIONAL,
   ...,
   [[
      ne-DC [4] ENUMERATED { supported(0) } OPTIONAL
   ]]
}

EUTRA-ParametersXDD-Diff ::= SEQUENCE {
   rsrqMeasWidebandEUTRA [0] ENUMERATED { supported(0) } OPTIONAL,
   ...
}

EUTRA-Parameters ::= SEQUENCE {
   supportedBandListEUTRA [0] SEQUENCE (SIZE (1..maxBandsEUTRA)) OF FreqBandIndicatorEUTRA,
   eutra-ParametersCommon [1] EUTRA-ParametersCommon OPTIONAL,
   eutra-ParametersXDD-Diff [2] EUTRA-ParametersXDD-Diff OPTIONAL,
   ...
}

-- TAG-IMS-PARAMETERS-STOP
-- TAG-INTERRAT-PARAMETERS-START
InterRAT-Parameters ::= SEQUENCE {
   eutra [0] EUTRA-Parameters OPTIONAL,
   ...
}

MAC-ParametersCommon ::= SEQUENCE {
   lcp-Restriction [0] ENUMERATED { supported(0) } OPTIONAL,
   dummy [1] ENUMERATED { supported(0) } OPTIONAL,
   lch-ToSCellRestriction [2] ENUMERATED { supported(0) } OPTIONAL,
   ...,
   [[
      recommendedBitRate [3] ENUMERATED { supported(0) } OPTIONAL,
      recommendedBitRateQuery [4] ENUMERATED { supported(0) } OPTIONAL
   ]]
}

MAC-ParametersXDD-Diff ::= SEQUENCE {
   skipUplinkTxDynamic [0] ENUMERATED { supported(0) } OPTIONAL,
   logicalChannelSR-DelayTimer [1] ENUMERATED { supported(0) } OPTIONAL,
   longDRX-Cycle [2] ENUMERATED { supported(0) } OPTIONAL,
   shortDRX-Cycle [3] ENUMERATED { supported(0) } OPTIONAL,
   multipleSR-Configurations [4] ENUMERATED { supported(0) } OPTIONAL,
   multipleConfiguredGrants [5] ENUMERATED { supported(0) } OPTIONAL,
   ...
}

-- TAG-INTERRAT-PARAMETERS-STOP
-- TAG-MAC-PARAMETERS-START
MAC-Parameters ::= SEQUENCE {
   mac-ParametersCommon [0] MAC-ParametersCommon OPTIONAL,
   mac-ParametersXDD-Diff [1] MAC-ParametersXDD-Diff OPTIONAL
}

MeasAndMobParametersCommon ::= SEQUENCE {
   supportedGapPattern [0] BIT STRING  (SIZE (22)) OPTIONAL,
   ssb-RLM [1] ENUMERATED { supported(0) } OPTIONAL,
   ssb-AndCSI-RS-RLM [2] ENUMERATED { supported(0) } OPTIONAL,
   ...,
   [[
      eventB-MeasAndReport [3] ENUMERATED { supported(0) } OPTIONAL,
      handoverFDD-TDD [4] ENUMERATED { supported(0) } OPTIONAL,
      eutra-CGI-Reporting [5] ENUMERATED { supported(0) } OPTIONAL,
      nr-CGI-Reporting [6] ENUMERATED { supported(0) } OPTIONAL
   ]],
   [[
      independentGapConfig [7] ENUMERATED { supported(0) } OPTIONAL,
      periodicEUTRA-MeasAndReport [8] ENUMERATED { supported(0) } OPTIONAL,
      handoverFR1-FR2 [9] ENUMERATED { supported(0) } OPTIONAL,
      maxNumberCSI-RS-RRM-RS-SINR [10] ENUMERATED { n4(0), n8(1), n16(2), 
         n32(3), n64(4), n96(5) } OPTIONAL
   ]],
   [[
      nr-CGI-Reporting-ENDC [11] ENUMERATED { supported(0) } OPTIONAL
   ]]
}

MeasAndMobParametersXDD-Diff ::= SEQUENCE {
   intraAndInterF-MeasAndReport [0] ENUMERATED { supported(0) } OPTIONAL,
   eventA-MeasAndReport [1] ENUMERATED { supported(0) } OPTIONAL,
   ...,
   [[
      handoverInterF [2] ENUMERATED { supported(0) } OPTIONAL,
      handoverLTE-EPC [3] ENUMERATED { supported(0) } OPTIONAL,
      handoverLTE-5GC [4] ENUMERATED { supported(0) } OPTIONAL
   ]],
   [[
      sftd-MeasNR-Neigh [5] ENUMERATED { supported(0) } OPTIONAL,
      sftd-MeasNR-Neigh-DRX [6] ENUMERATED { supported(0) } OPTIONAL
   ]]
}

MeasAndMobParametersFRX-Diff ::= SEQUENCE {
   ss-SINR-Meas [0] ENUMERATED { supported(0) } OPTIONAL,
   csi-RSRP-AndRSRQ-MeasWithSSB [1] ENUMERATED { supported(0) } OPTIONAL,
   csi-RSRP-AndRSRQ-MeasWithoutSSB [2] ENUMERATED { supported(0) } OPTIONAL,
   csi-SINR-Meas [3] ENUMERATED { supported(0) } OPTIONAL,
   csi-RS-RLM [4] ENUMERATED { supported(0) } OPTIONAL,
   ...,
   [[
      handoverInterF [5] ENUMERATED { supported(0) } OPTIONAL,
      handoverLTE-EPC [6] ENUMERATED { supported(0) } OPTIONAL,
      handoverLTE-5GC [7] ENUMERATED { supported(0) } OPTIONAL
   ]],
   [[
      maxNumberResource-CSI-RS-RLM [8] ENUMERATED { n2(0), n4(1), n6(2), n8(3)
          } OPTIONAL
   ]],
   [[
      simultaneousRxDataSSB-DiffNumerology [9] ENUMERATED { supported(0) }
          OPTIONAL
   ]]
}

-- TAG-MAC-PARAMETERS-STOP
-- TAG-MEASANDMOBPARAMETERS-START
MeasAndMobParameters ::= SEQUENCE {
   measAndMobParametersCommon [0] MeasAndMobParametersCommon OPTIONAL,
   measAndMobParametersXDD-Diff [1] MeasAndMobParametersXDD-Diff OPTIONAL,
   measAndMobParametersFRX-Diff [2] MeasAndMobParametersFRX-Diff OPTIONAL
}

MeasAndMobParametersMRDC-Common ::= SEQUENCE {
   independentGapConfig [0] ENUMERATED { supported(0) } OPTIONAL
}

MeasAndMobParametersMRDC-XDD-Diff ::= SEQUENCE {
   sftd-MeasPSCell [0] ENUMERATED { supported(0) } OPTIONAL,
   sftd-MeasNR-Cell [1] ENUMERATED { supported(0) } OPTIONAL
}

MeasAndMobParametersMRDC-FRX-Diff ::= SEQUENCE {
   simultaneousRxDataSSB-DiffNumerology [0] ENUMERATED { supported(0) }
       OPTIONAL
}

-- TAG-MEASANDMOBPARAMETERS-STOP
-- TAG-MEASANDMOBPARAMETERSMRDC-START
MeasAndMobParametersMRDC ::= SEQUENCE {
   measAndMobParametersMRDC-Common [0] MeasAndMobParametersMRDC-Common OPTIONAL
      ,
   measAndMobParametersMRDC-XDD-Diff [1] MeasAndMobParametersMRDC-XDD-Diff
       OPTIONAL,
   measAndMobParametersMRDC-FRX-Diff [2] MeasAndMobParametersMRDC-FRX-Diff
       OPTIONAL
}

MeasAndMobParametersMRDC-XDD-Diff-v1560 ::= SEQUENCE {
   sftd-MeasPSCell-NEDC [0] ENUMERATED { supported(0) } OPTIONAL
}

MeasAndMobParametersMRDC-v1560 ::= SEQUENCE {
   measAndMobParametersMRDC-XDD-Diff-v1560 [0] 
      MeasAndMobParametersMRDC-XDD-Diff-v1560 OPTIONAL
}

DummyG ::= SEQUENCE {
   maxNumberSSB-CSI-RS-ResourceOneTx [0] ENUMERATED { n8(0), n16(1), n32(2), 
      n64(3) },
   maxNumberSSB-CSI-RS-ResourceTwoTx [1] ENUMERATED { n0(0), n4(1), n8(2), 
      n16(3), n32(4), n64(5) },
   supportedCSI-RS-Density [2] ENUMERATED { one(0), three(1), oneAndThree(2) }
}

PTRS-DensityRecommendationDL ::= SEQUENCE {
   frequencyDensity1 [0] INTEGER (1..276),
   frequencyDensity2 [1] INTEGER (1..276),
   timeDensity1 [2] INTEGER (0..29),
   timeDensity2 [3] INTEGER (0..29),
   timeDensity3 [4] INTEGER (0..29)
}

PTRS-DensityRecommendationUL ::= SEQUENCE {
   frequencyDensity1 [0] INTEGER (1..276),
   frequencyDensity2 [1] INTEGER (1..276),
   timeDensity1 [2] INTEGER (0..29),
   timeDensity2 [3] INTEGER (0..29),
   timeDensity3 [4] INTEGER (0..29),
   sampleDensity1 [5] INTEGER (1..276),
   sampleDensity2 [6] INTEGER (1..276),
   sampleDensity3 [7] INTEGER (1..276),
   sampleDensity4 [8] INTEGER (1..276),
   sampleDensity5 [9] INTEGER (1..276)
}

DummyH ::= SEQUENCE {
   burstLength [0] INTEGER (1..2),
   maxSimultaneousResourceSetsPerCC [1] INTEGER (1..8),
   maxConfiguredResourceSetsPerCC [2] INTEGER (1..64),
   maxConfiguredResourceSetsAllCC [3] INTEGER (1..128)
}

BeamManagementSSB-CSI-RS ::= SEQUENCE {
   maxNumberSSB-CSI-RS-ResourceOneTx [0] ENUMERATED { n0(0), n8(1), n16(2), 
      n32(3), n64(4) },
   maxNumberCSI-RS-Resource [1] ENUMERATED { n0(0), n4(1), n8(2), n16(3), 
      n32(4), n64(5) },
   maxNumberCSI-RS-ResourceTwoTx [2] ENUMERATED { n0(0), n4(1), n8(2), n16(3), 
      n32(4), n64(5) },
   supportedCSI-RS-Density [3] ENUMERATED { one(0), three(1), oneAndThree(2) }
       OPTIONAL,
   maxNumberAperiodicCSI-RS-Resource [4] ENUMERATED { n0(0), n1(1), n4(2), 
      n8(3), n16(4), n32(5), n64(6) }
}

CSI-RS-IM-ReceptionForFeedback ::= SEQUENCE {
   maxConfigNumberNZP-CSI-RS-PerCC [0] INTEGER (1..64),
   maxConfigNumberPortsAcrossNZP-CSI-RS-PerCC [1] INTEGER (2..256),
   maxConfigNumberCSI-IM-PerCC [2] ENUMERATED { n1(0), n2(1), n4(2), n8(3), 
      n16(4), n32(5) },
   maxNumberSimultaneousNZP-CSI-RS-PerCC [3] INTEGER (1..64),
   totalNumberPortsSimultaneousNZP-CSI-RS-PerCC [4] INTEGER (2..256)
}

CSI-RS-ProcFrameworkForSRS ::= SEQUENCE {
   maxNumberPeriodicSRS-AssocCSI-RS-PerBWP [0] INTEGER (1..4),
   maxNumberAperiodicSRS-AssocCSI-RS-PerBWP [1] INTEGER (1..4),
   maxNumberSP-SRS-AssocCSI-RS-PerBWP [2] INTEGER (0..4),
   simultaneousSRS-AssocCSI-RS-PerCC [3] INTEGER (1..8)
}

CSI-ReportFramework ::= SEQUENCE {
   maxNumberPeriodicCSI-PerBWP-ForCSI-Report [0] INTEGER (1..4),
   maxNumberAperiodicCSI-PerBWP-ForCSI-Report [1] INTEGER (1..4),
   maxNumberSemiPersistentCSI-PerBWP-ForCSI-Report [2] INTEGER (0..4),
   maxNumberPeriodicCSI-PerBWP-ForBeamReport [3] INTEGER (1..4),
   maxNumberAperiodicCSI-PerBWP-ForBeamReport [4] INTEGER (1..4),
   maxNumberAperiodicCSI-triggeringStatePerCC [5] ENUMERATED { n3(0), n7(1), 
      n15(2), n31(3), n63(4), n128(5) },
   maxNumberSemiPersistentCSI-PerBWP-ForBeamReport [6] INTEGER (0..4),
   simultaneousCSI-ReportsPerCC [7] INTEGER (1..8)
}

CSI-RS-ForTracking ::= SEQUENCE {
   maxBurstLength [0] INTEGER (1..2),
   maxSimultaneousResourceSetsPerCC [1] INTEGER (1..8),
   maxConfiguredResourceSetsPerCC [2] INTEGER (1..64),
   maxConfiguredResourceSetsAllCC [3] INTEGER (1..256)
}

SpatialRelations ::= SEQUENCE {
   maxNumberConfiguredSpatialRelations [0] ENUMERATED { n4(0), n8(1), n16(2), 
      n32(3), n64(4), n96(5) },
   maxNumberActiveSpatialRelations [1] ENUMERATED { n1(0), n2(1), n4(2), n8(3)
      , n14(4) },
   additionalActiveSpatialRelationPUCCH [2] ENUMERATED { supported(0) }
       OPTIONAL,
   maxNumberDL-RS-QCL-TypeD [3] ENUMERATED { n1(0), n2(1), n4(2), n8(3), n14(4)
       }
}

-- TAG-MIMO-LAYERS-STOP
-- TAG-MIMO-PARAMETERSPERBAND-START
MIMO-ParametersPerBand ::= SEQUENCE {
   tci-StatePDSCH [0] SEQUENCE {
      maxNumberConfiguredTCIstatesPerCC [0] ENUMERATED { n4(0), n8(1), n16(2), 
         n32(3), n64(4), n128(5) } OPTIONAL,
      maxNumberActiveTCI-PerBWP [1] ENUMERATED { n1(0), n2(1), n4(2), n8(3) }
          OPTIONAL
   } OPTIONAL,
   additionalActiveTCI-StatePDCCH [1] ENUMERATED { supported(0) } OPTIONAL,
   pusch-TransCoherence [2] ENUMERATED { nonCoherent(0), partialCoherent(1), 
      fullCoherent(2) } OPTIONAL,
   beamCorrespondenceWithoutUL-BeamSweeping [3] ENUMERATED { supported(0) }
       OPTIONAL,
   periodicBeamReport [4] ENUMERATED { supported(0) } OPTIONAL,
   aperiodicBeamReport [5] ENUMERATED { supported(0) } OPTIONAL,
   sp-BeamReportPUCCH [6] ENUMERATED { supported(0) } OPTIONAL,
   sp-BeamReportPUSCH [7] ENUMERATED { supported(0) } OPTIONAL,
   dummy1 [8] DummyG OPTIONAL,
   maxNumberRxBeam [9] INTEGER (2..8) OPTIONAL,
   maxNumberRxTxBeamSwitchDL [10] SEQUENCE {
      scs-15kHz [0] ENUMERATED { n4(0), n7(1), n14(2) } OPTIONAL,
      scs-30kHz [1] ENUMERATED { n4(0), n7(1), n14(2) } OPTIONAL,
      scs-60kHz [2] ENUMERATED { n4(0), n7(1), n14(2) } OPTIONAL,
      scs-120kHz [3] ENUMERATED { n4(0), n7(1), n14(2) } OPTIONAL,
      scs-240kHz [4] ENUMERATED { n4(0), n7(1), n14(2) } OPTIONAL
   } OPTIONAL,
   maxNumberNonGroupBeamReporting [11] ENUMERATED { n1(0), n2(1), n4(2) }
       OPTIONAL,
   groupBeamReporting [12] ENUMERATED { supported(0) } OPTIONAL,
   uplinkBeamManagement [13] SEQUENCE {
      maxNumberSRS-ResourcePerSet-BM [0] ENUMERATED { n2(0), n4(1), n8(2), 
         n16(3) },
      maxNumberSRS-ResourceSet [1] INTEGER (1..8)
   } OPTIONAL,
   maxNumberCSI-RS-BFD [14] INTEGER (1..64) OPTIONAL,
   maxNumberSSB-BFD [15] INTEGER (1..64) OPTIONAL,
   maxNumberCSI-RS-SSB-CBD [16] INTEGER (1..256) OPTIONAL,
   dummy2 [17] ENUMERATED { supported(0) } OPTIONAL,
   twoPortsPTRS-UL [18] ENUMERATED { supported(0) } OPTIONAL,
   dummy5 [19] SRS-Resources OPTIONAL,
   dummy3 [20] INTEGER (1..4) OPTIONAL,
   beamReportTiming [21] SEQUENCE {
      scs-15kHz [0] ENUMERATED { sym2(0), sym4(1), sym8(2) } OPTIONAL,
      scs-30kHz [1] ENUMERATED { sym4(0), sym8(1), sym14(2), sym28(3) }
          OPTIONAL,
      scs-60kHz [2] ENUMERATED { sym8(0), sym14(1), sym28(2) } OPTIONAL,
      scs-120kHz [3] ENUMERATED { sym14(0), sym28(1), sym56(2) } OPTIONAL
   } OPTIONAL,
   ptrs-DensityRecommendationSetDL [22] SEQUENCE {
      scs-15kHz [0] PTRS-DensityRecommendationDL OPTIONAL,
      scs-30kHz [1] PTRS-DensityRecommendationDL OPTIONAL,
      scs-60kHz [2] PTRS-DensityRecommendationDL OPTIONAL,
      scs-120kHz [3] PTRS-DensityRecommendationDL OPTIONAL
   } OPTIONAL,
   ptrs-DensityRecommendationSetUL [23] SEQUENCE {
      scs-15kHz [0] PTRS-DensityRecommendationUL OPTIONAL,
      scs-30kHz [1] PTRS-DensityRecommendationUL OPTIONAL,
      scs-60kHz [2] PTRS-DensityRecommendationUL OPTIONAL,
      scs-120kHz [3] PTRS-DensityRecommendationUL OPTIONAL
   } OPTIONAL,
   dummy4 [24] DummyH OPTIONAL,
   aperiodicTRS [25] ENUMERATED { supported(0) } OPTIONAL,
   ...,
   [[
      dummy6 [26] ENUMERATED { true(0) } OPTIONAL,
      beamManagementSSB-CSI-RS [27] BeamManagementSSB-CSI-RS OPTIONAL,
      beamSwitchTiming [28] SEQUENCE {
         scs-60kHz [0] ENUMERATED { sym14(0), sym28(1), sym48(2), sym224(3), 
            sym336(4) } OPTIONAL,
         scs-120kHz [1] ENUMERATED { sym14(0), sym28(1), sym48(2), sym224(3), 
            sym336(4) } OPTIONAL
      } OPTIONAL,
      codebookParameters [29] CodebookParameters OPTIONAL,
      csi-RS-IM-ReceptionForFeedback [30] CSI-RS-IM-ReceptionForFeedback
          OPTIONAL,
      csi-RS-ProcFrameworkForSRS [31] CSI-RS-ProcFrameworkForSRS OPTIONAL,
      csi-ReportFramework [32] CSI-ReportFramework OPTIONAL,
      csi-RS-ForTracking [33] CSI-RS-ForTracking OPTIONAL,
      srs-AssocCSI-RS [34] SEQUENCE (SIZE (1..maxNrofCSI-RS-Resources)) OF SupportedCSI-RS-Resource
          OPTIONAL,
      spatialRelations [35] SpatialRelations OPTIONAL
   ]]
}

GeneralParametersMRDC-XDD-Diff ::= SEQUENCE {
   splitSRB-WithOneUL-Path [0] ENUMERATED { supported(0) } OPTIONAL,
   splitDRB-withUL-Both-MCG-SCG [1] ENUMERATED { supported(0) } OPTIONAL,
   srb3 [2] ENUMERATED { supported(0) } OPTIONAL,
   v2x-EUTRA [3] ENUMERATED { supported(0) } OPTIONAL,
   ...
}

UE-MRDC-CapabilityAddXDD-Mode ::= SEQUENCE {
   measAndMobParametersMRDC-XDD-Diff [0] MeasAndMobParametersMRDC-XDD-Diff
       OPTIONAL,
   generalParametersMRDC-XDD-Diff [1] GeneralParametersMRDC-XDD-Diff OPTIONAL
}

UE-MRDC-CapabilityAddFRX-Mode ::= SEQUENCE {
   measAndMobParametersMRDC-FRX-Diff [0] MeasAndMobParametersMRDC-FRX-Diff
}

-- TAG-MRDC-PARAMETERS-STOP
-- TAG-NRDC-PARAMETERS-START
NRDC-Parameters ::= SEQUENCE {
   measAndMobParametersNRDC [0] MeasAndMobParametersMRDC OPTIONAL,
   generalParametersNRDC [1] GeneralParametersMRDC-XDD-Diff OPTIONAL,
   fdd-Add-UE-NRDC-Capabilities [2] UE-MRDC-CapabilityAddXDD-Mode OPTIONAL,
   tdd-Add-UE-NRDC-Capabilities [3] UE-MRDC-CapabilityAddXDD-Mode OPTIONAL,
   fr1-Add-UE-NRDC-Capabilities [4] UE-MRDC-CapabilityAddFRX-Mode OPTIONAL,
   fr2-Add-UE-NRDC-Capabilities [5] UE-MRDC-CapabilityAddFRX-Mode OPTIONAL,
   lateNonCriticalExtension [6] OCTET STRING OPTIONAL,
   dummy [7] SEQUENCE {

   } OPTIONAL
}

NRDC-Parameters-v1570 ::= SEQUENCE {
   sfn-SyncNRDC [0] ENUMERATED { supported(0) } OPTIONAL
}

-- TAG-NRDC-PARAMETERS-STOP
-- TAG-PDCP-PARAMETERS-START
PDCP-Parameters ::= SEQUENCE {
   supportedROHC-Profiles [0] SEQUENCE {
      profile0x0000 [0] BOOLEAN,
      profile0x0001 [1] BOOLEAN,
      profile0x0002 [2] BOOLEAN,
      profile0x0003 [3] BOOLEAN,
      profile0x0004 [4] BOOLEAN,
      profile0x0006 [5] BOOLEAN,
      profile0x0101 [6] BOOLEAN,
      profile0x0102 [7] BOOLEAN,
      profile0x0103 [8] BOOLEAN,
      profile0x0104 [9] BOOLEAN
   },
   maxNumberROHC-ContextSessions [1] ENUMERATED { cs2(0), cs4(1), cs8(2), 
      cs12(3), cs16(4), cs24(5), cs32(6), cs48(7), cs64(8), cs128(9), cs256(10)
      , cs512(11), cs1024(12), cs16384(13), spare2(14), spare1(15) },
   uplinkOnlyROHC-Profiles [2] ENUMERATED { supported(0) } OPTIONAL,
   continueROHC-Context [3] ENUMERATED { supported(0) } OPTIONAL,
   outOfOrderDelivery [4] ENUMERATED { supported(0) } OPTIONAL,
   shortSN [5] ENUMERATED { supported(0) } OPTIONAL,
   pdcp-DuplicationSRB [6] ENUMERATED { supported(0) } OPTIONAL,
   pdcp-DuplicationMCG-OrSCG-DRB [7] ENUMERATED { supported(0) } OPTIONAL,
   ...
}

-- TAG-PDCP-PARAMETERS-STOP
-- TAG-PDCP-PARAMETERSMRDC-START
PDCP-ParametersMRDC ::= SEQUENCE {
   pdcp-DuplicationSplitSRB [0] ENUMERATED { supported(0) } OPTIONAL,
   pdcp-DuplicationSplitDRB [1] ENUMERATED { supported(0) } OPTIONAL
}

Phy-ParametersCommon ::= SEQUENCE {
   csi-RS-CFRA-ForHO [0] ENUMERATED { supported(0) } OPTIONAL,
   dynamicPRB-BundlingDL [1] ENUMERATED { supported(0) } OPTIONAL,
   sp-CSI-ReportPUCCH [2] ENUMERATED { supported(0) } OPTIONAL,
   sp-CSI-ReportPUSCH [3] ENUMERATED { supported(0) } OPTIONAL,
   nzp-CSI-RS-IntefMgmt [4] ENUMERATED { supported(0) } OPTIONAL,
   type2-SP-CSI-Feedback-LongPUCCH [5] ENUMERATED { supported(0) } OPTIONAL,
   precoderGranularityCORESET [6] ENUMERATED { supported(0) } OPTIONAL,
   dynamicHARQ-ACK-Codebook [7] ENUMERATED { supported(0) } OPTIONAL,
   semiStaticHARQ-ACK-Codebook [8] ENUMERATED { supported(0) } OPTIONAL,
   spatialBundlingHARQ-ACK [9] ENUMERATED { supported(0) } OPTIONAL,
   dynamicBetaOffsetInd-HARQ-ACK-CSI [10] ENUMERATED { supported(0) } OPTIONAL,
   pucch-Repetition-F1-3-4 [11] ENUMERATED { supported(0) } OPTIONAL,
   ra-Type0-PUSCH [12] ENUMERATED { supported(0) } OPTIONAL,
   dynamicSwitchRA-Type0-1-PDSCH [13] ENUMERATED { supported(0) } OPTIONAL,
   dynamicSwitchRA-Type0-1-PUSCH [14] ENUMERATED { supported(0) } OPTIONAL,
   pdsch-MappingTypeA [15] ENUMERATED { supported(0) } OPTIONAL,
   pdsch-MappingTypeB [16] ENUMERATED { supported(0) } OPTIONAL,
   interleavingVRB-ToPRB-PDSCH [17] ENUMERATED { supported(0) } OPTIONAL,
   interSlotFreqHopping-PUSCH [18] ENUMERATED { supported(0) } OPTIONAL,
   type1-PUSCH-RepetitionMultiSlots [19] ENUMERATED { supported(0) } OPTIONAL,
   type2-PUSCH-RepetitionMultiSlots [20] ENUMERATED { supported(0) } OPTIONAL,
   pusch-RepetitionMultiSlots [21] ENUMERATED { supported(0) } OPTIONAL,
   pdsch-RepetitionMultiSlots [22] ENUMERATED { supported(0) } OPTIONAL,
   downlinkSPS [23] ENUMERATED { supported(0) } OPTIONAL,
   configuredUL-GrantType1 [24] ENUMERATED { supported(0) } OPTIONAL,
   configuredUL-GrantType2 [25] ENUMERATED { supported(0) } OPTIONAL,
   pre-EmptIndication-DL [26] ENUMERATED { supported(0) } OPTIONAL,
   cbg-TransIndication-DL [27] ENUMERATED { supported(0) } OPTIONAL,
   cbg-TransIndication-UL [28] ENUMERATED { supported(0) } OPTIONAL,
   cbg-FlushIndication-DL [29] ENUMERATED { supported(0) } OPTIONAL,
   dynamicHARQ-ACK-CodeB-CBG-Retx-DL [30] ENUMERATED { supported(0) } OPTIONAL,
   rateMatchingResrcSetSemi-Static [31] ENUMERATED { supported(0) } OPTIONAL,
   rateMatchingResrcSetDynamic [32] ENUMERATED { supported(0) } OPTIONAL,
   bwp-SwitchingDelay [33] ENUMERATED { type1(0), type2(1) } OPTIONAL,
   ...,
   [[
      dummy [34] ENUMERATED { supported(0) } OPTIONAL
   ]],
   [[
      maxNumberSearchSpaces [35] ENUMERATED { n10(0) } OPTIONAL,
      rateMatchingCtrlResrcSetDynamic [36] ENUMERATED { supported(0) } OPTIONAL
         ,
      maxLayersMIMO-Indication [37] ENUMERATED { supported(0) } OPTIONAL
   ]]
}

Phy-ParametersXDD-Diff ::= SEQUENCE {
   dynamicSFI [0] ENUMERATED { supported(0) } OPTIONAL,
   twoPUCCH-F0-2-ConsecSymbols [1] ENUMERATED { supported(0) } OPTIONAL,
   twoDifferentTPC-Loop-PUSCH [2] ENUMERATED { supported(0) } OPTIONAL,
   twoDifferentTPC-Loop-PUCCH [3] ENUMERATED { supported(0) } OPTIONAL,
   ...,
   [[
      dl-SchedulingOffset-PDSCH-TypeA [4] ENUMERATED { supported(0) } OPTIONAL
         ,
      dl-SchedulingOffset-PDSCH-TypeB [5] ENUMERATED { supported(0) } OPTIONAL
         ,
      ul-SchedulingOffset [6] ENUMERATED { supported(0) } OPTIONAL
   ]]
}

Phy-ParametersFRX-Diff ::= SEQUENCE {
   dynamicSFI [0] ENUMERATED { supported(0) } OPTIONAL,
   dummy1 [1] BIT STRING  (SIZE (2)) OPTIONAL,
   twoFL-DMRS [2] BIT STRING  (SIZE (2)) OPTIONAL,
   dummy2 [3] BIT STRING  (SIZE (2)) OPTIONAL,
   dummy3 [4] BIT STRING  (SIZE (2)) OPTIONAL,
   supportedDMRS-TypeDL [5] ENUMERATED { type1(0), type1And2(1) } OPTIONAL,
   supportedDMRS-TypeUL [6] ENUMERATED { type1(0), type1And2(1) } OPTIONAL,
   semiOpenLoopCSI [7] ENUMERATED { supported(0) } OPTIONAL,
   csi-ReportWithoutPMI [8] ENUMERATED { supported(0) } OPTIONAL,
   csi-ReportWithoutCQI [9] ENUMERATED { supported(0) } OPTIONAL,
   onePortsPTRS [10] BIT STRING  (SIZE (2)) OPTIONAL,
   twoPUCCH-F0-2-ConsecSymbols [11] ENUMERATED { supported(0) } OPTIONAL,
   pucch-F2-WithFH [12] ENUMERATED { supported(0) } OPTIONAL,
   pucch-F3-WithFH [13] ENUMERATED { supported(0) } OPTIONAL,
   pucch-F4-WithFH [14] ENUMERATED { supported(0) } OPTIONAL,
   pucch-F0-2WithoutFH [15] ENUMERATED { notSupported(0) } OPTIONAL,
   pucch-F1-3-4WithoutFH [16] ENUMERATED { notSupported(0) } OPTIONAL,
   mux-SR-HARQ-ACK-CSI-PUCCH-MultiPerSlot [17] ENUMERATED { supported(0) }
       OPTIONAL,
   uci-CodeBlockSegmentation [18] ENUMERATED { supported(0) } OPTIONAL,
   onePUCCH-LongAndShortFormat [19] ENUMERATED { supported(0) } OPTIONAL,
   twoPUCCH-AnyOthersInSlot [20] ENUMERATED { supported(0) } OPTIONAL,
   intraSlotFreqHopping-PUSCH [21] ENUMERATED { supported(0) } OPTIONAL,
   pusch-LBRM [22] ENUMERATED { supported(0) } OPTIONAL,
   pdcch-BlindDetectionCA [23] INTEGER (4..16) OPTIONAL,
   tpc-PUSCH-RNTI [24] ENUMERATED { supported(0) } OPTIONAL,
   tpc-PUCCH-RNTI [25] ENUMERATED { supported(0) } OPTIONAL,
   tpc-SRS-RNTI [26] ENUMERATED { supported(0) } OPTIONAL,
   absoluteTPC-Command [27] ENUMERATED { supported(0) } OPTIONAL,
   twoDifferentTPC-Loop-PUSCH [28] ENUMERATED { supported(0) } OPTIONAL,
   twoDifferentTPC-Loop-PUCCH [29] ENUMERATED { supported(0) } OPTIONAL,
   pusch-HalfPi-BPSK [30] ENUMERATED { supported(0) } OPTIONAL,
   pucch-F3-4-HalfPi-BPSK [31] ENUMERATED { supported(0) } OPTIONAL,
   almostContiguousCP-OFDM-UL [32] ENUMERATED { supported(0) } OPTIONAL,
   sp-CSI-RS [33] ENUMERATED { supported(0) } OPTIONAL,
   sp-CSI-IM [34] ENUMERATED { supported(0) } OPTIONAL,
   tdd-MultiDL-UL-SwitchPerSlot [35] ENUMERATED { supported(0) } OPTIONAL,
   multipleCORESET [36] ENUMERATED { supported(0) } OPTIONAL,
   ...,
   [[
      csi-RS-IM-ReceptionForFeedback [37] CSI-RS-IM-ReceptionForFeedback
          OPTIONAL,
      csi-RS-ProcFrameworkForSRS [38] CSI-RS-ProcFrameworkForSRS OPTIONAL,
      csi-ReportFramework [39] CSI-ReportFramework OPTIONAL,
      mux-SR-HARQ-ACK-CSI-PUCCH-OncePerSlot [40] SEQUENCE {
         sameSymbol [0] ENUMERATED { supported(0) } OPTIONAL,
         diffSymbol [1] ENUMERATED { supported(0) } OPTIONAL
      } OPTIONAL,
      mux-SR-HARQ-ACK-PUCCH [41] ENUMERATED { supported(0) } OPTIONAL,
      mux-MultipleGroupCtrlCH-Overlap [42] ENUMERATED { supported(0) } OPTIONAL
         ,
      dl-SchedulingOffset-PDSCH-TypeA [43] ENUMERATED { supported(0) } OPTIONAL
         ,
      dl-SchedulingOffset-PDSCH-TypeB [44] ENUMERATED { supported(0) } OPTIONAL
         ,
      ul-SchedulingOffset [45] ENUMERATED { supported(0) } OPTIONAL,
      dl-64QAM-MCS-TableAlt [46] ENUMERATED { supported(0) } OPTIONAL,
      ul-64QAM-MCS-TableAlt [47] ENUMERATED { supported(0) } OPTIONAL,
      cqi-TableAlt [48] ENUMERATED { supported(0) } OPTIONAL,
      oneFL-DMRS-TwoAdditionalDMRS-UL [49] ENUMERATED { supported(0) } OPTIONAL
         ,
      twoFL-DMRS-TwoAdditionalDMRS-UL [50] ENUMERATED { supported(0) } OPTIONAL
         ,
      oneFL-DMRS-ThreeAdditionalDMRS-UL [51] ENUMERATED { supported(0) }
          OPTIONAL
   ]],
   [[
      pdcch-BlindDetectionNRDC [52] SEQUENCE {
         pdcch-BlindDetectionMCG-UE [0] INTEGER (1..15),
         pdcch-BlindDetectionSCG-UE [1] INTEGER (1..15)
      } OPTIONAL,
      mux-HARQ-ACK-PUSCH-DiffSymbol [53] ENUMERATED { supported(0) } OPTIONAL
   ]]
}

Phy-ParametersFR1 ::= SEQUENCE {
   pdcch-MonitoringSingleOccasion [0] ENUMERATED { supported(0) } OPTIONAL,
   scs-60kHz [1] ENUMERATED { supported(0) } OPTIONAL,
   pdsch-256QAM-FR1 [2] ENUMERATED { supported(0) } OPTIONAL,
   pdsch-RE-MappingFR1-PerSymbol [3] ENUMERATED { n10(0), n20(1) } OPTIONAL,
   ...,
   [[
      pdsch-RE-MappingFR1-PerSlot [4] ENUMERATED { n16(0), n32(1), n48(2), 
         n64(3), n80(4), n96(5), n112(6), n128(7), n144(8), n160(9), n176(10), 
         n192(11), n208(12), n224(13), n240(14), n256(15) } OPTIONAL
   ]]
}

Phy-ParametersFR2 ::= SEQUENCE {
   dummy [0] ENUMERATED { supported(0) } OPTIONAL,
   pdsch-RE-MappingFR2-PerSymbol [1] ENUMERATED { n6(0), n20(1) } OPTIONAL,
   ...,
   [[
      pCell-FR2 [2] ENUMERATED { supported(0) } OPTIONAL,
      pdsch-RE-MappingFR2-PerSlot [3] ENUMERATED { n16(0), n32(1), n48(2), 
         n64(3), n80(4), n96(5), n112(6), n128(7), n144(8), n160(9), n176(10), 
         n192(11), n208(12), n224(13), n240(14), n256(15) } OPTIONAL
   ]]
}

-- TAG-PDCP-PARAMETERSMRDC-STOP
-- TAG-PHY-PARAMETERS-START
Phy-Parameters ::= SEQUENCE {
   phy-ParametersCommon [0] Phy-ParametersCommon OPTIONAL,
   phy-ParametersXDD-Diff [1] Phy-ParametersXDD-Diff OPTIONAL,
   phy-ParametersFRX-Diff [2] Phy-ParametersFRX-Diff OPTIONAL,
   phy-ParametersFR1 [3] Phy-ParametersFR1 OPTIONAL,
   phy-ParametersFR2 [4] Phy-ParametersFR2 OPTIONAL
}

NAICS-Capability-Entry ::= SEQUENCE {
   numberOfNAICS-CapableCC [0] INTEGER (1..5),
   numberOfAggregatedPRB [1] ENUMERATED { n50(0), n75(1), n100(2), n125(3), 
      n150(4), n175(5), n200(6), n225(7), n250(8), n275(9), n300(10), n350(11)
      , n400(12), n450(13), n500(14), spare(15) },
   ...
}

-- TAG-PHY-PARAMETERS-STOP
-- TAG-PHY-PARAMETERSMRDC-START
Phy-ParametersMRDC ::= SEQUENCE {
   naics-Capability-List [0] SEQUENCE (SIZE (1..maxNrofNAICS-Entries)) OF NAICS-Capability-Entry
       OPTIONAL,
   ...
}

BandNR ::= SEQUENCE {
   bandNR [0] FreqBandIndicatorNR,
   modifiedMPR-Behaviour [1] BIT STRING  (SIZE (8)) OPTIONAL,
   mimo-ParametersPerBand [2] MIMO-ParametersPerBand OPTIONAL,
   extendedCP [3] ENUMERATED { supported(0) } OPTIONAL,
   multipleTCI [4] ENUMERATED { supported(0) } OPTIONAL,
   bwp-WithoutRestriction [5] ENUMERATED { supported(0) } OPTIONAL,
   bwp-SameNumerology [6] ENUMERATED { upto2(0), upto4(1) } OPTIONAL,
   bwp-DiffNumerology [7] ENUMERATED { upto4(0) } OPTIONAL,
   crossCarrierScheduling-SameSCS [8] ENUMERATED { supported(0) } OPTIONAL,
   pdsch-256QAM-FR2 [9] ENUMERATED { supported(0) } OPTIONAL,
   pusch-256QAM [10] ENUMERATED { supported(0) } OPTIONAL,
   ue-PowerClass [11] ENUMERATED { pc1(0), pc2(1), pc3(2), pc4(3) } OPTIONAL,
   rateMatchingLTE-CRS [12] ENUMERATED { supported(0) } OPTIONAL,
   channelBWs-DL [13] EXPLICIT CHOICE {
      fr1 [0] SEQUENCE {
         scs-15kHz [0] BIT STRING  (SIZE (10)) OPTIONAL,
         scs-30kHz [1] BIT STRING  (SIZE (10)) OPTIONAL,
         scs-60kHz [2] BIT STRING  (SIZE (10)) OPTIONAL
      },
      fr2 [1] SEQUENCE {
         scs-60kHz [0] BIT STRING  (SIZE (3)) OPTIONAL,
         scs-120kHz [1] BIT STRING  (SIZE (3)) OPTIONAL
      }
   } OPTIONAL,
   channelBWs-UL [14] EXPLICIT CHOICE {
      fr1 [0] SEQUENCE {
         scs-15kHz [0] BIT STRING  (SIZE (10)) OPTIONAL,
         scs-30kHz [1] BIT STRING  (SIZE (10)) OPTIONAL,
         scs-60kHz [2] BIT STRING  (SIZE (10)) OPTIONAL
      },
      fr2 [1] SEQUENCE {
         scs-60kHz [0] BIT STRING  (SIZE (3)) OPTIONAL,
         scs-120kHz [1] BIT STRING  (SIZE (3)) OPTIONAL
      }
   } OPTIONAL,
   ...,
   [[
      maxUplinkDutyCycle-PC2-FR1 [15] ENUMERATED { n60(0), n70(1), n80(2), 
         n90(3), n100(4) } OPTIONAL
   ]],
   [[
      pucch-SpatialRelInfoMAC-CE [16] ENUMERATED { supported(0) } OPTIONAL,
      powerBoosting-pi2BPSK [17] ENUMERATED { supported(0) } OPTIONAL
   ]],
   [[
      maxUplinkDutyCycle-FR2 [18] ENUMERATED { n15(0), n20(1), n25(2), n30(3), 
         n40(4), n50(5), n60(6), n70(7), n80(8), n90(9), n100(10) } OPTIONAL
   ]]
}

-- TAG-RAT-TYPE-STOP
-- TAG-RF-PARAMETERS-START
RF-Parameters ::= SEQUENCE {
   supportedBandListNR [0] SEQUENCE (SIZE (1..maxBands)) OF BandNR,
   supportedBandCombinationList [1] BandCombinationList OPTIONAL,
   appliedFreqBandListFilter [2] FreqBandList OPTIONAL,
   ...,
   [[
      supportedBandCombinationList-v1540 [3] BandCombinationList-v1540 OPTIONAL
         ,
      srs-SwitchingTimeRequested [4] ENUMERATED { true(0) } OPTIONAL
   ]],
   [[
      supportedBandCombinationList-v1550 [5] BandCombinationList-v1550 OPTIONAL
   ]],
   [[
      supportedBandCombinationList-v1560 [6] BandCombinationList-v1560 OPTIONAL
   ]]
}

-- TAG-RF-PARAMETERS-STOP
-- TAG-RF-PARAMETERSMRDC-START
RF-ParametersMRDC ::= SEQUENCE {
   supportedBandCombinationList [0] BandCombinationList OPTIONAL,
   appliedFreqBandListFilter [1] FreqBandList OPTIONAL,
   ...,
   [[
      srs-SwitchingTimeRequested [2] ENUMERATED { true(0) } OPTIONAL,
      supportedBandCombinationList-v1540 [3] BandCombinationList-v1540 OPTIONAL
   ]],
   [[
      supportedBandCombinationList-v1550 [4] BandCombinationList-v1550 OPTIONAL
   ]],
   [[
      supportedBandCombinationList-v1560 [5] BandCombinationList-v1560 OPTIONAL
         ,
      supportedBandCombinationListNEDC-Only [6] BandCombinationList OPTIONAL
   ]],
   [[
      supportedBandCombinationList-v1570 [7] BandCombinationList-v1570 OPTIONAL
   ]],
   [[
      supportedBandCombinationList-v1580 [8] BandCombinationList-v1580 OPTIONAL
   ]]
}

-- TAG-RF-PARAMETERSMRDC-STOP
-- TAG-RLC-PARAMETERS-START
RLC-Parameters ::= SEQUENCE {
   am-WithShortSN [0] ENUMERATED { supported(0) } OPTIONAL,
   um-WithShortSN [1] ENUMERATED { supported(0) } OPTIONAL,
   um-WithLongSN [2] ENUMERATED { supported(0) } OPTIONAL,
   ...
}

-- TAG-RLC-PARAMETERS-STOP
-- TAG-SDAP-PARAMETERS-START
SDAP-Parameters ::= SEQUENCE {
   as-ReflectiveQoS [0] ENUMERATED { true(0) } OPTIONAL,
   ...
}

UE-CapabilityRequestFilterNR-v1540 ::= SEQUENCE {
   srs-SwitchingTimeRequest [0] ENUMERATED { true(0) } OPTIONAL, -- Need N
   nonCriticalExtension [1] SEQUENCE {

   } OPTIONAL
}

-- TAG-UE-CAPABILITYREQUESTFILTERCOMMON-STOP
-- TAG-UE-CAPABILITYREQUESTFILTERNR-START
UE-CapabilityRequestFilterNR ::= SEQUENCE {
   frequencyBandListFilter [0] FreqBandList OPTIONAL, -- Need N
   nonCriticalExtension [1] UE-CapabilityRequestFilterNR-v1540 OPTIONAL
}

UE-MRDC-CapabilityAddXDD-Mode-v1560 ::= SEQUENCE {
   measAndMobParametersMRDC-XDD-Diff-v1560 [0] 
      MeasAndMobParametersMRDC-XDD-Diff-v1560 OPTIONAL
}

UE-MRDC-Capability-v1560 ::= SEQUENCE {
   receivedFilters [0] OCTET STRING (CONTAINING UECapabilityEnquiry-v1560-IEs)
       OPTIONAL,
   measAndMobParametersMRDC-v1560 [1] MeasAndMobParametersMRDC-v1560 OPTIONAL,
   fdd-Add-UE-MRDC-Capabilities-v1560 [2] UE-MRDC-CapabilityAddXDD-Mode-v1560
       OPTIONAL,
   tdd-Add-UE-MRDC-Capabilities-v1560 [3] UE-MRDC-CapabilityAddXDD-Mode-v1560
       OPTIONAL,
   nonCriticalExtension [4] SEQUENCE {

   } OPTIONAL
}

-- TAG-UE-CAPABILITYREQUESTFILTERNR-STOP
-- TAG-UE-MRDC-CAPABILITY-START
UE-MRDC-Capability ::= SEQUENCE {
   measAndMobParametersMRDC [0] MeasAndMobParametersMRDC OPTIONAL,
   phy-ParametersMRDC-v1530 [1] Phy-ParametersMRDC OPTIONAL,
   rf-ParametersMRDC [2] RF-ParametersMRDC,
   generalParametersMRDC [3] GeneralParametersMRDC-XDD-Diff OPTIONAL,
   fdd-Add-UE-MRDC-Capabilities [4] UE-MRDC-CapabilityAddXDD-Mode OPTIONAL,
   tdd-Add-UE-MRDC-Capabilities [5] UE-MRDC-CapabilityAddXDD-Mode OPTIONAL,
   fr1-Add-UE-MRDC-Capabilities [6] UE-MRDC-CapabilityAddFRX-Mode OPTIONAL,
   fr2-Add-UE-MRDC-Capabilities [7] UE-MRDC-CapabilityAddFRX-Mode OPTIONAL,
   featureSetCombinations [8] SEQUENCE (SIZE (1..maxFeatureSetCombinations)) OF FeatureSetCombination
       OPTIONAL,
   pdcp-ParametersMRDC-v1530 [9] PDCP-ParametersMRDC OPTIONAL,
   lateNonCriticalExtension [10] OCTET STRING OPTIONAL,
   nonCriticalExtension [11] UE-MRDC-Capability-v1560 OPTIONAL
}

UE-NR-CapabilityAddXDD-Mode ::= SEQUENCE {
   phy-ParametersXDD-Diff [0] Phy-ParametersXDD-Diff OPTIONAL,
   mac-ParametersXDD-Diff [1] MAC-ParametersXDD-Diff OPTIONAL,
   measAndMobParametersXDD-Diff [2] MeasAndMobParametersXDD-Diff OPTIONAL
}

UE-NR-CapabilityAddFRX-Mode ::= SEQUENCE {
   phy-ParametersFRX-Diff [0] Phy-ParametersFRX-Diff OPTIONAL,
   measAndMobParametersFRX-Diff [1] MeasAndMobParametersFRX-Diff OPTIONAL
}

UE-NR-CapabilityAddXDD-Mode-v1530 ::= SEQUENCE {
   eutra-ParametersXDD-Diff [0] EUTRA-ParametersXDD-Diff
}

UE-NR-CapabilityAddFRX-Mode-v1540 ::= SEQUENCE {
   ims-ParametersFRX-Diff [0] IMS-ParametersFRX-Diff OPTIONAL
}

UE-NR-Capability-v1570 ::= SEQUENCE {
   nrdc-Parameters-v1570 [0] NRDC-Parameters-v1570 OPTIONAL,
   nonCriticalExtension [1] SEQUENCE {

   } OPTIONAL
}

UE-NR-Capability-v1560 ::= SEQUENCE {
   nrdc-Parameters [0] NRDC-Parameters OPTIONAL,
   receivedFilters [1] OCTET STRING (CONTAINING UECapabilityEnquiry-v1560-IEs)
       OPTIONAL,
   nonCriticalExtension [2] UE-NR-Capability-v1570 OPTIONAL
}

UE-NR-Capability-v1550 ::= SEQUENCE {
   reducedCP-Latency [0] ENUMERATED { supported(0) } OPTIONAL,
   nonCriticalExtension [1] UE-NR-Capability-v1560 OPTIONAL
}

UE-NR-Capability-v1540 ::= SEQUENCE {
   sdap-Parameters [0] SDAP-Parameters OPTIONAL,
   overheatingInd [1] ENUMERATED { supported(0) } OPTIONAL,
   ims-Parameters [2] IMS-Parameters OPTIONAL,
   fr1-Add-UE-NR-Capabilities-v1540 [3] UE-NR-CapabilityAddFRX-Mode-v1540
       OPTIONAL,
   fr2-Add-UE-NR-Capabilities-v1540 [4] UE-NR-CapabilityAddFRX-Mode-v1540
       OPTIONAL,
   fr1-fr2-Add-UE-NR-Capabilities [5] UE-NR-CapabilityAddFRX-Mode OPTIONAL,
   nonCriticalExtension [6] UE-NR-Capability-v1550 OPTIONAL
}

UE-NR-Capability-v1530 ::= SEQUENCE {
   fdd-Add-UE-NR-Capabilities-v1530 [0] UE-NR-CapabilityAddXDD-Mode-v1530
       OPTIONAL,
   tdd-Add-UE-NR-Capabilities-v1530 [1] UE-NR-CapabilityAddXDD-Mode-v1530
       OPTIONAL,
   dummy [2] ENUMERATED { supported(0) } OPTIONAL,
   interRAT-Parameters [3] InterRAT-Parameters OPTIONAL,
   inactiveState [4] ENUMERATED { supported(0) } OPTIONAL,
   delayBudgetReporting [5] ENUMERATED { supported(0) } OPTIONAL,
   nonCriticalExtension [6] UE-NR-Capability-v1540 OPTIONAL
}

-- TAG-UE-MRDC-CAPABILITY-STOP
-- TAG-UE-NR-CAPABILITY-START
UE-NR-Capability ::= SEQUENCE {
   accessStratumRelease [0] AccessStratumRelease,
   pdcp-Parameters [1] PDCP-Parameters,
   rlc-Parameters [2] RLC-Parameters OPTIONAL,
   mac-Parameters [3] MAC-Parameters OPTIONAL,
   phy-Parameters [4] Phy-Parameters,
   rf-Parameters [5] RF-Parameters,
   measAndMobParameters [6] MeasAndMobParameters OPTIONAL,
   fdd-Add-UE-NR-Capabilities [7] UE-NR-CapabilityAddXDD-Mode OPTIONAL,
   tdd-Add-UE-NR-Capabilities [8] UE-NR-CapabilityAddXDD-Mode OPTIONAL,
   fr1-Add-UE-NR-Capabilities [9] UE-NR-CapabilityAddFRX-Mode OPTIONAL,
   fr2-Add-UE-NR-Capabilities [10] UE-NR-CapabilityAddFRX-Mode OPTIONAL,
   featureSets [11] FeatureSets OPTIONAL,
   featureSetCombinations [12] SEQUENCE (SIZE (1..maxFeatureSetCombinations)) OF FeatureSetCombination
       OPTIONAL,
   lateNonCriticalExtension [13] OCTET STRING OPTIONAL,
   nonCriticalExtension [14] UE-NR-Capability-v1530 OPTIONAL
}

-- Value assignments

maxBandComb INTEGER ::= 65536

maxCellBlack INTEGER ::= 16

maxCellInter INTEGER ::= 16

maxCellIntra INTEGER ::= 16

maxCellMeasEUTRA INTEGER ::= 32

maxEARFCN INTEGER ::= 262143

maxEUTRA-CellBlack INTEGER ::= 16

maxEUTRA-NS-Pmax INTEGER ::= 8

maxMultiBands INTEGER ::= 8

maxNARFCN INTEGER ::= 3279165

maxNR-NS-Pmax INTEGER ::= 8

maxNrofServingCells INTEGER ::= 32

maxNrofServingCells-1 INTEGER ::= 31

maxNrofAggregatedCellsPerCellGroup INTEGER ::= 16

maxNrofSCells INTEGER ::= 31

maxNrofCellMeas INTEGER ::= 32

maxNrofSS-BlocksToAverage INTEGER ::= 16

maxNrofCSI-RS-ResourcesToAverage INTEGER ::= 16

maxNrofDL-Allocations INTEGER ::= 16

maxNrofSR-ConfigPerCellGroup INTEGER ::= 8

maxLCG-ID INTEGER ::= 7

maxLC-ID INTEGER ::= 32

maxNrofTAGs INTEGER ::= 4

maxNrofTAGs-1 INTEGER ::= 3

maxNrofBWPs INTEGER ::= 4

maxNrofCombIDC INTEGER ::= 128

maxNrofSymbols-1 INTEGER ::= 13

maxNrofSlots INTEGER ::= 320

maxNrofSlots-1 INTEGER ::= 319

maxNrofPhysicalResourceBlocks INTEGER ::= 275

maxNrofPhysicalResourceBlocks-1 INTEGER ::= 274

maxNrofPhysicalResourceBlocksPlus1 INTEGER ::= 276

maxNrofControlResourceSets-1 INTEGER ::= 11

maxCoReSetDuration INTEGER ::= 3

maxNrofSearchSpaces-1 INTEGER ::= 39

maxSFI-DCI-PayloadSize INTEGER ::= 128

maxSFI-DCI-PayloadSize-1 INTEGER ::= 127

maxINT-DCI-PayloadSize INTEGER ::= 126

maxINT-DCI-PayloadSize-1 INTEGER ::= 125

maxNrofRateMatchPatterns INTEGER ::= 4

maxNrofRateMatchPatterns-1 INTEGER ::= 3

maxNrofRateMatchPatternsPerGroup INTEGER ::= 8

maxNrofCSI-ReportConfigurations INTEGER ::= 48

maxNrofCSI-ReportConfigurations-1 INTEGER ::= 47

maxNrofCSI-ResourceConfigurations INTEGER ::= 112

maxNrofCSI-ResourceConfigurations-1 INTEGER ::= 111

maxNrofAP-CSI-RS-ResourcesPerSet INTEGER ::= 16

maxNrOfCSI-AperiodicTriggers INTEGER ::= 128

maxNrofReportConfigPerAperiodicTrigger INTEGER ::= 16

maxNrofNZP-CSI-RS-Resources INTEGER ::= 192

maxNrofNZP-CSI-RS-Resources-1 INTEGER ::= 191

maxNrofNZP-CSI-RS-ResourcesPerSet INTEGER ::= 64

maxNrofNZP-CSI-RS-ResourceSets INTEGER ::= 64

maxNrofNZP-CSI-RS-ResourceSets-1 INTEGER ::= 63

maxNrofNZP-CSI-RS-ResourceSetsPerConfig INTEGER ::= 16

maxNrofNZP-CSI-RS-ResourcesPerConfig INTEGER ::= 128

maxNrofZP-CSI-RS-Resources INTEGER ::= 32

maxNrofZP-CSI-RS-Resources-1 INTEGER ::= 31

maxNrofZP-CSI-RS-ResourceSets-1 INTEGER ::= 15

maxNrofZP-CSI-RS-ResourcesPerSet INTEGER ::= 16

maxNrofZP-CSI-RS-ResourceSets INTEGER ::= 16

maxNrofCSI-IM-Resources INTEGER ::= 32

maxNrofCSI-IM-Resources-1 INTEGER ::= 31

maxNrofCSI-IM-ResourcesPerSet INTEGER ::= 8

maxNrofCSI-IM-ResourceSets INTEGER ::= 64

maxNrofCSI-IM-ResourceSets-1 INTEGER ::= 63

maxNrofCSI-IM-ResourceSetsPerConfig INTEGER ::= 16

maxNrofCSI-SSB-ResourcePerSet INTEGER ::= 64

maxNrofCSI-SSB-ResourceSets INTEGER ::= 64

maxNrofCSI-SSB-ResourceSets-1 INTEGER ::= 63

maxNrofCSI-SSB-ResourceSetsPerConfig INTEGER ::= 1

maxNrofFailureDetectionResources INTEGER ::= 10

maxNrofFailureDetectionResources-1 INTEGER ::= 9

maxNrofObjectId INTEGER ::= 64

maxNrofPageRec INTEGER ::= 32

maxNrofPCI-Ranges INTEGER ::= 8

maxPLMN INTEGER ::= 12

maxNrofCSI-RS-ResourcesRRM INTEGER ::= 96

maxNrofCSI-RS-ResourcesRRM-1 INTEGER ::= 95

maxNrofMeasId INTEGER ::= 64

maxNrofQuantityConfig INTEGER ::= 2

maxNrofCSI-RS-CellsRRM INTEGER ::= 96

maxNrofSRS-ResourceSets INTEGER ::= 16

maxNrofSRS-ResourceSets-1 INTEGER ::= 15

maxNrofSRS-Resources INTEGER ::= 64

maxNrofSRS-Resources-1 INTEGER ::= 63

maxNrofSRS-ResourcesPerSet INTEGER ::= 16

maxNrofSRS-TriggerStates-1 INTEGER ::= 3

maxNrofSRS-TriggerStates-2 INTEGER ::= 2

maxRAT-CapabilityContainers INTEGER ::= 8

maxSimultaneousBands INTEGER ::= 32

maxNrofSlotFormatCombinationsPerSet INTEGER ::= 512

maxNrofSlotFormatCombinationsPerSet-1 INTEGER ::= 511

maxNrofPUCCH-Resources INTEGER ::= 128

maxNrofPUCCH-Resources-1 INTEGER ::= 127

maxNrofPUCCH-ResourceSets INTEGER ::= 4

maxNrofPUCCH-ResourceSets-1 INTEGER ::= 3

maxNrofPUCCH-ResourcesPerSet INTEGER ::= 32

maxNrofPUCCH-P0-PerSet INTEGER ::= 8

maxNrofPUCCH-PathlossReferenceRSs INTEGER ::= 4

maxNrofPUCCH-PathlossReferenceRSs-1 INTEGER ::= 3

maxNrofP0-PUSCH-AlphaSets INTEGER ::= 30

maxNrofP0-PUSCH-AlphaSets-1 INTEGER ::= 29

maxNrofPUSCH-PathlossReferenceRSs INTEGER ::= 4

maxNrofPUSCH-PathlossReferenceRSs-1 INTEGER ::= 3

maxNrofNAICS-Entries INTEGER ::= 8

maxBands INTEGER ::= 1024

maxBandsMRDC INTEGER ::= 1280

maxBandsEUTRA INTEGER ::= 256

maxCellReport INTEGER ::= 8

maxDRB INTEGER ::= 29

maxFreq INTEGER ::= 8

maxFreqIDC-MRDC INTEGER ::= 32

maxNrofCandidateBeams INTEGER ::= 16

maxNrofPCIsPerSMTC INTEGER ::= 64

maxNrofQFIs INTEGER ::= 64

maxNrOfSemiPersistentPUSCH-Triggers INTEGER ::= 64

maxNrofSR-Resources INTEGER ::= 8

maxNrofSlotFormatsPerCombination INTEGER ::= 256

maxNrofSpatialRelationInfos INTEGER ::= 8

maxNrofIndexesToReport INTEGER ::= 32

maxNrofIndexesToReport2 INTEGER ::= 64

maxNrofSSBs-1 INTEGER ::= 63

maxNrofS-NSSAI INTEGER ::= 8

maxNrofTCI-StatesPDCCH INTEGER ::= 64

maxNrofTCI-States INTEGER ::= 128

maxNrofTCI-States-1 INTEGER ::= 127

maxNrofUL-Allocations INTEGER ::= 16

maxQFI INTEGER ::= 63

maxRA-CSIRS-Resources INTEGER ::= 96

maxRA-OccasionsPerCSIRS INTEGER ::= 64

maxRA-Occasions-1 INTEGER ::= 511

maxRA-SSB-Resources INTEGER ::= 64

maxSCSs INTEGER ::= 5

maxSecondaryCellGroups INTEGER ::= 3

maxNrofServingCellsEUTRA INTEGER ::= 32

maxMBSFN-Allocations INTEGER ::= 8

maxNrofMultiBands INTEGER ::= 8

maxCellSFTD INTEGER ::= 3

maxReportConfigId INTEGER ::= 64

maxNrofCodebooks INTEGER ::= 16

maxNrofCSI-RS-Resources INTEGER ::= 7

maxNrofSRI-PUSCH-Mappings INTEGER ::= 16

maxNrofSRI-PUSCH-Mappings-1 INTEGER ::= 15

maxSIB INTEGER ::= 32

maxSI-Message INTEGER ::= 32

maxPO-perPF INTEGER ::= 4

maxAccessCat-1 INTEGER ::= 63

maxBarringInfoSet INTEGER ::= 8

maxCellEUTRA INTEGER ::= 8

maxEUTRA-Carrier INTEGER ::= 8

maxPLMNIdentities INTEGER ::= 8

maxDownlinkFeatureSets INTEGER ::= 1024

maxUplinkFeatureSets INTEGER ::= 1024

maxEUTRA-DL-FeatureSets INTEGER ::= 256

maxEUTRA-UL-FeatureSets INTEGER ::= 256

maxFeatureSetsPerBand INTEGER ::= 128

maxPerCC-FeatureSets INTEGER ::= 1024

maxFeatureSetCombinations INTEGER ::= 1024

maxInterRAT-RSTD-Freq INTEGER ::= 3


END
