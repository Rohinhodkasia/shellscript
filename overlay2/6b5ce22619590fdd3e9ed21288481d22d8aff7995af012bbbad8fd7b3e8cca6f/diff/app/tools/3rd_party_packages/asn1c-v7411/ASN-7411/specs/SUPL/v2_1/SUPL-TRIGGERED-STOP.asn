-- This file was generated by the Objective Systems ASN1C Compiler
-- (http://www.obj-sys.com).  Version: 6.8.A, Date: 15-Nov-2014.

SUPL-TRIGGERED-STOP DEFINITIONS AUTOMATIC TAGS ::= BEGIN

IMPORTS

StatusCode
FROM ULP-Components ;

-- Productions

Ver2-SUPLTRIGGEREDSTOP ::= SEQUENCE {
   statusCode [0] StatusCode OPTIONAL,
   ...
}

END
