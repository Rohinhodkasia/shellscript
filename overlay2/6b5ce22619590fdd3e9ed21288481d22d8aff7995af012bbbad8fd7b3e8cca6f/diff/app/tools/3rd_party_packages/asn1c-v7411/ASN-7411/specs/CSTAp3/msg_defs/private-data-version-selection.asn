CSTA-private-data-version-selection
	{ iso( 1) identified-organization( 3) icd-ecma( 12)
		standard( 0) csta3( 285) private-data-version-selection( 368) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) };

privateDataVersionSelection OPERATION ::=
{ 	ARGUMENT		PrivateDataVersionSelectionArgument
	RESULT			PrivateDataVersionSelectionResult
	ERRORS			{universalFailure }
	CODE			local: 368 }

PrivateDataVersionSelectionArgument ::= INTEGER

PrivateDataVersionSelectionResult ::=  CHOICE
{	extensions			CSTACommonArguments,
	noData 				NULL }

END -- of CSTA-private-data-version-selection
