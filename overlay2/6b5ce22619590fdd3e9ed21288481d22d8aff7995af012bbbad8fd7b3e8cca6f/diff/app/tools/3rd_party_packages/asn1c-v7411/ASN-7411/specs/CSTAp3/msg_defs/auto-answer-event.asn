CSTA-auto-answer-event
	{ iso( 1) identified-organization( 3) icd-ecma( 12)
		standard( 0) csta3( 285) auto-answer-event( 40) }

DEFINITIONS ::=
BEGIN

IMPORTS

-- Data Types --
SubjectDeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

AutoAnswerEvent ::= SEQUENCE
{	invokingDevice 			SubjectDeviceID,
	autoAnswerOn			BOOLEAN,
	numberOfRings			INTEGER					OPTIONAL,
	extensions 			CSTACommonArguments			OPTIONAL }

END -- of CSTA-auto-answer-event
