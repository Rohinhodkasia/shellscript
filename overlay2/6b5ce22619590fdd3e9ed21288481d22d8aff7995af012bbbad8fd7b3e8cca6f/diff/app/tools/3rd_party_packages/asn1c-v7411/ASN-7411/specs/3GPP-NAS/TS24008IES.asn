TS24008IES DEFINITIONS AUTOMATIC TAGS ::= BEGIN

-- Common types

/* 10.5.1.1 - Cell Identity */

CellIdentityValue ::= INTEGER (0..65535)

/* 10.5.1.2 - Ciphering Key Sequence Number */

/* 3-bit number.  Valid values are 0 thru 6.  7 is no key available */
CiphKeySeqNum ::= SEQUENCE {
   spare BOOLEAN, 
   value INTEGER(0..7)
}

TBCDString ::= IA5String (FROM ("0123456789#*abc"))

-- BCDString3 should be configured as <ctype>chararray</ctype>
TBCDString3 ::= TBCDString (SIZE(3))

-- MCC/MNC pair
MCCMNCPair ::= SEQUENCE {
   mcc TBCDString3, 
   mnc TBCDString3
}

--<ctype>chararray</ctype>
--<isTBCDString/>
IMSI ::= IA5String (FROM ("0123456789"))(SIZE (14..15))

--<ctype>chararray</ctype>
--<isTBCDString/>
IMEI ::= IA5String (FROM ("0123456789"))(SIZE (15))

--<ctype>chararray</ctype>
--<isTBCDString/>
IMEISV ::= IA5String (FROM ("0123456789"))(SIZE (16))

--<isGSMString/>
GSMString ::= PrintableString

/* 10.5.1.3 - Location Area Identification */

LocAreaIdent ::= SEQUENCE {
   mcc-mnc MCCMNCPair, 
   lac INTEGER (0..65535)
}

/* 10.5.1.4 - Mobile Identity */

MobileIdentity-TMGI ::= SEQUENCE {
   mbmsSessIdInd BOOLEAN,
   mccMncInd BOOLEAN,
   mbmsServiceID OCTET STRING (SIZE (3)), 
   mcc-mnc MCCMNCPair, 
   mbmsSessionID INTEGER(0..255)
}

MobileIdentity ::= CHOICE {
   imsi IMSI,
   imei IMEI,
   imeisv IMEISV, 
   tmsi OCTET STRING (SIZE (4)), 
   tmgi MobileIdentity-TMGI,
   /* When none is used, the identity digits shall be all zeros (as per 
      24.008. 10.5.1.4.)  The value of the none field indicates the length
      of the MobileIdentity IE, which is required to be 1 or 3.
   */
   none INTEGER(1|3)
}

/* 10.5.1.5 - Mobile Station Classmark 1 */

MobileStationClassmark1 ::= SEQUENCE {
   spare BOOLEAN, 
   revLevel INTEGER(0..3),  /* 0 = GSM phase 1, 
                               1 = GSM phase 2, 
                               2 = R99 or later */
   esInd BOOLEAN, 
   a5-1-alg BOOLEAN, 
   rfPowerCap INTEGER(0..7)
}

/* 10.5.1.6 - Mobile Station Classmark 2 */

MobileStationClassmark2 ::= SEQUENCE {
   /* octet 3 */
   cm1 MobileStationClassmark1 OPTIONAL,

   /* octet 4 */
   octet4 SEQUENCE {
      spare BOOLEAN, 
      psCapability BOOLEAN,  
      ssScreeningInd INTEGER(0..3),
      smCapability BOOLEAN,  
      vbsNotifRecept BOOLEAN,  
      vgcsNotifRecept BOOLEAN,  
      fcFreqCap BOOLEAN
   } OPTIONAL,

   /* octet 5 */
   octet5 SEQUENCE {
      cm3 BOOLEAN,  
      spare BOOLEAN, 
      lcsvaCap BOOLEAN,  
      ucs2Treatment BOOLEAN,  
      soLSA BOOLEAN,  
      cmsp BOOLEAN,  
      a5-3-alg BOOLEAN,  
      a5-2-alg BOOLEAN
   } OPTIONAL
}

/* 10.5.1.7 - Mobile Station Classmark 3 */
/*
< MS Measurement capability > ::=
	< SMS_VALUE : bit (4) >
	< SM_VALUE : bit (4) > ;
*/
MSMeasurementCap ::= SEQUENCE {
   smsValue INTEGER(0..15), 
   smValue  INTEGER(0..15)
}

-- Name has to begin with some uppercase letter.
Type8PSKStruct ::= SEQUENCE {
   modulationCap BOOLEAN,
   rfPowerCap1 INTEGER(0..3) OPTIONAL, 
   rfPowerCap2 INTEGER(0..3) OPTIONAL
}

GERANIuModeCap ::= SEQUENCE {
   --<is3GLength bitFieldSize="4" units="bits"/>
   length INTEGER (0..15), -- number of bits, may be padded
   floIuCap BOOLEAN, 
   --<inline/>
   --<length fixed-size="0"/>
   spareBits BIT STRING (SIZE (0..14))
}

/*
< A5 bits > ::= 
	< A5/7 : bit > < A5/6 : bit > < A5/5 : bit > < A5/4 : bit >  ;
*/
A5Bits ::= SEQUENCE {
   a5-7 BOOLEAN, 
   a5-6 BOOLEAN, 
   a5-5 BOOLEAN, 
   a5-4 BOOLEAN
}

/*
<R Support>::=
	< R-GSM band Associated Radio Capability : bit(3) > ;
*/
RSupport ::= INTEGER(0..7)

/*
< HSCSD Multi Slot Capability > ::=
	< HSCSD Multi Slot Class : bit(5) >  ;
*/
HSCSDMultiSlotCap ::= INTEGER(0..31)

-- This type enumerates all of the valid bit patterns expressed in the CSN
-- for the multibandSupported eleemnt in MobileStationClassmark3

MBSEnum ::= ENUMERATED { 
   mbs0(0), mbs1(1), mbs2(2), mbs4(4), mbs5(5), mbs6(6)
} 

-- MultibandSupported is defined as a separate type to allow a custom NAS
-- encode and decode function to be defined to support the following CSN:
/*
{	< Multiband supported : { 000 } >
		< A5 bits > 
|	< Multiband supported : { 101 | 110 } > 
		< A5 bits >
		< Associated Radio Capability 2 : bit(4) >
		< Associated Radio Capability 1 : bit(4) >
|	< Multiband supported : { 001 | 010 | 100 } > 
		< A5 bits >
		< spare bit >(4)
		< Associated Radio Capability 1 : bit(4) > }
*/
MultibandSupported ::= SEQUENCE {
   supported MBSEnum,
   a5bits A5Bits, 
   assocRadioCap2 INTEGER(0..15),
   assocRadioCap1 INTEGER(0..15)
}

/*
{       < T-GSM 400 Bands Supported : { 01 | 10 | 11 } >
	< T-GSM 400 Associated Radio Capability: bit(4) > }
*/
GSM400Struct ::= SEQUENCE { 
   bandsSupported ENUMERATED { band1(1), band2(2), band3(3) },
   assocRadioCap INTEGER (0..15)   
}

/*
{ 	< DTM GPRS Multi Slot Class : bit(2) >
	< Single Slot DTM : bit >
	{0 | 1 < DTM EGPRS Multi Slot Class : bit(2) > } } 
*/
DTMGPRSStruct ::= SEQUENCE {
   dtmGPRSMultiSlotClass INTEGER(0..3),
   singleSlotDTM BOOLEAN,
   dtmEGPRSMultiSlotClass INTEGER(0..3) OPTIONAL
} 

--<aligned/>
MobileStationClassmark3 ::= SEQUENCE {
   --<is3GLength/>
   length INTEGER (0..32), 
   spare BOOLEAN, 
   multiband MultibandSupported,
   /*
	{ 0 | 1 < R Support > }
	{ 0 | 1 < HSCSD Multi Slot Capability > }
	< UCS2 treatment: bit >
	< Extended Measurement Capability : bit >
	{ 0 | 1 < MS measurement capability > }
	{ 0 | 1 < MS Positioning Method Capability > }
	{ 0 | 1 < ECSD Multi Slot Capability > }
	{ 0 | 1 < 8-PSK Struct > }
   */
   rSupport RSupport OPTIONAL,
   hscsdMultiSlotCap HSCSDMultiSlotCap OPTIONAL,
   ucs2Treatment BOOLEAN,
   extMeasurementCap BOOLEAN,
   msMeasurementCap MSMeasurementCap OPTIONAL,
   msPositioningMethodCap INTEGER(0..31) OPTIONAL,
   ecsdMultiSlotCap INTEGER(0..31) OPTIONAL,
   an-8-PSKStruct Type8PSKStruct OPTIONAL,
   /*
	{ 0 | 1 < GSM 400 Struct >
   */
   gsm400Struct GSM400Struct OPTIONAL,
   /*
	{ 0 | 1 <GSM 850 Associated Radio Capability : bit(4) > }
	{ 0 | 1 <GSM 1900 Associated Radio Capability : bit(4) > }
	< UMTS FDD Radio Access Technology Capability : bit >
	< UMTS 3.84 Mcps TDD Radio Access Technology Capability : bit >
	< CDMA 2000 Radio Access Technology Capability : bit >
   */
   gsm850AssocRadioCap INTEGER(0..15) OPTIONAL,
   gsm1900AssocRadioCap INTEGER(0..15) OPTIONAL,
   umtsFDDRadioAccessTechCap BOOLEAN,
   umts384McpsTDDRadioAccessTechCap BOOLEAN,
   cdma2000RadioAccessTechCap BOOLEAN,
   /*
	{ 0 | 1	< DTM GPRS Struct > }
   */
   dtmGPRSStruct DTMGPRSStruct OPTIONAL,

   -- Release 4 starts here
   /*
	{ 0 | 1 < Single Band Support > }
	{ 0 | 1 <GSM 750 Associated Radio Capability : bit(4)>}
	< UMTS 1.28 Mcps TDD Radio Access Technology Capability : bit >
	< GERAN Feature Package 1 : bit >
   */
   singleBandSupport INTEGER(0..15) OPTIONAL,
   gsm750AssocRadioCap INTEGER(0..15) OPTIONAL,
   umts1-28McpsTDDRadioAccessTechCap BOOLEAN, 
   geranFeaturePackage1 BOOLEAN,
   /*
	{ 0 | 1 < Extended DTM GPRS Multi Slot Class : bit(2) >
		< Extended DTM EGPRS Multi Slot Class : bit(2) > }
   */
   extDtmGPRSStruct SEQUENCE {
      extDtmGPRSMultiSlotClass INTEGER(0..3),
      extDtmEGPRSMultiSlotClass INTEGER(0..3)
   } OPTIONAL,

   -- Release 5 starts here
   /*
	{ 0 | 1 < High Multislot Capability : bit(2) > }
	{ 0 | 1 < GERAN Iu Mode Capabilities > }
	< GERAN Feature Package 2 : bit >
	< GMSK Multislot Power Profile : bit (2) >
	< 8-PSK Multislot Power Profile : bit (2) >
   */
   highMultislotCap INTEGER(0..3) OPTIONAL,
   geranIuModeCap GERANIuModeCap OPTIONAL,
   geranFeaturePackage2 BOOLEAN,
   gmskMultislotPowerProfile INTEGER(0..3),
   multislotPowerProfile8PSK INTEGER(0..3),

   -- Release 6 starts here
   /*
	{ 0 | 1 < GSM 400 Struct >
   */
   tgsm400Struct GSM400Struct OPTIONAL,
   /* 
        0	The value '1' was allocated in an earlier version of the 
                protocol and shall not be used 
   */
   zerobit BOOLEAN DEFAULT FALSE,
   /*
	< Downlink Advanced Receiver Performance : bit (2)>
	< DTM Enhancements Capability : bit >
   */
   downlinkAdvancedRcvrPerf INTEGER(0..3),
   dtmEnhancementsCap BOOLEAN,
   /*
	{ 0 | 1	< DTM GPRS High Multi Slot Class : bit(3) >
		< Offset required : bit>
		{ 0 | 1 < DTM EGPRS High Multi Slot Class : bit(3) > } }
   */
   dtmGPRSStruct2 SEQUENCE {
      dtmGPRSHighMultiSlotClass INTEGER(0..7),
      offsetRequired BOOLEAN,
      dtmEGPRSHighMultiSlotClass INTEGER(0..7) OPTIONAL
   } OPTIONAL,
   /*
	< Repeated ACCH Capability : bit >
   */
   repeatedACCHCap BOOLEAN,
   /*
        -- Release 7 starts here
	{ 0 | 1 <GSM 710 Associated Radio Capability : bit(4)>}
	{ 0 | 1 <T-GSM 810 Associated Radio Capability : bit(4)>}
	< Ciphering Mode Setting Capability : bit >
	< Additional Positioning Capabilities : bit >
   */
   gsm710AssocRadioCap INTEGER(0..15) OPTIONAL,
   tgsm810AssocRadioCap INTEGER(0..15) OPTIONAL,
   cipheringModeSettingCap BOOLEAN,
   additionalPositioningCap BOOLEAN,
   /*
       	-- Release 8 starts here
	< E-UTRA FDD support : bit >
	< E-UTRA TDD support : bit >
	< E-UTRA Measurement and Reporting support : bit >
	< Priority-based reselection support : bit >
   */
   e-UTRA-FDD-support BOOLEAN,
   e-UTRA-TDD-support BOOLEAN,
   e-UTRA-MeasAndReportSupport BOOLEAN,
   priorityBasedReselectionSupport BOOLEAN,
   ...,
   /*
        -- Release 9 starts here
	< UTRA CSG Cells Reporting : bit >
	< VAMOS Level : bit(2) >
   */
   [[ 9:
   uTRA-CSG-Cells-Reporting BOOLEAN, 
   vAMOS-Level INTEGER (0..3)
   ]], 
   /*
	-- Release 10 starts here
	< TIGHTER Capability : bit(2) >
	< Selective Ciphering of Downlink SACCH : bit >
   */
   [[ 10:
   tighterCapability INTEGER (0..3), 
   selCiphOf-DL-SACCH BOOLEAN
   ]],
   /*
	-- Release 11 starts here
    < CS to PS SRVCC from GERAN to UTRA : bit(2) >
    < CS to PS SRVCC from GERAN to E-UTRA : bit(2)>
    < GERAN Network Sharing support : bit >
    < E-UTRA Wideband RSRQ measurements support : bit >
   */
   [[ 11:
   csToPsFromGeranToUtra INTEGER (0..3), 
   csToPsFromGeranToEUtra INTEGER (0..3), 
   geranNetShareSupport BOOLEAN,
   eutraWideRsrqSupport BOOLEAN
   ]],
   /*
	-- Release 12 starts here
    < ER Band Support : bit >
    < UTRA Multiple Frequency Band Indicators support : bit >
    < E-UTRA Multiple Frequency Band Indicators support: bit >
    < Extended TSC Set Capability support: bit >
    < Extended EARFCN value range : bit > -- Late addition of a rel11 feature
   */
   [[ 12:
   erBandSupport BOOLEAN, 
   utraMultFreqBandSupport BOOLEAN, 
   eutraMultFreqBandSupport BOOLEAN, 
   extTscSetCapSupport BOOLEAN,
   extEarfcnValRange BOOLEAN
   ]],
   spareBits BIT STRING
}

/* 10.5.1.9 - Descriptive group or broadcast call reference */

DescrGroupOrBcastCallRef ::= SEQUENCE {
   --binary code is a 27 bit value
   bc INTEGER(0..134217727),
   sf BOOLEAN,
   af BOOLEAN, 
   callPriority INTEGER(0..7),
   cipheringInformation INTEGER(0..15), 
   spare INTEGER(0..15) DEFAULT 0 -- should be set to 0
}

/* 10.5.1.10 - Group Cipher Key Number */
GroupCipherKeyNumber ::= INTEGER(0..15)

/* 10.5.1.10a - PD and SAPI $(CCBS)$ */
PDAndSAPI ::= SEQUENCE {
   spare INTEGER(0..3) DEFAULT 0, -- should be set to 0
   sapi  INTEGER(0..3),
   pd    INTEGER(0..15)
}

/* 10.5.1.11 - Priority Level */
PriorityLevel ::= SEQUENCE {
   spare BOOLEAN,
   callPriority INTEGER(0..7)
}

/* 10.5.1.12 - Core Network System Information (UMTS only) */
/* 10.5.1.12.1 - CN Common GSM-MAP NAS system information */

CNCommonGSM-MAPNASSystemInformation ::= INTEGER(0..65535)

/* 10.5.1.12.2 - CS domain specific system information */
CSDomainSpecificSystemInformation ::= SEQUENCE {
   t3212 INTEGER(0..255),
   spare INTEGER(0..127) DEFAULT 0, -- should be set to 0
   att   BOOLEAN
}

/* 10.5.1.12.3 - PS domain specific system information */
PSDomainSpecificSystemInformation ::= SEQUENCE {
   rac   INTEGER (0..255),
   spare INTEGER (0..63) DEFAULT 0, -- should be set to 0
   nmo1  BOOLEAN, 
   nmo   BOOLEAN
} 

/* 10.5.1.13 - PLMN list */
PLMNList ::= SEQUENCE (SIZE(1..15)) OF MCCMNCPair

/* 10.5.1.14 - NAS container for PS HO */
NASContainerForPSHO ::= SEQUENCE {
   spare1 INTEGER(0..7) DEFAULT 0, -- should be set to 0
   xid BOOLEAN,
   spare2 BOOLEAN DEFAULT FALSE, 
   typeCiphAlgorithm INTEGER(0..7),
   valueIOV-UI INTEGER(0..4294967295)
}

/* 10.5.1.15 - MS Network Feature Support */
MSNetFeatureSupport ::= SEQUENCE {
   spare INTEGER (0..7) DEFAULT 0, 
   extPeriodTimer BOOLEAN
}

/* 10.5.3.1 - Authentication parameter RAND */
AuthParamRAND ::= OCTET STRING (SIZE(16))

/* 10.5.3.1.1 - 
	Authentication Parameter AUTN (UMTS and EPS authentication challenge) */
AuthParamAUTN ::= SEQUENCE {
   --<is3GLength/>
   length INTEGER(0..255) DEFAULT 16, -- should be set to 16
   autn OCTET STRING (SIZE(16))
}

/* 10.5.3.2 - Authentication Response parameter */
AuthRespParam ::= OCTET STRING (SIZE(4))

/* 10.5.3.2.1 - 
   Authentication Response Parameter (extension)
   (UMTS authentication challenge only) */

AuthRespParamExt ::= OCTET STRING (SIZE(1..12))

/* 10.5.3.2.2 - 
   Authentication Failure parameter (UMTS and EPS authentication challenge) */
AuthFailureParam ::= SEQUENCE {
   --<is3GLength/>
   length INTEGER(0..255) DEFAULT 14, -- should be set to 14
   param OCTET STRING (SIZE(14))
}

/* 10.5.3.3 - CM service type */

CMServiceType ::= ENUMERATED {
   mobOrigCallEstab(1), emerCallEstab(2), sms(4), suplSvcActv(8), 
   voiceGrpCallEstab(9), voiceBcastCallEstab(10), locationSvcs(11)
} 

/* 10.5.3.4 - Identity type */

IdentityTypeValue ::= SEQUENCE {
   spare BOOLEAN DEFAULT FALSE, 
   typeOfIdent ENUMERATED { 
      imsi(1), imei(2), imeisv(3), tmsi(4), p-tmsi(5) 
   } 
}

/* 10.5.3.5 - Location updating type */
LocationUpdatingType ::= SEQUENCE {
   for BOOLEAN, -- Follow-on request pending
   spare BOOLEAN DEFAULT FALSE, 
   lut ENUMERATED { 
      normLocUpdate(0), periodicUpdate(1), imsiAttach(2), reserved(3)
   } 
} 

/* 10.5.3.5a - Network Name */
NetworkName ::= SEQUENCE {
   --<is3GLength/>
   length INTEGER (0..255),
   ext BOOLEAN DEFAULT TRUE, 
   codingScheme ENUMERATED { callBcastData(0), ucs2(1), codingSchemeMAX(7) },
   addCI BOOLEAN,
   numSpareBitsInLastOct INTEGER(0..7),
   --<inline/>
   textString CHOICE {
      --<selector element="codingScheme" value="0"/>
      --<length fixed-size="0" unusedBits="@numSpareBitsInLastOct"/>
      callBcastData GSMString, 
      --<selector element="codingScheme" value="1"/>
      ucs2 BMPString
   }
}

/* 10.5.3.6 - Reject cause */

RejectCauseValue ::= ENUMERATED {
   imsiUnkInHLR(2), illegalMS(3), imsiUnkInVLR(4), imeiNotAcc(5), 
   illegalME(6), plmnNotAllow(11), locNotAllow(12), roamNotAllow(13), 
   noCellsInLoc(15), networkFail(17), macFail(20), synchFail(21), 
   congestion(22), gsmAuthUnaccept(23), csgNotAuth(25), svcOptNotSupp(32), 
   notSubscribed(33), outOfOrder(34), callNotIdent(38), semIncorrectMsg(95), 
   invMandInfo(96), msgTypeNotExist(97), msgTypeNotCompat(98), 
   ieNotExist(99), condIEErr(100), msgNotCompat(101), protocolErr(111), 
   rejectCauseValueMAX(255)
} 

/* 10.5.3.7 - Follow-on Proceed: no value; IEI only */

/* 10.5.3.8 - Time Zone */

TimeZone ::= INTEGER(0..255)

/* 10.5.3.9 - Time Zone and Time */
TimeZoneAndTime ::= SEQUENCE {
   year INTEGER(0..255),
   month INTEGER(0..255),
   day INTEGER(0..255),
   hour INTEGER(0..255),
   minute INTEGER(0..255),
   second INTEGER(0..255),
   timezone INTEGER(0..255)
}

/* 10.5.3.10 - CTS permission: no value; IEI only */

/* 10.5.3.11 - LSA Identifier */
LSAIdentifier ::= OCTET STRING (SIZE(0|3))

/* 10.5.3.12 - Daylight Saving Time */
DaylightSavingTime ::= SEQUENCE {
   --<is3GLength/>
   length INTEGER (1),
   spare INTEGER (0..63) DEFAULT 0, -- should be set to 0
   dst   ENUMERATED { dstNoAdjust, dstPlus1, dstPlus2, dstReserved }
}

/* 10.5.3.13 - Emergency Number List */

/* If the emergency number contains an odd number of digits, 
   bits 5 to 8 of the last octet of the respective emergency 
   number (catValueOne or catValueTwo)
   shall be filled with an end mark coded as "1111". */

EmergencyNumber ::= SEQUENCE {
   --<is3GLength/>
   length INTEGER(0..255), 
   spare INTEGER(0..7) DEFAULT 0, 
   catValue INTEGER(0..31),
   -- digits is string of valid TBCD numbers (0-9, #, *, a, b, c)
   --<length fixed-size="0"/>
   digits TBCDString
}

-- Configured the following to use an array
EmergencyNumberList ::=  SEQUENCE {
   --<is3GLength/>
   length INTEGER (0..255), 
   --<is3GVarLenList lengthElem="length"/>
   --<storage>array</storage>
   numbers SEQUENCE (SIZE (1..10)) OF EmergencyNumber
}

/* 10.5.3.14 - Additional update parameters */

AddnUpdateParams ::= SEQUENCE {
   spare BOOLEAN DEFAULT FALSE,
   drvcc BOOLEAN, -- added in v15.3
   cmso  BOOLEAN, 
   cmst  BOOLEAN
}

/* 10.5.3.16 - MM Timer */

MMTimer ::= SEQUENCE {
   --<is3GLength/>
   length INTEGER (1), 
   value  INTEGER (0..255)
}

/* 10.5.4.1 - Extensions of codesets: informative only */
/* 10.5.4.2 - Locking shift procedure */
LockingShiftCodesetID ::= INTEGER(0..7)

/* 10.5.4.3 - Non-locking shift procedure */
NonLockingShiftCodesetID ::= INTEGER(0..7)

/* 10.5.4.4 - Auxiliary states */
AuxiliaryStates ::= SEQUENCE {
   ext BOOLEAN DEFAULT TRUE, 
   spare INTEGER(0..7) DEFAULT 0,
   holdAuxState INTEGER(0..3),
   multiPartyAuxState INTEGER(0..3)
}

/* 10.5.4.4a - Backup bearer capability */

BackupBearerCapability ::= SEQUENCE {
   --<is3GLength/>
   length INTEGER (0..255),
   --<first3GExtElem/>
   --<last3GExtElem/>
   octet3 BearerCapOctet3,
   --<first3GExtElem/>
   --<last3GExtElem/>
   octet4 BearerCapOctet4 OPTIONAL,
   --<first3GExtElem/>
   octet5 BearerCapOctet5 OPTIONAL,
   --<last3GExtElem/>   
   octet5a BearerCapOctet5a OPTIONAL,
   --<first3GExtElem/>
   octet6 BearerCapOctet6 OPTIONAL,
   octet6a BearerCapOctet6a OPTIONAL,
   octet6b BearerCapOctet6b OPTIONAL,
   octet6c BearerCapOctet6c OPTIONAL,
   octet6d BearerCapOctet6d OPTIONAL,
   octet6e BearerCapOctet6e OPTIONAL,
   octet6f BearerCapOctet6f OPTIONAL,
   --<last3GExtElem/>
   octet6g BearerCapOctet6g OPTIONAL,
   --<first3GExtElem/>
   --<last3GExtElem/>   
   octet7 BearerCapOctet7 OPTIONAL
}

InfoXferCap ::= ENUMERATED {
   speech(0), digital(1), audio(2), fax(3), otherITC(5), reserved(7)
}

BearerCapOctet3 ::= SEQUENCE {
   radioChannelRequirement INTEGER(0..3), /* 2 bits; always 1 */
   nonstandardCoding BOOLEAN, /* 0 - GSM */
   packetXferMode BOOLEAN, /* 0 - circuit mode */
   infoXferCap InfoXferCap  /* 3 bits */
}

BearerCapOctet4 ::= SEQUENCE {
   compression BOOLEAN,
   structure INTEGER(0..3),
   fullDuplexMode BOOLEAN,
   configuration BOOLEAN,
   nirr BOOLEAN,
   establishment BOOLEAN
}

BearerCapOctet5 ::= SEQUENCE {
   accessIdentity INTEGER(0..3), /* 2 bits; always 0 */
   rateAdaption INTEGER(0..3),  /* 2 bits */
   signallingAccessProtocol INTEGER(0..7) /* 3 bits; always 1 - I.440/450 */
}

BearerCapOctet5a ::= SEQUENCE {
   /* 2 bits; always 0 - restricted digital information */
   otherITC INTEGER(0..3), 
   otherRateAdaption INTEGER(0..3), /* 2 bits */
   spare INTEGER(0..7) DEFAULT 0
}


BearerCapOctet6 ::= SEQUENCE {
   layer1Identity INTEGER(0..3), /* 2 bits; always 1 - octet identifier */
   userInfoLayer1Protocol INTEGER(0..15), /* 4 bits; always 0 - default */
   asynchronous BOOLEAN /* 0 - synchronous */
}

BearerCapOctet6a ::= SEQUENCE {
   twoStopBits BOOLEAN, /* 0 - one stop bit */
   negotiation BOOLEAN, /* always 0 */
   data8bits BOOLEAN, /* 0 - 7 bits */
   userRate INTEGER(0..15) /* 4 bits */
}

BearerCapOctet6b ::= SEQUENCE {
   intermediateRate INTEGER(0..3), /* 2 bits */
   nicOnTX BOOLEAN,
   nicOnRX BOOLEAN,
   parity INTEGER(0..7) /* 3 bits */
}

BearerCapOctet6c ::= SEQUENCE {
   connectionElement INTEGER(0..3), /* 2 bits */
   modemType INTEGER(0..31) /* 5 bits */
}

BearerCapOctet6d ::= SEQUENCE {
   otherModemType INTEGER(0..3),/* 2 bits */
   fixedNetworkUserRate INTEGER(0..31) /* 5 bits */
}

BearerCapOctet6e ::= SEQUENCE {
   acceptableChannelCodings INTEGER(0..15), /* 4 bits; always 0 */
   maximumNumberOfTrafficChannels INTEGER(0..7) /* 3 bits; always 0 */
}

BearerCapOctet6f ::= SEQUENCE {
   uimi INTEGER(0..7), /* 3 bits */
   wantedAirInterfaceUserRate INTEGER(0..15) /* 4 bits; always 0 */
}

BearerCapOctet6g ::= SEQUENCE {
   acceptableChannelCodingsExtended INTEGER(0..7), /* 3 bits; always 0 */
   asymmetryIndication INTEGER(0..3), /* 2 bits; always 0 */
   spare INTEGER(0..3) DEFAULT 0
}


BearerCapOctet7 ::= SEQUENCE {
   layer2Identity INTEGER(0..3), /* 2 bits; always 2 - octet identifier */
   userInformationLayer2Protocol INTEGER(0..31) /* 5 bits */
}

BearerCapOctet3b ::= SEQUENCE {
   coding BOOLEAN,
   spare INTEGER (0..3) DEFAULT 0,
   speechVersion INTEGER (0..15)
}

BearerCapOctet5b ::= SEQUENCE {
   rateAdaptionHeader BOOLEAN,
   multipleFrameEstablishment BOOLEAN,
   protocolSensitiveMode BOOLEAN,
   fullProtocolNegotiation BOOLEAN,
   assignorOnly BOOLEAN,
   uiNegotiation BOOLEAN, 
   spare BOOLEAN DEFAULT FALSE
}

--<is3GExtList pre-eol="1"/>
BearerCapOctet3bList ::= SEQUENCE OF BearerCapOctet3b

/* 10.5.4.5 - Bearer capability */

BearerCapability ::= SEQUENCE {
   --<is3GLength/>
   length INTEGER (0..255),
   --<first3GExtElem/>
   octet3 BearerCapOctet3,
   octet3a BearerCapOctet3a OPTIONAL,
   --<last3GExtElem/>
   octet3b BearerCapOctet3bList,
   --<first3GExtElem/>
   --<last3GExtElem/>
   octet4 BearerCapOctet4 OPTIONAL,
   --<first3GExtElem/>
   octet5 BearerCapOctet5 OPTIONAL, 
   octet5a BearerCapOctet5a OPTIONAL,
   --<last3GExtElem/>
   octet5b BearerCapOctet5b OPTIONAL,
   --<first3GExtElem/>
   octet6 BearerCapOctet6 OPTIONAL,
   octet6a BearerCapOctet6a OPTIONAL,
   octet6b BearerCapOctet6b OPTIONAL,
   octet6c BearerCapOctet6c OPTIONAL,
   octet6d BearerCapOctet6d OPTIONAL,
   octet6e BearerCapOctet6e OPTIONAL,
   octet6f BearerCapOctet6f OPTIONAL,
   --<last3GExtElem/>
   octet6g BearerCapOctet6g OPTIONAL,
   --<first3GExtElem/>
   --<last3GExtElem/>   
   octet7 BearerCapOctet7 OPTIONAL
}

BearerCapOctet3a ::= SEQUENCE {
   coding BOOLEAN,
   ctm BOOLEAN,
   spare BOOLEAN DEFAULT FALSE, 
   speechVersion INTEGER (0..15) /* 4 bits */
}


/* 10.5.4.5a - Call Control Capabilities */
CallControlCapabilities ::= SEQUENCE {
   --<is3GLength/>
   length INTEGER (0..255) DEFAULT 2, 
   maxNumSupportedBearers INTEGER (0..15),
   mcat BOOLEAN,
   enicm BOOLEAN,
   pcp BOOLEAN,
   dtmf BOOLEAN,
   spare INTEGER (0..15) DEFAULT 0,
   maxNumSpeechBearers INTEGER (0..15)
}

/* 10.5.4.6 - Call state */
CodingStandard ::= ENUMERATED {
   q931, rsvdForIntl, national, stdDefForGSMPLMS
} 

CallState ::= SEQUENCE {
   codingStandard CodingStandard,
   callStateValue INTEGER (0..63)
}


/* 10.5.4.7 - Called party BCD number */
CalledPartyBCDNumber ::= SEQUENCE {
   --<is3GLength/>
   length INTEGER(0..255),
   --<first3GExtElem/>
   --<last3GExtElem/>
   octet3 SEQUENCE {
      typeOfNumber INTEGER (0..7),
      numberingPlanID INTEGER (0..15)
   },
   --<length fixed-size="0"/>
   number TBCDString
}

/* 10.5.4.8 - Called party subaddress */
PartySubaddress ::= SEQUENCE {
   --<is3GLength/>
   length INTEGER(0..255),
   --<first3GExtElem/>
   --<last3GExtElem/>
   octet3 SEQUENCE {
      typeOfSubaddr INTEGER (0..7),
      oddEvenIndicator BOOLEAN,
      spare INTEGER (0..7) DEFAULT 0
   } OPTIONAL,
   --<length fixed-size="0"/>
   subaddrInfo OCTET STRING (SIZE (0..20))
}

/* 10.5.4.9 - Calling party BCD number */
CallingPartyBCDNumber ::= SEQUENCE {
   --<is3GLength/>
   length INTEGER(0..255),
   --<first3GExtElem/>
   octet3 SEQUENCE {
      typeOfNumber INTEGER (0..7),
      numberingPlanID INTEGER (0..15)
   },
   --<last3GExtElem/>
   octet3a SEQUENCE {
      presentationIndicator INTEGER (0..3),
      spare INTEGER (0..7) DEFAULT 0,
      screeningIndicator INTEGER (0..3)
   } OPTIONAL,
   --<length fixed-size="0"/>
   number TBCDString
}

/* 10.5.4.11 - Cause */
Location ::= ENUMERATED {
   user(0), prvNWServLclUser(1), pubNWServLclUser(2), transit(3), 
   pubNWServRemUser(4), prvNWServRemUser(5), intlNetwork(7), 
   netBeyondIntworkPt(10)
} 

-- Cause value constants

unassignedCause INTEGER ::= 1
noRouteToDest INTEGER ::= 3
chanUnaccept INTEGER ::= 6
operDetBarring INTEGER ::= 8
callComplElsewhere INTEGER ::= 13
normCallClear INTEGER ::= 16
userBusy INTEGER ::= 17
noUserRespond INTEGER ::= 18
noAnswer INTEGER ::= 19
callRejected INTEGER ::= 21
numberChanged INTEGER ::= 22
callRejDestFeat INTEGER ::= 24
preemption INTEGER ::= 25
nonSelUserClr INTEGER ::= 26
destOutOfOrder INTEGER ::= 27
invNumberFmt INTEGER ::= 28
facilityReject INTEGER ::= 29
respToStatEnq INTEGER ::= 30
normalUnspec INTEGER ::= 31
noCircChanAvail INTEGER ::= 34
netOutOfOrder INTEGER ::= 38
tempFailure INTEGER ::= 41
swEquipCongest INTEGER ::= 42
accInfoDiscard INTEGER ::= 43
reqCircChanNotAvail INTEGER ::= 44
resourceUnavail INTEGER ::= 47
qosUnavail INTEGER ::= 49
reqFacNotSub INTEGER ::= 50
inCallsBarred INTEGER ::= 55
bearCapNotAuth INTEGER ::= 57
bearCapNotAvail INTEGER ::= 58
svcOptNotAvail INTEGER ::= 63
bearSvcNotImpl INTEGER ::= 65
acmEqOrGtMax INTEGER ::= 68
reqFacNotImpl INTEGER ::= 69
restDigInfoBearCap INTEGER ::= 70 
svcOptNotImpl INTEGER ::= 79
invTransId INTEGER ::= 81
userNotMemOfCUG INTEGER ::= 87 
incompatDest INTEGER ::= 88
invTransNetSel INTEGER ::= 91
semBadMsg INTEGER ::= 95
invMandInfo INTEGER ::= 96 
noMsgType INTEGER ::= 97
incompatMsgType INTEGER ::= 98
noInfoElem INTEGER ::= 99
condIEErr INTEGER ::= 100 
incompatMsg INTEGER ::= 101
recOnTimerExp INTEGER ::= 102
protocolErr INTEGER ::= 111
interworkErr INTEGER ::= 127

-- Custom encode/decode function is used to handle condition of recommendation
Cause ::= SEQUENCE {
   --<is3GLength/>
   length INTEGER (0..255),
   --<first3GExtElem/>
   octet3 SEQUENCE {
      codingStandard CodingStandard,
      spare BOOLEAN DEFAULT FALSE,
      location Location
   },
   --<last3GExtElem/>
   recommendation INTEGER (0..127) OPTIONAL,
   --<first3GExtElem/>
   --<last3GExtElem/>
   causeValue INTEGER (0..127),
   --<inline/>
   --<length fixed-size="0"/>
   diagnostics OCTET STRING (SIZE (0..32))
}

-- 10.5.4.11a CLIR suppression: IEI only
-- 10.5.4.11b CLIR invocation: IEI only

/* 10.5.4.12 - Congestion level */
CongestionLevel ::= INTEGER (0..15)

/* 10.5.4.13 - Connected number */
ConnectedNumber ::= CallingPartyBCDNumber

/* 10.5.4.14 - Connected subaddress */
ConnectedSubaddress ::= PartySubaddress

/* 10.5.4.15 - Facility */
Facility ::= OCTET STRING

/* 10.5.4.16 - High layer compatibility */
HighLayerCompatibility ::= SEQUENCE {
   --<is3GLength/>
   length INTEGER (0..255), 
   --<first3GExtElem/>
   --<last3GExtElem/>
   --<noPresentBit/>
   octet3 SEQUENCE {
      codingStandard CodingStandard,
      interpretation INTEGER (0..7),
      presentMethOfProtoProf INTEGER (0..3)
   } OPTIONAL,
   --<first3GExtElem/>
   --<noPresentBit/>
   highLayerCharacteristicsID INTEGER (0..127) OPTIONAL,
   --<last3GExtElem/>
   extHighLayerCharacteristicsID INTEGER (0..127) OPTIONAL
}

/* 10.5.4.17 - Keypad facility */
KeypadFacilityInfo ::= SEQUENCE {
   spare BOOLEAN DEFAULT FALSE, 
   value INTEGER (0..127)
}

/* 10.5.4.18 - Low layer compatibility */
LowLayerCompatibility ::= OCTET STRING (SIZE(0..16))
   
/* 10.5.4.19 - More data: IEI only */

/* 10.5.4.20 - Notification indicator */
NotificationIndicator ::= SEQUENCE {
   ext BOOLEAN DEFAULT TRUE,
   value INTEGER (0..127)
}

/* 10.5.4.21 - Progress indicator */
ProgressIndicator ::= SEQUENCE {
   --<is3GLength/>
   length INTEGER (0..255) DEFAULT 2, 
   --<first3GExtElem/>
   --<last3GExtElem/>
   octet3 SEQUENCE {
      codingStandard CodingStandard,
      spare BOOLEAN DEFAULT FALSE,
      location INTEGER (0..15)
   } ,
   --<first3GExtElem/>
   --<last3GExtElem/>
   description INTEGER (0..127)
}

-- 10.5.4.21a Recall type $(CCBS)$
RecallType ::= SEQUENCE {
   spare INTEGER (0..31) DEFAULT 0,
   value INTEGER(0..7)
}

/* 10.5.4.21b - Redirecting party BCD number */
RedirectingPartyBCDNumber ::= CallingPartyBCDNumber

/* 10.5.4.21c - Redirecting party subaddress */
RedirectingPartySubaddress ::= ConnectedSubaddress

/* 10.5.4.22 - Repeat indicator */
RepeatIndicator ::= INTEGER (0..15)

/* 10.5.4.22a - Reverse call setup direction: IEI only */

/* 10.5.4.22b - SETUP Container $(CCBS)$ */
Setup-Container ::= OCTET STRING

/* 10.5.4.23 - Signal */
Signal ::= INTEGER (0..255)

/* 10.5.4.24 - SS Version Indicator */
SSVersionIndicator ::= OCTET STRING

/* 10.5.4.25 - User-user */
UserUser ::= SEQUENCE {
   --<is3GLength/>
   length INTEGER (1..129), 
   uupd INTEGER(0..255),  /* User-user protocol discriminator */
   uuInfo OCTET STRING    /* User-user info */
}

/* 10.5.4.26 - Alerting Pattern $(NIA)$ */
AlertingPattern ::= SEQUENCE {
   --<is3GLength/>
   length INTEGER (1),
   spare  INTEGER (0..15) DEFAULT 0,
   value  INTEGER (0..15)
}

/* 10.5.4.27 - Allowed actions $(CCBS)$ */
AllowedActions ::= SEQUENCE {
   --<is3GLength/>
   length INTEGER (1),
   ccbs-activation BOOLEAN, 
   spare INTEGER (0..127) DEFAULT 0
}

/* 10.5.4.28 - Stream Identifier */
StreamIdentifierValue ::= SEQUENCE {
   --<is3GLength/>
   length INTEGER (1),
   value INTEGER (0..255)
}

/* 10.5.4.29 - Network Call Control Capabilities */
NetCallCtrlCaps ::= SEQUENCE {
   --<is3GLength/>
   length INTEGER (1),
   spare  INTEGER (0..127) DEFAULT 0, 
   mcs    BOOLEAN
}

/* 10.5.4.30 - Cause of No CLI */
CauseOfNoCLI ::= SEQUENCE {
   --<is3GLength/>
   length INTEGER (1),
   value INTEGER (0..255)
}

/* 10.5.4.32 - Supported codec list */
SupportedCodec ::= SEQUENCE {
   sysID INTEGER(0..255),
   codecBitmap OCTET STRING (SIZE(1..2))
}

SupportedCodecList ::= SEQUENCE {
   --<is3GLength/>
   length INTEGER (3..253), 
   --<is3GVarLenList lengthElem="length"/>
   --<storage>array</storage>
   codecs SEQUENCE (SIZE (1..83)) OF SupportedCodec
}

/* 10.5.4.33 Service category */
ServiceCategoryValue ::= SEQUENCE {
   spare BOOLEAN DEFAULT FALSE, 
   value INTEGER(0..127)
}

/* 10.5.4.34 - Redial: IEI only */
/* 10.5.4.35 - Network-initiated Service Upgrade indicator: IEI only */

/* 10.5.5.0 - Additional update type */
AddnUpdateType ::= SEQUENCE {
   spare INTEGER (0..7), 
   autv BOOLEAN
}

/* 10.5.5.1 - Attach result */
AttachResult ::= SEQUENCE {
   fop BOOLEAN,
   resultOfAttach INTEGER (0..7)
}

/* 10.5.5.2 - Attach type */
AttachType ::= SEQUENCE {
   for BOOLEAN,
   typeOfAttach INTEGER (0..7)
}

/* 10.5.5.3 - Ciphering algorithm */
CipheringAlgorithmType ::= SEQUENCE {
   spare BOOLEAN DEFAULT FALSE,
   value INTEGER (0..7)
}

/* 10.5.5.3a - Integrity algorithm */
IntegrityAlgorithmType ::= SEQUENCE {
   spare BOOLEAN DEFAULT FALSE,
   value INTEGER (0..7)
}

/* 10.5.5.4 - TMSI status */
TMSIStatus ::= SEQUENCE {
   spare INTEGER (0..7) DEFAULT 0,
   flag  BOOLEAN
}

/* 10.5.5.5 - Detach type */
DetachType ::= SEQUENCE {
   powerOff BOOLEAN,
   detachTypeValue INTEGER (0..7)
}

/* 10.5.5.6 - DRX parameter */
DRXParameter ::= SEQUENCE {
   splitPGCycleCode INTEGER(0..255),
   lenCoefAndValue INTEGER(0..15),
   splitOnCCCH BOOLEAN,
   nonDRXTimer INTEGER(0..7)
}

/* 10.5.5.7 - Force to standby */
ForceToStandbyValue ::= SEQUENCE {
   spare BOOLEAN DEFAULT FALSE,
   value INTEGER (0..7)
}

/* 10.5.5.8 - P-TMSI signature */
P-TMSISignature ::= SEQUENCE {
   value OCTET STRING (SIZE(3))
}

/* 10.5.5.8a - P-TMSI signature 2 */
P-TMSISignature2 ::= SEQUENCE {
   --<is3GLength/>
   length INTEGER (3) DEFAULT 3, 
   value OCTET STRING (SIZE(3))
}

/* 10.5.5.9 - Identity type 2 */
IdentityType2Value ::= IdentityTypeValue

/* 10.5.5.10 - IMEISV request */
IMEISVRequest ::= SEQUENCE {
   spare BOOLEAN DEFAULT FALSE,
   value INTEGER (0..7)
}

/* 10.5.5.11 - Receive N-PDU Numbers list */
ReceiveNPDUNumber ::= SEQUENCE {
   nsapi INTEGER (1..15),
   numberValue INTEGER (0..255)
}

--<aligned/>
ReceiveNPDUNumberList ::= SEQUENCE {
   --<is3GLength/>
   length INTEGER (2..255),
   --<is3GVarLenList lengthElem="length"/>
   --<cDecSrcFname>TS24008IESDec_ReceiveNPDUNumber.c</cDecSrcFname>
   receiveNPDUNumber SEQUENCE (SIZE (1..MAX)) OF ReceiveNPDUNumber
}

/* 10.5.5.12 - MS network capability */
--<aligned/>
MSNetworkCapability ::= SEQUENCE {
   --<is3GLength/>
   length INTEGER (0..8), 

   --<noPresentBit/>
   --<inline/>
   octet1 SEQUENCE {
      gea1 BOOLEAN,
      smCapDeicatedChan BOOLEAN,
      smCapGPRSChan BOOLEAN,
      ucs2Support BOOLEAN,
      ssScreeningInd INTEGER (0..3),
      soLSACap BOOLEAN,
      revisionLevelInd BOOLEAN
   } OPTIONAL, 

   --<noPresentBit/>
   --<inline/>
   octet2 SEQUENCE {
      pfcFeatureMode BOOLEAN,
      extendedGEA INTEGER (0..63),
      lcsVACap BOOLEAN
   } OPTIONAL, 

   --<noPresentBit/>
   --<inline/>
   octet3 SEQUENCE {
      psInterRATHOToUTRANIuModeCap BOOLEAN,
      psInterRATHOToEUTRANS1ModeCap BOOLEAN,
      emmCombinedProcCap BOOLEAN,
      isrSupport BOOLEAN,
      srvccToGERAN-UTRANCap BOOLEAN,
      epcCap BOOLEAN,
      -- added in release 9
      nfCapability BOOLEAN, 
      -- added in release 11
      geranNetShareCap BOOLEAN
   } OPTIONAL, 

   --<noPresentBit/>
   --<inline/>
   octet4 SEQUENCE {
      userPlaneIntegProtSupp BOOLEAN,
      gia-4 BOOLEAN,
      gia-5 BOOLEAN, 
      gia-6 BOOLEAN, 
      gia-7 BOOLEAN, 
      epcoIeIndicator BOOLEAN,
      restrictUseEnhancedCovCap BOOLEAN,
      dualConnEutraNRCap BOOLEAN
   } OPTIONAL, 

   -- spare bits used to pad out length > 4
   spareBits BIT STRING
}

/* 10.5.5.12a - MS Radio Access capability */

/* GMSK Multislot Power Profile (2 bit field)
   8-PSK Multislot Power Profile (2 bit field)
   For detailed definitions, see the Mobile Station Classmark 3 IE.
*/
MultislotCapability ::= SEQUENCE {
   hscsdMultiSlotClass INTEGER(0..31) OPTIONAL,
   gprsMSC SEQUENCE {
      gprsMultiSlotClass INTEGER(0..31),
      extGPRSDynAllocCap BOOLEAN
   } OPTIONAL,
   value-SMS-SM MSMeasurementCap OPTIONAL,
   ecsdMultiSlotClass INTEGER(0..31) OPTIONAL,
   egprsMSC SEQUENCE {
      egprsMultiSlotClass INTEGER(0..31),
      extEGPRSDynAllocCap BOOLEAN
   } OPTIONAL,
   /*
	{ 0 | 1	< DTM GPRS Struct > }
   */
   dtmGPRSStruct DTMGPRSStruct OPTIONAL
}

/*
< Enhanced Flexible Timeslot Assignment struct > ::=
	{ 0 | 1 	< Alternative EFTA Multislot Class : bit(4) > 
			< EFTA Multislot Capability Reduction for 
                          Downlink Dual Carrier: bit (3) > };
*/
EnhanFlexTimeSlotAssnStruct ::= SEQUENCE {
   alt-EFTA-MultislotClass INTEGER (0..15), 
   eFTA-Multislot-Cap-Reduct INTEGER (0..7) 
}

/*
< Additional access technologies struct > ::=
	< Access Technology Type : bit (4) >
	< GMSK Power Class : bit (3) >
	< 8PSK Power Class : bit (2) > ;
*/
AddAccessTechStruct ::= SEQUENCE {
   accessTechType INTEGER(0..15),
   powerClass-GMSK INTEGER(0..7),
   powerClass-8PSK INTEGER(0..3)
}

--<is3GExtList post-eol="0"/>
AddAccessTechStructList ::= SEQUENCE OF AddAccessTechStruct

AdditionalAccessTech ::= SEQUENCE {
   --<is3GLength bitFieldSize="7" units="bits"/>
   length INTEGER (0..127), 
   content AddAccessTechStructList,
   spareBits BIT STRING
}

/*
< Access capabilities struct > ::=
	< Length : bit (7) > -- length in bits of Content and spare bits
	<Access capabilities : <Content>> 
	<spare bits>** ; -- expands to the indicated length
			  -- may be used for future enhancements
*/
AccessCapability ::= SEQUENCE {
   --<is3GLength bitFieldSize="7" units="bits"/>
   length INTEGER (0..127), 

   -- Content
   rfPowerCap INTEGER(0..7),
   --<inline/>
   a5Bits SEQUENCE {
      a5-1 BOOLEAN, 
      a5-2 BOOLEAN, 
      a5-3 BOOLEAN, 
      a5-4 BOOLEAN, 
      a5-5 BOOLEAN, 
      a5-6 BOOLEAN, 
      a5-7 BOOLEAN
   } OPTIONAL,
   esInd BOOLEAN,
   ps BOOLEAN,
   vgcs BOOLEAN,
   vbs BOOLEAN,
   multislotCap MultislotCapability OPTIONAL,
   powerCap8PSK INTEGER(0..3) OPTIONAL,
   compactIMC BOOLEAN,
   revisionLevelInd BOOLEAN,
   umts-FDD-RATechCap BOOLEAN,
   umts-384-Mcps-TDD-RA-TechCap BOOLEAN,
   cdma-2000-RA-TechCap BOOLEAN,
   ..., 
   [[ 4:
   umts-128-Mcps-TDD-RA-TechCap BOOLEAN,
   geranFeaturePackage1 BOOLEAN,
   extGPRSMSC SEQUENCE {
      extDtmGPRSMultiSlotClass INTEGER(0..3),
      extDtmEGPRSMultiSlotClass INTEGER(0..3)
   } OPTIONAL,
   moduleBasedMSCSupp BOOLEAN
   ]],
   [[ 5:
   highMultislotCap INTEGER(0..3) OPTIONAL,
   geranIuModeCap GERANIuModeCap OPTIONAL,
   multislotPowerProfile-GMSK INTEGER(0..3),
   multislotPowerProfile-8PSK INTEGER(0..3)
   ]],
   [[ 6:
   multipleTBFCap BOOLEAN,
   downlinkAdvRecPerf INTEGER(0..3),
   extendedRMCMSCap BOOLEAN,
   dtmEnhancementsCap BOOLEAN,
   dtmGPRSHighMSC SEQUENCE {
      dtmGPRSHighMultiSlotClass INTEGER(0..7),
      dtmEGPRSHighMultiSlotClass INTEGER(0..7) OPTIONAL
   } OPTIONAL,
   psHandoverCap BOOLEAN
   ]],
   [[ 7:
   dtmHandoverCap BOOLEAN,
   downlinkDualCarrierCap SEQUENCE {
      mscReductForDownlinkDualCarrier INTEGER(0..3),
      downlinkDualCarrierForDtmCap BOOLEAN
   } OPTIONAL,
   flexibleTimeslotAssign BOOLEAN,
   gan-PS-HandoverCap BOOLEAN,
   rlcNonPersistentMode BOOLEAN,
   reducedLatencyCap BOOLEAN,
   uplinkEGPRS2 INTEGER(0..3),
   downlinkEGPRS2 INTEGER(0..3)
   ]],
   [[ 8:
   e-UTRA-FDD-Supp BOOLEAN,
   e-UTRA-TDD-Supp BOOLEAN,
   gERANToEUTRATransferMode INTEGER(0..3),
   priBasedReselectionSupp BOOLEAN
   ]],
   [[ 9:
   enhanFlexTimeSlotAssn EnhanFlexTimeSlotAssnStruct OPTIONAL, 
   upLayerPDUStartCapRLCUMInd BOOLEAN, 
   emstCapability BOOLEAN, 
   mttiCapability BOOLEAN, 
   utraCSGCellsReporting BOOLEAN,
   e-utraCSGCellsReporting BOOLEAN
   ]],
   [[ 10:
   dtrCapability BOOLEAN, 
   emsrCapability BOOLEAN, 
   fast-DL-Freq-Sw-Cap BOOLEAN, 
   tighterCapability BOOLEAN
   ]], 
   [[ 11:
   fanrCapability BOOLEAN, 
   ipaCapability BOOLEAN,
   geranNetShareSupp BOOLEAN, 
   eUTRA-WB-RSRQ-MeasSupp BOOLEAN
   -- NOTE: extEARFCNValRange in rel 12 is actually a rel 11 feature, 
   -- but there is no way to express in this extension group
   ]],
   [[ 12:
   uTRA-MultFreqBandIndSupp BOOLEAN, 
   e-UTRA-MultFreqBandIndSupp BOOLEAN, 
   dlmcCap DLMCCapability OPTIONAL, 
   extTSCSetCapSupp BOOLEAN, 
   extEARFCNValRange BOOLEAN -- used in rel 11
   ]], 
   [[ 13:
   ec-pchMonSupp ENUMERATED {
      pchSupported, 
      ecPchSupported, 
      pchAndEcPchSupported, 
      ec-pchMonReserved
   }
   ]], 
   [[ 14:
   msSyncAccuracy INTEGER(0..15) OPTIONAL,
   ecULCoverageEnhanceSupp BOOLEAN
   ]], 
   [[ 15:
   mtaAccessSecuritySupp BOOLEAN,
   ecPagingIndChanMonitorSupp BOOLEAN
   ]], 
   spareBits BIT STRING
}

-- < DLMC Capability struct > ::=
--	{ 0 | 1	< DLMC - Non-contiguous intra-band reception : bit(2) >
-- 			< DLMC - Inter-band reception : bit(1) > }
--	< DLMC - Maximum Bandwidth : bit(2) >
--	< DLMC - Maximum Number of Downlink Timeslots : bit(6) >
--	< DLMC - Maximum Number of Downlink Carriers : bit(3) > ;
DLMCNonContigIntraBandRecep ::= ENUMERATED {
   nonContigIntraBandRecepNotSupp, 
   band-EGSM-GSM850, 
   band-DCS1800-PCS1900, 
   band-EGSM-GSM850-DCS1800-PCS1900
}

DLMCCapability ::= SEQUENCE {
   --<inline/>
   dlmc SEQUENCE {
      nonContigIntraBandRecep DLMCNonContigIntraBandRecep, 
      interBandRecep BOOLEAN
   } OPTIONAL, 
   maxBandwidth ENUMERATED { bw5MHz, bw10MHz, bw15MHz, bw20MHz }, 
   maxNumDLTimeSlots INTEGER (0..63), 
   maxNumDLCarriers INTEGER (0..7) -- (n + 1) * 2
}

MSRACapValuePartStruct ::= SEQUENCE {
   accessTechType INTEGER(0..15),
   --<inline/>
   accessCapOrTech CHOICE {
      accessCapability AccessCapability,
      --<selector element="accessTechType" value="15"/>
      additionalAccessTech AdditionalAccessTech
   }  
}

--<aligned/>
MSRadioAccessCapability ::= SEQUENCE {
   --<is3GLength/>
   length INTEGER (0..50),
   firstRec MSRACapValuePartStruct, 
   --<inline/>
   --<is3GExtList post-eol="0"/>
   additionalRecs SEQUENCE OF MSRACapValuePartStruct
}
   
/* 10.5.5.14 - GMM cause */
GMMCauseValue ::= INTEGER (0..255)

/* 10.5.5.15 - Routing area identification */
RoutingAreaIdent ::= SEQUENCE {
   mcc-mnc MCCMNCPair, 
   lac INTEGER(0..65535),
   rac INTEGER (0..255)
}

-- 10.5.5.15a Routing area identification 2
RoutingAreaIdent2 ::= SEQUENCE {
   --<is3GLength/>
   length INTEGER (6), 
   value RoutingAreaIdent
}

/* 10.5.5.17 - Update result */
UpdateResult ::= SEQUENCE {
   fop BOOLEAN,
   value INTEGER (0..7)
}

/* 10.5.5.18 - Update type */
UpdateType ::= SEQUENCE {
   for BOOLEAN,
   value INTEGER (0..7)
}

/* 10.5.5.19 - A&C reference number */
AC-Reference-Number ::= INTEGER (0..15)

/* 10.5.5.20 - Service type */
ServiceType ::= SEQUENCE {
   spare BOOLEAN DEFAULT FALSE,
   value INTEGER (0..7)
}

/* 10.5.5.21 - Cell Notification: IEI only */

/* 10.5.5.22 - PS LCS Capability */
PS-LCSCapbility ::= SEQUENCE {
   --<is3GLength/>
   length INTEGER (2), 
   mta-E BOOLEAN,
   mta-R BOOLEAN,
   apc BOOLEAN,
   otd-A BOOLEAN,
   otd-B BOOLEAN,
   gps-A BOOLEAN,
   gps-B BOOLEAN,
   gps-C BOOLEAN,
   spare INTEGER (0..63) DEFAULT 0,
   motd BOOLEAN,
   mta-A BOOLEAN
}

/* 10.5.5.23 - Network feature support */
NetFeatureSupp ::= SEQUENCE {
   lcs-molr BOOLEAN,
   mbms BOOLEAN,
   imsVoPS BOOLEAN, 
   emcBS BOOLEAN 
}

/* 10.5.5.23A - Additional network feature support */
AddnNetFeatureSupport ::= SEQUENCE {
   --<is3GLength/>
   length INTEGER (1), 
   spare INTEGER (0..31) DEFAULT 0, 
   epco BOOLEAN, -- added in/before v15.3
   restrictEC BOOLEAN, -- added in/before v15.3
   gprs-sms BOOLEAN
}

/* 10.5.5.24 - Inter RAT information container */
InterRATInfoContainer ::= OCTET STRING (SIZE(1..248))

/* 10.5.5.25 - Requested MS information */
RequestedMSInfo ::= SEQUENCE {
   i-RAT BOOLEAN,
   i-RAT2 BOOLEAN, 
   spare INTEGER (0..3) DEFAULT 0
}

/* 10.5.5.26 - UE network capability */
UENetCapability ::= OCTET STRING (SIZE(2..5))

/* 10.5.5.27 - E-UTRAN inter RAT information container */
E-UTRANInterRATInfoContainer ::= OCTET STRING -- (SIZE(1..255))

/* 10.5.5.28 - Voice domain preference and UE's usage setting */
VoiceDomainPref ::= SEQUENCE {
   --<is3GLength/>
   length INTEGER (1), 
   spare  INTEGER (0..31) DEFAULT 0, 
   usUsageSetting BOOLEAN, -- TRUE = voice, FALSE = data
   enumValue ENUMERATED {
      csVoiceOnly(0), imsPsVoiceOnly(1), csVoicePref(2), imsPsVoicePref(3)
   }
}

/* 10.5.5.29 - P-TMSI type */
P-TMSI-Type ::= SEQUENCE {
   spare INTEGER (0..7) DEFAULT 0, 
   p-tmsi-type BOOLEAN
}

/* 10.5.5.30 - Location Area Identification 2 */
LocAreaIdent2 ::= SEQUENCE {
   --<is3GLength/>
   length INTEGER (5), 
   value LocAreaIdent
}

/* 10.5.5.31 - Network Resource Indentifier Container */
NetResourceIdentContainer ::= SEQUENCE {
   --<is3GLength/>
   length INTEGER (2), 
   nriContValue INTEGER (0..1023), 
   spare INTEGER (0..63) DEFAULT 0
}

/* 10.5.5.32 - Extended DRX parameters */
ExtDRXParams ::= SEQUENCE {
   --<is3GLength/>
   length INTEGER (1), 
   pagingTimeWindow INTEGER (0..16), 
   eDRXValue INTEGER (0..16)
}

/* 10.5.5.33 - Message authentication code */
MsgAuthCode ::= OCTET STRING

/* 10.5.5.34 - User plane integrity indicator */
UserPlaneIntegInd ::= SEQUENCE {
   spare4 BOOLEAN DEFAULT FALSE, 
   spare3 BOOLEAN DEFAULT FALSE, 
   spare2 BOOLEAN DEFAULT FALSE, 
   integInd BOOLEAN
}

/* 10.5.5.35 - DCN-ID */
DcnID ::= OCTET STRING(SIZE(2))

/* 10.5.5.36 - PLMN identity of the CN operator */
PlmnCnID ::= SEQUENCE {
   mcc-mnc MCCMNCPair
}

/* 10.5.5.37 - Non-3GPP NW provided policies */
Non3GPPNetPolicies ::= SEQUENCE {
   spare4 BOOLEAN DEFAULT FALSE, 
   spare3 BOOLEAN DEFAULT FALSE, 
   spare2 BOOLEAN DEFAULT FALSE, 
   emergencyNum BOOLEAN
}

/* 10.5.6.1 - Access point name */
--<ctype>chararray</ctype>
--<cDecFuncFname>TS24008IESDec_AccessPointName.c</cDecFuncFname>
--<cEncFuncFname>TS24008IESEnc_AccessPointName.c</cEncFuncFname>
AccessPointName ::= IA5String (SIZE(1..100))

/* 10.5.6.2 - Network service access point identifier */
NSAPIValue ::= SEQUENCE {
   spare INTEGER (0..15) DEFAULT 0,
   value INTEGER (0..15)
}

/* 10.5.6.3 - Protocol configuration options */

/* PCOUnit is used to describe both Protocol and Container fields */

PCOUnit ::= SEQUENCE {
   protocolID INTEGER (0..65535),
   contents OCTET STRING
}

/*
   The contents member of struct below may contain one or more
   PCOUnit structures.  These are used to represent both Protocol ID 
   and Container ID structures.
*/
ProtocolConfigOptions ::= SEQUENCE {
   --<is3GLength/>
   length INTEGER (1..253), 
   --<first3GExtElem/>
   --<last3GExtElem/>
   octet3 SEQUENCE {
      spare INTEGER (0..15) DEFAULT 0,
      configProtocol INTEGER (0..7)
   },
   --<is3GVarLenList lengthElem="length"/>
   pcoUnits SEQUENCE OF PCOUnit
}

ExtProtoConfigOptions ::= SEQUENCE {
   --<is3GLength bitFieldSize="16"/>
   length INTEGER (1..65532), 
   --<first3GExtElem/>
   --<last3GExtElem/>
   octet4 SEQUENCE {
      spare INTEGER (0..15) DEFAULT 0,
      configProtocol INTEGER (0..7)
   },
   --<is3GVarLenList lengthElem="length"/>
   pcoUnits SEQUENCE OF PCOUnit
}

/* 10.5.6.4 - Packet data protocol address */

/*
   PDP type organization field
   All other values are reserved.
*/

/*
   PDP type number field
   All other values are reserved.
*/

PacketDataProtoAddr ::= SEQUENCE {
   --<is3GLength/>
   length INTEGER (2..22), 
   spare INTEGER(0..15) DEFAULT 0, -- should be set to 0
   pdpTypeOrg INTEGER (0..15), /* PDP type organization */
   pdpTypeNum INTEGER (0..255), /* PDP type number */
   --<inline/>
   --<length fixed-size="0"/>
   addressInfo OCTET STRING (SIZE(0..20)) /* Address information */
}

/* 10.5.6.5 - Quality of service */

QualityOfService ::= SEQUENCE {
   --<is3GLength/>
   length INTEGER (4..255), 
   spare1 INTEGER (0..3) DEFAULT 0,
   delayClass INTEGER (0..7),
   reliabilityClass INTEGER (0..7),
   peakThroughput INTEGER (0..15),
   spare2 INTEGER (0..1) DEFAULT 0,
   precedenceClass INTEGER (0..7),
   spare3 INTEGER (0..7) DEFAULT 0,
   meanThroughput INTEGER (0..31),
   trafficClass INTEGER (0..7),
   deliveryOrder INTEGER (0..3),
   deliveryErroneousSDU INTEGER (0..7),
   maxSDUSize INTEGER (0..255),
   maxUplinkBR INTEGER (0..255), /* BR = Bit rate */
   maxDownlinkBR INTEGER (0..255),
   residualBER INTEGER (0..15), /* BER = Bit error rate */
   sduErrorRatio INTEGER (0..15),
   transferDelay INTEGER (0..63),
   trafficHandlingPrio INTEGER (0..3),
   guaranteedUplinkBR INTEGER (0..255),
   guaranteedDownlinkBR INTEGER (0..255),
   spare4 INTEGER (0..7) DEFAULT 0,
   signallingIndication BOOLEAN,
   sourceStatsDescriptor INTEGER (0..15),
   --<is3GVarLenList lengthElem="length"/>
   --<storage>array</storage>
   extBitRate SEQUENCE (SIZE (0..8)) OF INTEGER (0..255)
   -- Extension bit rate values, up to 8 can be specified as follows:
   --   0 : max downlink bitrate
   --   1 : guaranteed downlink bitrate
   --   2 : max uplink bitrate
   --   3 : guaranteed uplink bitrate
   --   4 : max downlink bitrate (extension 2)
   --   5 : guaranteed downlink bitrate (extension 2)
   --   6 : max uplink bitrate (extension 2)
   --   7 : guaranteed uplink bitrate (extension 2)
}

/* 10.5.6.5A - Re-attempt indicator */
ReattemptInd ::= SEQUENCE {
   --<is3GLength/>
   length INTEGER (1), 
   spare8 BOOLEAN, 
   spare7 BOOLEAN,
   spare6 BOOLEAN,
   spare5 BOOLEAN,
   spare4 BOOLEAN, 
   spare3 BOOLEAN,
   eplmNCValue BOOLEAN, 
   ratcValue BOOLEAN
}

/* 10.5.6.5B - Extended quality of service */
ExtQualityOfService ::= SEQUENCE {
   maxBRUnit INTEGER (0..255), /* BR = Bit rate */
   maxUplinkBR INTEGER (0..65535),
   maxDownlinkBR INTEGER (0..65535),
   guaranteedBRUnit INTEGER (0..255),
   guaranteedUplinkBR INTEGER (0..65535),
   guaranteedDownlinkBR INTEGER (0..65535)
}

/* 10.5.6.6 - SM cause */
SMCauseValue ::= INTEGER(0..255)

-- 10.5.6.6A SM cause 2
SMCause2Value ::= SMCauseValue

/* 10.5.6.7 - Linked TI */
--<cDecFuncFname>TS24008IESDec_LinkedTI.c</cDecFuncFname>
--<cEncFuncFname>TS24008IESEnc_LinkedTI.c</cEncFuncFname>
LinkedTI ::= SEQUENCE {
   flag  BOOLEAN,
   value INTEGER (0..7),
   spare INTEGER (0..15) DEFAULT 0
}

/* 10.5.6.9 - LLC service access point identifier */
LLCSAPIValue ::= SEQUENCE {
   spare    INTEGER (0..15) DEFAULT 0,
   value    INTEGER (0..15)
}

/* 10.5.6.10 - Tear down indicator */
TDIValue ::= SEQUENCE {
   spare INTEGER (0..7) DEFAULT 0,
   tdiFlag BOOLEAN
}

/* 10.5.6.11 - Packet Flow Identifier */
PacketFlowIdentValue ::= SEQUENCE {
   --<is3GLength/>
   length INTEGER (1),
   spare BOOLEAN DEFAULT FALSE,
   value INTEGER (0..127)
}

/* 10.5.6.12 - Traffic Flow Template */
TFTOctet1 ::= SEQUENCE {
   tftOperationCode ENUMERATED {
      ignoreThisIE(0), createTFT(1), deleteTFT(2), addPktFilters(3), 
      replPktFilters(4), delPktFilters(5), noTFTOp(6)
   } ,
   eBit BOOLEAN,
   numPacketFilters INTEGER (0..15)
}

TFTPacketFilterItem ::= SEQUENCE { /* pf = packet filter */
   spare INTEGER (0..3),
   pfDirection INTEGER (0..3),
   pfIdentifier INTEGER (0..15),
   pfEvaluationPrecedence INTEGER (0..255),
   contents OCTET STRING
}

TFTParam ::= SEQUENCE {
   paramIdentifier INTEGER (0..255),
   contents OCTET STRING
}

/*
   The contents member of the struct below may consist of a packet filter
   list followed by a parameter list.

   The format of the packet filter list depends on the tftOperationCode
   field.  If the operation is "delete packet filters" (0x05), then the
   packet filter list will just be a seqence of packet filter identifiers
   (one octet each).

   If, however, the operation is "create new TFT" (0x01), "add packet filters
   to existing TFT" (0x03), or "replace packet filters in existing TFT"
   (0x04), then the packet filter list will be one or more of the
   TFTPacketFilterItem structs.

   The parameter list consists of one or more of the TFTParam
   structures.
*/
TFT ::= SEQUENCE {
   --<is3GLength/>
   length INTEGER (1..255), 
   octet1 TFTOctet1,

   -- choice alternatives below are based on tftOperationCode value
   -- if operation is delete, identifiers alternative is selected
   -- if operation is create, add, or replace, filter item list is used
   --<inline/>
   packetFilterList CHOICE {
      --<selector element="octet1.tftOperationCode" value="5"/>
      identifiers OCTET STRING, -- each identifer is one octet in length
      filterItems SEQUENCE OF TFTPacketFilterItem
   } ,

   --<inline/>
   paramList SEQUENCE OF TFTParam
}

/* 10.5.6.13 - Temporary Mobile Group Identity (TMGI) */

TMGI ::= SEQUENCE {
   mbmsServiceID OCTET STRING (SIZE(3)),
   mcc-mnc MCCMNCPair
}

/* 10.5.6.14 - MBMS bearer capabilities */
MBMSBearerCaps ::= SEQUENCE {
   maxDownlinkBR INTEGER (0..255), /* BR = bit rate */
   maxDownlinkBRExt INTEGER (0..255)
}

/* 10.5.6.15 - MBMS protocol configuration options */
MBMS-PCO ::= OCTET STRING

/* 10.5.6.16 - Enhanced network service access point identifier */
EnhancedNSAPIValue ::= INTEGER(0..255)

/* 10.5.6.17 - Request type */
RequestTypeValue ::= SEQUENCE {
    spare BOOLEAN DEFAULT FALSE, 
    value INTEGER (0..7)
}

/* 10.5.6.18 - Session management notification indicator */
SM-NotificationIndicator ::= OCTET STRING (SIZE (1))

/* 10.5.6.19 - Connectivity type */
ConnectivityType ::= INTEGER (0..15)

/* 10.5.6.20 - WLAN offload acceptability */
WLANOffloadAccept ::= SEQUENCE {
   spare1 BOOLEAN, 
   spare2 BOOLEAN, 
   uTranOffloadAcceptValue BOOLEAN, 
   e-UTranOffloadAcceptValue BOOLEAN
}

/* 10.5.6.21 - NBIFOM container */
NBIFOMContainer ::= OCTET STRING

/* 10.5.7.1 - PDP context status */
PDPContextStatus ::= SEQUENCE {
   --<is3GLength/>
   length INTEGER (0..255) DEFAULT 2, 
   value OCTET STRING (SIZE(2))
}

/* 10.5.7.2 - Radio priority */
RadioPriorityValue ::= ENUMERATED {
   priorityLevel1(1), 
   priorityLevel2(2), 
   priorityLevel3(3), 
   priorityLevel4(4), 
   radioPriorityValueMAX(15)
}

/* 10.5.7.3 - GPRS Timer */
GPRSTimer ::= SEQUENCE {
   unit INTEGER (0..7),
   timerValue INTEGER (0..31)
}

/* 10.5.7.4 - GPRS Timer 2 */
GPRSTimer2 ::= SEQUENCE {
   --<is3GLength/>
   length INTEGER (1),
   value INTEGER(0..255)
}

/* 10.5.7.4a - GPRS Timer 3 */
GPRSTimer3 ::= SEQUENCE {
   --<is3GLength/>
   length INTEGER (1),
   unit ENUMERATED {
      valIncrMult10Mins(0), 
      valIncrMult1Hr(1), 
      valIncrMult10hrs(2), 
      valIncrMult2Secs(3), 
      valIncrMult30Secs(4), 
      valIncrMult1Min(5), 
      valIncrMult320Hrs(6), 
      timerDeact(7)
   },
   timerValue INTEGER (0..31)
}

/* 10.5.7.5 - Radio priority 2 */
RadioPriorityValue2 ::= RadioPriorityValue

/* 10.5.7.6 - MBMS context status */
MBMSContextStatus ::= OCTET STRING (SIZE(0..16))

/* 10.5.7.7 - Uplink data status */
UplinkDataStatus ::= SEQUENCE {
   --<is3GLength/>
   length INTEGER (2) DEFAULT 2,
   value OCTET STRING (SIZE(2))
}

/* 10.5.7.8 - Device properties */

DeviceProperties ::= SEQUENCE {
   spare INTEGER (0..7) DEFAULT 0, 
   lowPriority BOOLEAN
}

END
