-- This file was generated by the Objective Systems ASN1C Compiler
-- (http://www.obj-sys.com).  Version: 6.8.A, Date: 18-Nov-2014.

ULP-Version-3-message-extensions DEFINITIONS AUTOMATIC TAGS ::= BEGIN

IMPORTS

Ver, QoP, FQDN, SessionID
FROM ULP-Components 

PosProtocolVersion3GPP, PosProtocolVersion3GPP2
FROM ULP-Version-2-parameter-extensions 

PosProtocolVersionOMA
FROM ULP-Version-3-parameter-extensions 

PosPayLoad
FROM SUPL-POS 

Notification
FROM SUPL-INIT 

NotificationResponse
FROM SUPL-NOTIFY-RESPONSE 

maxnumSessions, SessionList
FROM SUPL-REPORT 

OMA-LPPe-RelativeLocation, OMA-LPPe-ReferencePointUniqueID, 
   OMA-LPPeCivicLocation, OMA-LPPe-CivicLocation
FROM OMA-LPPE 

GeographicTargetArea, GeographicTargetAreaList, AreaIdList, maxAreaIdList
FROM SUPL-TRIGGERED-START ;

-- Productions

SupportedPosProtocols ::= BIT STRING  { lpp(0), lppe(1), tia-801(2) } (SIZE (1..8
   ))

SupportedProtocolVersions ::= SEQUENCE {
   posProtocolVersionLPP [0] PosProtocolVersion3GPP OPTIONAL,
   posProtocolVersionLPPe [1] PosProtocolVersionOMA OPTIONAL,
   posProtocolVersionTIA801 [2] PosProtocolVersion3GPP2 OPTIONAL,
   ...
}

QoPCapabilities ::= SEQUENCE {
   highQualityPositionRX [0] BOOLEAN,
   highQualityPositionTX [1] BOOLEAN,
   highQualityVelocityRX [2] BOOLEAN,
   highQualityVelocityTX [3] BOOLEAN,
   ...
}

CivicPositioningCapabilities ::= SEQUENCE {
   positioningAbsoluteCivicAddress [0] BOOLEAN,
   ...
}

RelativePositioningCapabilities ::= SEQUENCE {
   positioningRelativeToReferencePoint [0] BOOLEAN,
   ...
}

LocationURICapabilities ::= SEQUENCE {
   locationURISupport [0] BOOLEAN,
   ...
}

SLPCapabilities ::= SEQUENCE {
   supportedPosProtocols [0] SupportedPosProtocols,
   supportedProtocolVersions [1] SupportedProtocolVersions,
   qoPCapabilities [2] QoPCapabilities OPTIONAL,
   civicPositioningCapabilities [3] CivicPositioningCapabilities OPTIONAL,
   relativePositioningCapabilities [4] RelativePositioningCapabilities OPTIONAL
      ,
   locationURICapabilities [5] LocationURICapabilities OPTIONAL,
   ...
}

MessageCountDuration ::= SEQUENCE {
   numUplinkMessages [0] INTEGER (1..4096) OPTIONAL,
   numDownlinkMessages [1] INTEGER (1..4096) OPTIONAL,
   numTotalMessages [2] INTEGER (1..8192) OPTIONAL,
   ...
}

Duration ::= SEQUENCE {
   timeDuration [0] INTEGER (1..44640) OPTIONAL,
   messageCountDuration [1] MessageCountDuration OPTIONAL,
   ...
}

GSSParameters ::= SEQUENCE {
   duration [0] Duration,
   ...
}

URI ::= VisibleString (FROM ("a".."z" | "A".."Z" | "0".."9" | ":" | "/" | "?" | "#" | "[" | "]" | "@" | "!" | "$" | "&" | "'" | "("
    | ")" | "*" | "+" | "," | ";" | "=" | "-" | "." | "_" | "~" | "%"))

ExtendedNotification ::= SEQUENCE {
   locationURI [0] URI OPTIONAL,
   ...
}

SLP-Address ::= SEQUENCE {
   fqdn [0] FQDN,
   ...
}

HighAccuracyQoP ::= SEQUENCE {
   horacc [0] INTEGER (0..255),
   veracc [1] INTEGER (0..255) OPTIONAL,
   maxLocAge [2] INTEGER (0..65535) OPTIONAL,
   delay [3] INTEGER (1..256) OPTIONAL,
   requestVelocity [4] BOOLEAN,
   ...
}

Ver3-SUPL-INIT-extension ::= SEQUENCE {
   sLPCapabilities [0] SLPCapabilities OPTIONAL,
   gSSParameters [1] GSSParameters OPTIONAL,
   extendedNotification [2] ExtendedNotification OPTIONAL,
   d-slp-Address [3] SLP-Address OPTIONAL,
   highAccuracyQoP [4] HighAccuracyQoP OPTIONAL,
   ...
}

LocationURIList ::= SEQUENCE (SIZE (1..maxLocationURI)) OF URI

LocationURIValidity ::= INTEGER (1..1440)

LocationURISet ::= SEQUENCE {
   locationURIList [0] LocationURIList,
   validity [1] LocationURIValidity,
   ...
}

LocationURIReason ::= ENUMERATED { emergencysession(0), h-SLP(1), undefined(2)
   , ... }

LocationURIRequest ::= SEQUENCE {
   reason [0] LocationURIReason,
   validity [1] LocationURIValidity,
   ...
}

SLP-Address-List ::= SEQUENCE (SIZE (1..maxSLP)) OF SLP-Address

D-SLP-Query ::= SEQUENCE {
   authorized-D-SLP-Address-List [0] SLP-Address-List OPTIONAL,
   preferred-D-SLP-Address-List [1] SLP-Address-List OPTIONAL,
   not-preferred-D-SLP-Address-List [2] SLP-Address-List OPTIONAL,
   qop [3] QoP OPTIONAL,
   ...
}

E-SLP-Query ::= SEQUENCE {
   authorized-E-SLP-Address-List [0] SLP-Address-List OPTIONAL,
   preferred-E-SLP-Address-List [1] SLP-Address-List OPTIONAL,
   not-preferred-E-SLP-Address-List [2] SLP-Address-List OPTIONAL,
   ...
}

SLPQuery ::= SEQUENCE {
   d-SLP-Query [0] D-SLP-Query OPTIONAL,
   e-SLP-Query [1] E-SLP-Query OPTIONAL,
   ...
}

EmergencyServicesIndication ::= SEQUENCE {
   ...
}

Ver3-SUPL-START-extension ::= SEQUENCE {
   gSSParameters [0] GSSParameters OPTIONAL,
   locationURISet [1] LocationURISet OPTIONAL,
   locationURIRequest [2] LocationURIRequest OPTIONAL,
   ver [3] Ver OPTIONAL,
   slpQuery [4] SLPQuery OPTIONAL,
   emergencyServicesIndication [5] EmergencyServicesIndication OPTIONAL,
   referencePointId [6] OMA-LPPe-ReferencePointUniqueID OPTIONAL,
   highAccuracyQoP [7] HighAccuracyQoP OPTIONAL,
   ...
}

Ver3-SUPL-RESPONSE-extension ::= SEQUENCE {
   sLPCapabilities [0] SLPCapabilities OPTIONAL,
   gSSParameters [1] GSSParameters OPTIONAL,
   relativePosition [2] OMA-LPPe-RelativeLocation OPTIONAL,
   civicPosition [3] OMA-LPPe-CivicLocation OPTIONAL,
   ...
}

Ver3-SUPL-POS-extension ::= SEQUENCE {
   more [0] BOOLEAN,
   end [1] BOOLEAN,
   ...
}

Ver3-SUPL-POS-INIT-extension ::= SEQUENCE {
   locationURISet [0] LocationURISet OPTIONAL,
   ...
}

ServiceDuration ::= INTEGER (1..1024)

ServiceArea ::= SEQUENCE {
   geographicArea [0] GeographicTargetAreaList,
   areaIdLists [1] SEQUENCE (SIZE (1..maxAreaIdList)) OF AreaIdList OPTIONAL,
   ...
}

MCC-MNC ::= SEQUENCE {
   mcc [0] SEQUENCE (SIZE (3)) OF INTEGER (0..9),
   mnc [1] SEQUENCE (SIZE (2..3)) OF INTEGER (0..9) OPTIONAL
}

SID-NID ::= SEQUENCE {
   sid [0] INTEGER (0..65535),
   nid [1] INTEGER (0..32767) OPTIONAL
}

Sector-ID ::= BIT STRING  (SIZE (128))

BSID ::= SEQUENCE {
   bsID-MSB [0] BIT STRING  (SIZE (24)),
   bsID-LSB [1] BIT STRING  (SIZE (24)) OPTIONAL
}

WLAN-ID ::= SEQUENCE {
   apMACAddress [0] BIT STRING  (SIZE (48)) OPTIONAL,
   ssid [1] OCTET STRING (SIZE (1..32)) OPTIONAL,
   ...
}

Fixed-Access ::= SEQUENCE {
   ipV4Address [0] BIT STRING  (SIZE (32)) OPTIONAL,
   ipV6Address [1] BIT STRING  (SIZE (128)) OPTIONAL,
   ...
}

AccessNetwork ::= CHOICE {
   gSMAccess [0] MCC-MNC,
   wCDMAAccess [1] MCC-MNC,
   lTEAccess [2] MCC-MNC,
   eHRPDAccess [3] MCC-MNC,
   cDMAAccess [4] SID-NID,
   hRPDAccess [5] Sector-ID,
   wiMaxAccess [6] BSID,
   wLANAccess [7] WLAN-ID,
   fixedAccess [8] Fixed-Access,
   ...
}

AccessNetworkList ::= SEQUENCE (SIZE (1..maxAccessNetwork)) OF AccessNetwork

CombinationType ::= ENUMERATED { and(0), or(1), conditional-or(2), ... }

D-SLP-Services ::= SEQUENCE {
   nI-SingleFix [0] BOOLEAN,
   nI-SessionInfoQuery [1] BOOLEAN,
   nI-TriggeredPeriodic [2] BOOLEAN,
   nI-TriggeredAreaEvent [3] BOOLEAN,
   nI-VelocityEvent [4] BOOLEAN,
   nI-RetrievalHistoricPosition [5] BOOLEAN,
   nI-GSS [6] BOOLEAN,
   sI-SingleFix [7] BOOLEAN,
   sI-SingleFixThirdParty [8] BOOLEAN,
   sI-SingleFixThirdPartyRelative [9] BOOLEAN,
   sI-SingleFixTransferThirdParty [10] BOOLEAN,
   sI-TriggeredPeriodic [11] BOOLEAN,
   sI-TriggeredAreaEvent [12] BOOLEAN,
   sI-VelocityEvent [13] BOOLEAN,
   sI-GSS [14] BOOLEAN,
   nI-LocationURIRequest [15] BOOLEAN,
   ...
}

Proxy-D-SLP ::= SEQUENCE {
   ...
}

D-SLP-Authorization ::= SEQUENCE {
   d-SLP-Address [0] SLP-Address,
   serviceDuration [1] ServiceDuration OPTIONAL,
   serviceArea [2] ServiceArea OPTIONAL,
   accessNetworkList [3] AccessNetworkList OPTIONAL,
   combinationtype [4] CombinationType OPTIONAL,
   services [5] D-SLP-Services OPTIONAL,
   proxy-d-slp [6] Proxy-D-SLP OPTIONAL,
   ...
}

D-SLP-List ::= SEQUENCE (SIZE (0..maxSLP)) OF D-SLP-Authorization

H-SLP-Access-Preference ::= ENUMERATED { no-access(0), access-not-preferred(1)
   , access-preferred(2), ... }

Report-D-SLP-Access ::= SEQUENCE {
   only-Notify-D-SLPs-Authorized-For-NI-Service [0] BOOLEAN,
   include-Proxy-D-SLP-Authorized-D-SLPs [1] BOOLEAN,
   ...
}

D-SLP-Authorization-List ::= SEQUENCE {
   d-slp-List [0] D-SLP-List,
   h-SLP-Access-Preference [1] H-SLP-Access-Preference OPTIONAL,
   report-D-SLP-Access [2] Report-D-SLP-Access OPTIONAL,
   ...
}

Proxy-E-SLP ::= SEQUENCE {
   ...
}

E-SLP-Authorization ::= SEQUENCE {
   e-SLP-Address [0] SLP-Address,
   serviceDuration [1] ServiceDuration OPTIONAL,
   serviceArea [2] GeographicTargetArea OPTIONAL,
   accessNetworkList [3] AccessNetworkList OPTIONAL,
   combinationType [4] CombinationType OPTIONAL,
   proxy-e-slp [5] Proxy-E-SLP OPTIONAL,
   ...
}

E-SLP-List ::= SEQUENCE (SIZE (0..maxSLP)) OF E-SLP-Authorization

E-SLP-Authorization-List ::= SEQUENCE {
   e-slp-List [0] E-SLP-List,
   ...
}

SLPAuthorization ::= SEQUENCE {
   d-SLP-Authorization-List [0] D-SLP-Authorization-List OPTIONAL,
   e-SLP-Authorization-List [1] E-SLP-Authorization-List OPTIONAL,
   minimum-retry-period [2] INTEGER (0..1440) OPTIONAL,
   ...
}

ModeAKeyEstablishment ::= SEQUENCE {
   modeAKeyIdentifier [0] OCTET STRING (SIZE (8)),
   temporaryModeAKeyIdentifier [1] OCTET STRING (SIZE (8)),
   sUPLINITROOTKEY [2] BIT STRING  (SIZE (128)),
   modeAKeyLifetime [3] UTCTime,
   ...
}

ModeAResynch ::= SEQUENCE {
   modeAKeyIdentifier [0] OCTET STRING (SIZE (8)),
   temporaryModeAKeyIdentifier [1] OCTET STRING (SIZE (8)),
   ...
}

SULPINITKeyResponse ::= CHOICE {
   modeAKeyEstablishment [0] ModeAKeyEstablishment,
   modeAResynch [1] ModeAResynch,
   ...
}

Ver3-SUPL-END-extension ::= SEQUENCE {
   locationURISet [0] LocationURISet OPTIONAL,
   slpAuthorization [1] SLPAuthorization OPTIONAL,
   relativePosition [2] OMA-LPPe-RelativeLocation OPTIONAL,
   civicPosition [3] OMA-LPPe-CivicLocation OPTIONAL,
   sULPINITKeyResponse [4] SULPINITKeyResponse OPTIONAL,
   ...
}

Ver3-SUPL-TRIGGERED-START-extension ::= SEQUENCE {
   posPayLoad [0] PosPayLoad,
   referencePointId [1] OMA-LPPe-ReferencePointUniqueID OPTIONAL,
   highAccuracyQoP [2] HighAccuracyQoP OPTIONAL,
   ...
}

Ver3-SUPL-TRIGGERED-RESPONSE-extension ::= SEQUENCE {
   sLPCapabilities [0] SLPCapabilities OPTIONAL,
   ...
}

RequestType ::= ENUMERATED { stop(0), pause(1), resume(2), ... }

Ver3-SUPL-TRIGGERED-STOP-extension ::= SEQUENCE {
   requestType [0] RequestType OPTIONAL,
   endSessionList [1] SessionList OPTIONAL,
   slpAuthorization [2] SLPAuthorization OPTIONAL,
   ...
}

NotificationSession ::= SEQUENCE {
   sessionID [0] SessionID,
   notification [1] Notification,
   ...
}

Ver3-SUPL-NOTIFY-extension ::= SEQUENCE {
   notificationList [0] SEQUENCE (SIZE (1..maxnumSessions)) OF NotificationSession OPTIONAL,
   ...
}

NotificationRepSession ::= SEQUENCE {
   sessionID [0] SessionID,
   notificationResponse [1] NotificationResponse,
   ...
}

Ver3-SUPL-NOTIFY-RESPONSE-extension ::= SEQUENCE {
   notificationRepList [0] SEQUENCE (SIZE (1..maxnumSessions)) OF NotificationRepSession
       OPTIONAL,
   ...
}

ResultType ::= ENUMERATED { absoluteposition(0), 
   positionrelativetoreferencepoint(1), positionrelativetoSET(2), ... }

Ver3-SUPL-SET-INIT-extension ::= SEQUENCE {
   resultType [0] ResultType OPTIONAL,
   referencePointId [1] OMA-LPPe-ReferencePointUniqueID OPTIONAL,
   highAccuracyQoP [2] HighAccuracyQoP OPTIONAL,
   ...
}

Authorized-D-SLP ::= SEQUENCE {
   d-SLP-Address [0] SLP-Address,
   proxy-Authorized-D-SLP-List [1] SLP-Address-List OPTIONAL,
   ...
}

Authorized-D-SLP-List ::= SEQUENCE (SIZE (1..maxSLP)) OF Authorized-D-SLP

Authorized-E-SLP ::= SEQUENCE {
   e-SLP-Address [0] SLP-Address,
   proxy-Authorized-E-SLP-List [1] SLP-Address-List OPTIONAL,
   ...
}

Authorized-E-SLP-List ::= SEQUENCE (SIZE (1..maxSLP)) OF Authorized-E-SLP

D-SLP-Access-Notification ::= SEQUENCE {
   d-SLP-Address [0] SLP-Address,
   ...
}

Ver3-SUPL-REPORT-extension ::= SEQUENCE {
   pauseSessionList [0] SessionList OPTIONAL,
   authorized-D-SLP-List [1] Authorized-D-SLP-List OPTIONAL,
   authorized-E-SLP-List [2] Authorized-E-SLP-List OPTIONAL,
   d-slp-Access-Notification [3] D-SLP-Access-Notification OPTIONAL,
   relativePosition [4] OMA-LPPe-RelativeLocation OPTIONAL,
   civicPosition [5] OMA-LPPe-CivicLocation OPTIONAL,
   ...
}

-- Value assignments

maxLocationURI INTEGER ::= 5

maxSLP INTEGER ::= 10

maxArea INTEGER ::= 32

maxAccessNetwork INTEGER ::= 1024


END
