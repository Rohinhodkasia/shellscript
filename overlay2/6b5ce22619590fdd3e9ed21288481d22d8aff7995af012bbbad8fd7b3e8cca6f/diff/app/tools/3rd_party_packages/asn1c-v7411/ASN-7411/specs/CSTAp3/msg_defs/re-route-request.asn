CSTA-re-route-request 
	{ iso( 1) identified-organization( 3) icd-ecma( 12)
		standard( 0) csta3( 285) re-route-request( 82) }

DEFINITIONS ::=
BEGIN

IMPORTS
OPERATION, ERROR FROM Remote-Operations-Information-Objects 
	{joint-iso-itu-t remote-operations(4) informationObjects(5) version1(0) }

-- Data Types --
CorrelatorData, RouteRegisterReqID, RouteingCrossRefID 
FROM CSTA-device-feature-types
	{ iso( 1) identified-organization( 3) icd-ecma( 12)
		standard( 0) csta3( 285) device-feature-types( 127) }
CSTACommonArguments FROM CSTA-extension-types 
	{ iso( 1) identified-organization( 3) icd-ecma( 12)
		standard( 0) csta3( 285) extension-types( 129) }
CallLinkageData FROM CSTA-call-control 
	{ iso( 1) identified-organization( 3) icd-ecma( 12)
		standard( 0) csta3( 285) call-control( 130) }
universalFailure FROM CSTA-error-definition
	{ iso( 1) identified-organization( 3) icd-ecma( 12)
		standard( 0) csta3( 285) error-definition( 120) };

reRouteRequest OPERATION ::=
{	ARGUMENT		ReRouteRequestArgument
	ERRORS  		{universalFailure }
	ALWAYS RESPONDS		FALSE
	CODE			local: 32 }

ReRouteRequestArgument ::= SEQUENCE
{	crossRefIdentifier		RouteingCrossRefID,
	routeRegisterReqID 		[0] IMPLICIT RouteRegisterReqID		OPTIONAL,
	replyTimeout 			[1] IMPLICIT INTEGER 			OPTIONAL,
	correlatorData 			[2] IMPLICIT CorrelatorData 		OPTIONAL,
	callLinkageData			[3] IMPLICIT CallLinkageData		OPTIONAL,
	extensions 			CSTACommonArguments			OPTIONAL }

END  -- of CSTA-re-route-request
