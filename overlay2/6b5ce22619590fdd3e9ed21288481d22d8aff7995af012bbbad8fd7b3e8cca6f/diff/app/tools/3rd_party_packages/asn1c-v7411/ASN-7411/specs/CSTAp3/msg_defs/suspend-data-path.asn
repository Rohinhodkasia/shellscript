CSTA-suspend-data-path
	{ iso( 1) identified-organization( 3) icd-ecma( 12)
		standard( 0) csta3( 285) suspend-data-path( 115) }

DEFINITIONS ::=
BEGIN

IMPORTS	
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
IOCrossRefID, IORegisterReqID FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

suspendDataPath	OPERATION ::=
{	ARGUMENT		SuspendDataPathArgument
	RESULT			SuspendDataPathResult
	ERRORS			{universalFailure }
	CODE			local: 115 }

SuspendDataPathArgument ::= SEQUENCE
{	ioCrossRefID			IOCrossRefID,
	ioRegisterReqID			IORegisterReqID				OPTIONAL,
	extensions			CSTACommonArguments			OPTIONAL }

SuspendDataPathResult ::= CHOICE
{	extensions			CSTACommonArguments,
	noData				NULL }

END  -- of CSTA-suspend-data-path
