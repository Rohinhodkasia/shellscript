CSTA-error-definition
	{ iso( 1) identified-organization( 3) icd-ecma( 12)
		standard( 0) csta3( 285) error-definition( 120) }

DEFINITIONS ::=
BEGIN

EXPORTS
UniversalFailure, universalFailure, ErrorValue;

IMPORTS
ERROR FROM Remote-Operations-Information-Objects
	{joint-iso-itu-t remote-operations(4) informationObjects(5) version1(0) };

universalFailure ERROR ::=
{	PARAMETER 	UniversalFailure
	CODE 		local:1 }

ErrorValue ::= UniversalFailure

UniversalFailure ::= CHOICE
{ 	operation 				[0] OperationErrors,
	security 				[1] SecurityErrors,
	stateIncompatibility 			[2] StateIncompatibilityErrors,
	systemResourceAvailability 		[3] SystemResourceAvailabilityErrors,
	subscribedResourceAvailability 		[4] SubscribedResourceAvailabilityErrors,
	performanceManagement 			[5] PerformanceManagementErrors,
	privateData 				[6] PrivateDataInfoErrors,
	unspecified 				[7] UnspecifiedErrors }

OperationErrors ::= ENUMERATED -- in CSTA2 added in CSTA3
{ 	generic 					(  1),
	atLeastOneConditionalParameterNotProvided 	( 29),
	featureAlreadySet 				( 30),
	invalidMsgID 					( 25),
	invalidParameterValue 				( 31),
	invalidAccountCode 				( 21),
	invalidAgentGroup 				( 32),
	invalidAgentIdentifier 				( 33),
	invalidAgentPassword 				( 34),
	invalidAgentState 				( 35),
	invalidAlertTime 				( 36),
	invalidAllocationState 				( 16),
	invalidAuthCode 				( 22),
	invalidAutoAnswer 				( 37),
	invalidBitRate 					( 38),
	invalidButtonIdentifier 			( 39),
	invalidCallType 				( 42),
	invalidConnectionRate 				( 43),
	invalidConsultPurpose 				( 44),
	invalidCorrelatorData 				( 20),
	invalidCrossRefID 				( 17),
	invalidDelayTolerance 				( 45),
	invalidDestination 				( 14),
	invalidDestinationDetect 			( 46),
	invalidDoNotDisturb 				( 47),
	invalidEscapeCrossRefID 			( 48),
	invalidFeature 					( 15),
	invalidFile 					( 28),
	invalidFlowDirection 				( 49),
	invalidForwardingDestination 			(  7),
	invalidForwardingFlag 				( 51),
	invalidForwardingType 				( 52),
	invalidHookswitchType 				( 53),
	invalidHookswitchComponent 			( 54),
	invalidLampMode 				( 55),
	invalidLampID 					( 56),
	invalidMessageWaitingSetting 			( 57),
	invalidMicrophoneGain 				( 58),
	invalidMicrophoneMute 				( 59),
	invalidMonitorCrossRefID 			( 60),
	invalidMonitorFilter 				( 61),
	invalidMonitorObject 				( 62),
	invalidMonitorType 				( 63),
	invalidNumberOFChannels 			( 64),
	invalidParticipationType 			( 65),
	invalidRemainRetry 				( 66),
	invalidRingCount 				( 67),
	invalidRingPattern 				( 68),
	invalidRingVolume 				( 69),
	invalidRouteingAlgorithm 			( 70),
	invalidRouteingCrossRefID 			( 71),
	invalidRouteRegistrationCrossRefID 		( 72),
	invalidSpeakerVolume 				( 73),
	invalidSpeakerMute 				( 74),
	invalidSwitchingSubdomainCharsType 		( 75),
	invalidObjectType 				( 18),
	invalidActiveCallObject 			( 76),
	invalidCalledDeviceObjectType 			( 77),
	invalidCallingDeviceObjectType 			( 78),
	invalidCallToBePickedUpObjectType 		( 79),
	invalidCallToDivertObjectType 			( 80),
	invalidCallToParkObjectType 			( 81),
	invalidDestinationDeviceObject 			(195),
	invalidHeldCallObject 				( 82),
	invalidMonitorObjectType 			( 83),
	invalidParkToObjectType 			( 84),
	messageIDRequired 				( 26),
	notDifferentDevices 				( 85),
	notSameDevice 					( 86),
	objectNotKnown 					(  4),
	invalidCallID 					( 11),
	invalidActiveCallID 				( 87),
	invalidHeldCallID 				( 88),
	invalidConnectionID 				( 13),
	invalidActiveConnectionID 			( 89),
	invalidHeldConnectionID 			( 90),
	invalidDeviceID 				( 12),
	invalidActiveDeviceID 				( 91),
	invalidCalledDeviceID 				(  6),
	invalidCallingDeviceID 				(  5),
	invalidCallToParkDeviceID 			( 92),
	invalidDestinationDeviceID 			( 93),
	invalidDivertingDeviceID 			( 94),
	invalidHeldDeviceID 				( 95),
	invalidParkToDeviceID 				( 96),
	invalidPickUpDeviceID 				( 97),
	parameterNotSupported 				( 98),
	accountCodeNotSupported 			( 99),
	agentGroupNotSupported 				(100),
	agentPasswordNotSupported 			(101),
	agentStateNotSupported 				(102),
	alertTimeNotSupported 				(103),
	allocationNotSupported 				(104),
	authorisationCodeNotSupported 			(105),
	autoAnswerNotSupported 				(106),
	bitRateNotSupported 				(107),
	buttonNotSupported 				(108),
	callTypeNotSupported 				(109),
	charactersToSendNotSupported 			(110),
	connectionRateNotSupported 			(111),
	connectionReservationNotSupported 		(112),
	consultPurposeNotSupported 			(113),
	correlatorDataNotSupported 			(114),
	delayToleranceNotSupported 			(115),
	destinationDetectNotSupported 			(116),
	digitModeNotSupported 				(117),
	errorValueNotSupported 				(118),
	flowDirectionNotSupported 			(119),
	forwardingDestinationNotSupported 		(120),
	lampNotSupported 				(121),
	monitorTypeNotSupported 			(122),
	numberOfChannelsNotSupported 			(123),
	parameterTypeNotSupported 			(124),
	priorityNotSupported 				(125),
	privateDataNotSupported 			(126),
	pulseDurationNotSupported 			(127),
	pulseRateNotSupported 				(128),
	remainRetryNotSupported 			(129),
	ringCountNotSupported 				(130),
	routeUsedNotSupported 				(131),
	securityNotSupported 				(132),
	swSubdomainCCIETypeNotSupported 		(133),
	toneDurationNotSupported 			(134),
	sysStatRegIDNotSupported 			(135),
	userDataNotSupported 				(136),
	privilegeViolationSpecifiedDevice		(  8),
	privilegeViolationActiveDevice 			(137),
	privilegeViolationCalledDevice			(  9),
	privilegeViolationCallingDevice			( 10),
	privilegeViolationCallToParkDevice 		(138),
	privilegeViolationDestinationDevice 		(139),
	privilegeViolationOnDivertingDevice 		(140),
	privilegeViolationHeldDevice 			(141),
	privilegeViolationOnParkToDevice 		(142),
	privilegeViolationPickUpDevice 			(143),
	routeingTimerExpired 				(144),
	requestIncompatibleWithObject 			(  2),
	requestIncompatibleWithConnection 		(145),
	requestIncompatibleWithActiveConnection 	(146),
	requestIncompatibleWithHeldConnection 		(147),
	requestIncompatibleWithDevice 			(148),
	requestIncompatibleWithCalledDevice 		( 24),
	requestIncompatibleWithCallingDevice 		( 23),
	requestIncompatibleWithSubjectDevice 		(149),
	requestIncompatibleWithActiveDevice 		(150),
	requestIncompatibleWithCallToParkDevice 	(151),
	requestIncompatibleWithDestinationDevice 	(152),
	requestIncompatibleWithDivertingDevice 		(153),
	requestIncompatibleWithHeldDevice 		(154),
	requestIncompatibleWithMedia 			( 27),
	requestIncompatibleWithParkToDevice 		(155),
	requestIncompatibleWithPickupDevice 		(156),
	serviceNotSupported 				( 50),
	securityViolation 				( 19),
	valueOutOfRange 				(  3),
	agentStateOutOfRange 				(157),
	alertTimeOutOfRange 				(158),
	allocationOutOfRange 				(159),
	autoAnswerOutOfRange 				(160),
	bitRateOutOfRange 				(161),
	callTypeOutOfRange 				(162),
	connectionRateOutOfRange 			(163),
	connectionReservoationOutOfRange 		(164),
	consultPurposeOutOfRange 			(165),
	correlatorDataOutOfRange 			(166),
	delayToleranceOutOfRange 			(167),
	destinationDetectOutOfRange 			(168),
	digitModeOutOfRange 				(169),
	doNotDisturbOutOfRange 				(170),
	flowDirectionOutOfRange 			(171),
	forwardingFlagOutOfRange 			(172),
	forwardingTypeOutOfRange 			(173),
	hookswitchComponentOutOfRange 			(174),
	hookswitchTypeOutOfRange 			(175),
	lampModeOutOfRange 				(176),
	messageWaitingSettingOutOfRange 		(177),
	micGainOutOfRange 				(178),
	micMuteOutOfRange 				(179),
	monitorTypeOutOfRange 				(180),
	numberOfChannelsOutOfRange 			(181),
	participationTypeOutOfRange 			(182),
	pulseDurationOutOfRange 			(183),
	pulseRateOutOfRange 				(184),
	ringCountOutOfRange 				(185),
	ringPatternOutOfRange 				(186),
	ringVolumnOutOfRange 				(187),
	routeingAlgorithmOutOfRange 			(188),
	speakerMuteOutOfRange 				(189),
	speakerVolumeOutOfRange 			(190),
	switchingCcittTypeOutOfRange 			(191),
	systemStatusOutOfRange 				(192),
	toneCharacterOutOfRange 			(193),
	toneDurationOutOfRange 				(194) }

SecurityErrors ::= ENUMERATED
{ 	generic 					( 0),
	sequenceNumberViolated 				( 1),
	timeStampViolated 				( 2),
	securityInfoViolated 				( 4) }

StateIncompatibilityErrors ::= ENUMERATED
{ 	generic 					( 1),
	invalidObjectState 				( 2),
	invalidDeviceState 				(15),
	connectedCallExists 				(16),
	invalidActiveDeviceState 			(17),
	invalidCalledDeviceState 			(18),
	invalidCallingDeviceState 			(19),
	invalidCallToParkDeviceState 			(20),
	invalidDestinationDeviceState 			(21),
	invalidDivertingDeviceState 			(22),
	invalidHeldDeviceState 				(23),
	invalidParkToDeviceState 			(24),
	invalidConnectionState 				(25),
	invalidActiveConnectionState 			(26),
	invalidConnectionIDForActiveCall 		( 3),
	invalidHeldConnectionState 			(27),
	noActiveCall 					( 4),
	noCallToAnswer 					( 8),
	noCallToClear 					( 6),
	noCallToComplete 				( 9),
	noConnectionToClear 				( 7),
	noHeldCall 					( 5),
	incorrectMsgState 				(28),
	beginningOfMsg 					(13),
	endOfMsg 					(12),
	msgSuspended 					(14),
	notAbleToPlay 					(10),
	notAbleToResume 				(11) }

SystemResourceAvailabilityErrors ::= ENUMERATED
{ 	generic 					( 1),
	resourceBusy 					( 2),
	internalResourceBusy 				( 3),
	classifierBusy 					( 9),
	noMediaChannelsAvailable 			(10),
	channelsInUseForBridgedDevices 			(11),
	channelsInUseForData 				(12),
	toneDetectorBusy 				(13),
	toneGeneratorBusy 				(14),
	networkBusy 					( 5),
	resourceOutOfService 				( 4),
	deviceOutOfService 				(15),
	activeDeviceOutOfService 			(16),
	calledDeviceOutOfService 			(17),
	callingDeviceOutOfService 			(18),
	callToParkDeviceOutOfService 			(19),
	destinationDeviceOutOfService 			(20),
	divertingDeviceOutOfService 			(21),
	heldDeviceOutOfService 				(22),
	parkToDeviceOutOfService 			(23),
	pickupDeviceOutOfService 			(24),
	networkOutOfService 				( 6),
	otherResourceOutOfService 			(25),
	resourceLimitExceeded 				(26),
	overallMonitorLimitExceeded 			( 7),
	conferenceMemberLimitExceeded 			( 8),
	registrationLimitExceeded 			(27),
	conferenceResourceCannotBeSatisfied 		(28),
	maxDevicesExceeded				(29),
	startTimeOutOfRange				(30),
	durationExceeded				(31) }

SubscribedResourceAvailabilityErrors ::= ENUMERATED
{	generic 					( 1),
	objectMonitorLimitExceeded 			( 2),
	trunkLimitExceeded 				( 3),
	outstandingReqLimitExceeded 			( 4),
	objectRegistrationLimitExceeded 		( 5) }

PerformanceManagementErrors ::= ENUMERATED
{ 	generic 					( 1),
	performanceLimitExceeded 			( 2) }

PrivateDataInfoErrors ::= ENUMERATED
{ 	cSTAPrivateDataInfoError			( 1) }

UnspecifiedErrors ::= NULL

END -- of CSTA-error-definition
