CSTA-get-forwarding
	{ iso( 1) identified-organization( 3) icd-ecma( 12)
		standard( 0) csta3( 285) get-forwarding( 309) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
ForwardList FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) };

getForwarding OPERATION ::=
{	ARGUMENT 		GetForwardingArgument
	RESULT 			GetForwardingResult
	ERRORS 			{universalFailure }
	CODE			local: 309 }

GetForwardingArgument ::= SEQUENCE
{	device 				DeviceID,
	extensions			CSTACommonArguments 			OPTIONAL }

GetForwardingResult ::= SEQUENCE
{	forwardingList			ForwardList,
	extensions			CSTACommonArguments			OPTIONAL }

END -- of CSTA-get-forwarding
