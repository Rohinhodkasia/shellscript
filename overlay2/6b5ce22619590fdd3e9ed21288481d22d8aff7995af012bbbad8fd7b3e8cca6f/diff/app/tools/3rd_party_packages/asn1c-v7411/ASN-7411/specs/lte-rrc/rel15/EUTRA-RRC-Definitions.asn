-- This file was generated by the Objective Systems ASN1C Compiler
-- (http://www.obj-sys.com).  Version: 7.4.0.3, Date: 24-Mar-2020.

EUTRA-RRC-Definitions DEFINITIONS AUTOMATIC TAGS ::= BEGIN

-- Productions

PHICH-Config ::= SEQUENCE {
   phich-Duration [0] ENUMERATED { normal(0), extended(1) },
   phich-Resource [1] ENUMERATED { oneSixth(0), half(1), one(2), two(3) }
}

MasterInformationBlock ::= SEQUENCE {
   dl-Bandwidth [0] ENUMERATED { n6(0), n15(1), n25(2), n50(3), n75(4), n100(5)
       },
   phich-Config [1] PHICH-Config,
   systemFrameNumber [2] BIT STRING  (SIZE (8)),
   schedulingInfoSIB1-BR-r13 [3] INTEGER (0..31),
   systemInfoUnchanged-BR-r15 [4] BOOLEAN,
   spare [5] BIT STRING  (SIZE (4))
}

BCCH-BCH-MessageType ::= MasterInformationBlock

MasterInformationBlock-MBMS-r14 ::= SEQUENCE {
   dl-Bandwidth-MBMS-r14 [0] ENUMERATED { n6(0), n15(1), n25(2), n50(3), n75(4)
      , n100(5) },
   systemFrameNumber-r14 [1] BIT STRING  (SIZE (6)),
   additionalNonMBSFNSubframes-r14 [2] INTEGER (0..3),
   spare [3] BIT STRING  (SIZE (13))
}

BCCH-BCH-MessageType-MBMS-r14 ::= MasterInformationBlock-MBMS-r14

IMSI-Digit ::= INTEGER (0..9)

SCellGroupIndex-r15 ::= INTEGER (1..maxSCellGroups-r15)

ReestablishmentCause ::= ENUMERATED { reconfigurationFailure(0), 
   handoverFailure(1), otherFailure(2), spare1(3) }

ReleaseCause ::= ENUMERATED { loadBalancingTAUrequired(0), other(1), 
   cs-FallbackHighPriority-v1020(2), rrc-Suspend-v1320(3) }

EstablishmentCause ::= ENUMERATED { emergency(0), highPriorityAccess(1), 
   mt-Access(2), mo-Signalling(3), mo-Data(4), delayTolerantAccess-v1020(5), 
   mo-VoiceCall-v1280(6), spare1(7) }

EstablishmentCause-5GC ::= ENUMERATED { emergency(0), highPriorityAccess(1), 
   mt-Access(2), mo-Signalling(3), mo-Data(4), mo-VoiceCall(5), spare2(6), 
   spare1(7) }

ResumeCause ::= ENUMERATED { emergency(0), highPriorityAccess(1), mt-Access(2)
   , mo-Signalling(3), mo-Data(4), delayTolerantAccess-v1020(5), 
   mo-VoiceCall-v1280(6), spare1(7) }

ResumeCause-r15 ::= ENUMERATED { emergency(0), highPriorityAccess(1), 
   mt-Access(2), mo-Signalling(3), mo-Data(4), rna-Update(5), mo-VoiceCall(6), 
   spare1(7) }

SL-DestinationIdentity-r12 ::= BIT STRING  (SIZE (24))

AC-BarringConfig ::= SEQUENCE {
   ac-BarringFactor [0] ENUMERATED { p00(0), p05(1), p10(2), p15(3), p20(4), 
      p25(5), p30(6), p40(7), p50(8), p60(9), p70(10), p75(11), p80(12), 
      p85(13), p90(14), p95(15) },
   ac-BarringTime [1] ENUMERATED { s4(0), s8(1), s16(2), s32(3), s64(4), 
      s128(5), s256(6), s512(7) },
   ac-BarringForSpecialAC [2] BIT STRING  (SIZE (5))
}

PowerRampingParameters ::= SEQUENCE {
   powerRampingStep [0] ENUMERATED { dB0(0), dB2(1), dB4(2), dB6(3) },
   preambleInitialReceivedTargetPower [1] ENUMERATED { dBm-120(0), dBm-118(1), 
      dBm-116(2), dBm-114(3), dBm-112(4), dBm-110(5), dBm-108(6), dBm-106(7), 
      dBm-104(8), dBm-102(9), dBm-100(10), dBm-98(11), dBm-96(12), dBm-94(13), 
      dBm-92(14), dBm-90(15) }
}

PreambleTransMax ::= ENUMERATED { n3(0), n4(1), n5(2), n6(3), n7(4), n8(5), 
   n10(6), n20(7), n50(8), n100(9), n200(10) }

RACH-CE-LevelInfo-r13 ::= SEQUENCE {
   preambleMappingInfo-r13 [0] SEQUENCE {
      firstPreamble-r13 [0] INTEGER (0..63),
      lastPreamble-r13 [1] INTEGER (0..63)
   },
   ra-ResponseWindowSize-r13 [1] ENUMERATED { sf20(0), sf50(1), sf80(2), 
      sf120(3), sf180(4), sf240(5), sf320(6), sf400(7) },
   mac-ContentionResolutionTimer-r13 [2] ENUMERATED { sf80(0), sf100(1), 
      sf120(2), sf160(3), sf200(4), sf240(5), sf480(6), sf960(7) },
   rar-HoppingConfig-r13 [3] ENUMERATED { on(0), off(1) },
   ...,
   [[
      edt-Parameters-r15 [4] SEQUENCE {
         edt-LastPreamble-r15 [0] INTEGER (0..63),
         edt-SmallTBS-Enabled-r15 [1] BOOLEAN,
         edt-TBS-r15 [2] ENUMERATED { b328(0), b408(1), b504(2), b600(3), 
            b712(4), b808(5), b936(6), b1000or456(7) },
         mac-ContentionResolutionTimer-r15 [3] ENUMERATED { sf240(0), sf480(1)
            , sf960(2), sf1920(3), sf3840(4), sf5760(5), sf7680(6), sf10240(7)
             } OPTIONAL -- Need OP
      } OPTIONAL
   ]]
}

RACH-CE-LevelInfoList-r13 ::= SEQUENCE (SIZE (1..maxCE-Level-r13)) OF RACH-CE-LevelInfo-r13

RACH-ConfigCommon ::= SEQUENCE {
   preambleInfo [0] SEQUENCE {
      numberOfRA-Preambles [0] ENUMERATED { n4(0), n8(1), n12(2), n16(3), 
         n20(4), n24(5), n28(6), n32(7), n36(8), n40(9), n44(10), n48(11), 
         n52(12), n56(13), n60(14), n64(15) },
      preamblesGroupAConfig [1] SEQUENCE {
         sizeOfRA-PreamblesGroupA [0] ENUMERATED { n4(0), n8(1), n12(2), n16(3)
            , n20(4), n24(5), n28(6), n32(7), n36(8), n40(9), n44(10), n48(11)
            , n52(12), n56(13), n60(14) },
         messageSizeGroupA [1] ENUMERATED { b56(0), b144(1), b208(2), b256(3) }
            ,
         messagePowerOffsetGroupB [2] ENUMERATED { minusinfinity(0), dB0(1), 
            dB5(2), dB8(3), dB10(4), dB12(5), dB15(6), dB18(7) },
         ...
      } OPTIONAL -- Need OP
   },
   powerRampingParameters [1] PowerRampingParameters,
   ra-SupervisionInfo [2] SEQUENCE {
      preambleTransMax [0] PreambleTransMax,
      ra-ResponseWindowSize [1] ENUMERATED { sf2(0), sf3(1), sf4(2), sf5(3), 
         sf6(4), sf7(5), sf8(6), sf10(7) },
      mac-ContentionResolutionTimer [2] ENUMERATED { sf8(0), sf16(1), sf24(2), 
         sf32(3), sf40(4), sf48(5), sf56(6), sf64(7) }
   },
   maxHARQ-Msg3Tx [3] INTEGER (1..8),
   ...,
   [[
      preambleTransMax-CE-r13 [4] PreambleTransMax OPTIONAL,
      rach-CE-LevelInfoList-r13 [5] RACH-CE-LevelInfoList-r13 OPTIONAL
   ]],
   [[
      edt-SmallTBS-Subset-r15 [6] ENUMERATED { true(0) } OPTIONAL
   ]]
}

BCCH-Config ::= SEQUENCE {
   modificationPeriodCoeff [0] ENUMERATED { n2(0), n4(1), n8(2), n16(3) }
}

PCCH-Config ::= SEQUENCE {
   defaultPagingCycle [0] ENUMERATED { rf32(0), rf64(1), rf128(2), rf256(3) },
   nB [1] ENUMERATED { fourT(0), twoT(1), oneT(2), halfT(3), quarterT(4), 
      oneEighthT(5), oneSixteenthT(6), oneThirtySecondT(7) }
}

PRACH-ConfigInfo ::= SEQUENCE {
   prach-ConfigIndex [0] INTEGER (0..63),
   highSpeedFlag [1] BOOLEAN,
   zeroCorrelationZoneConfig [2] INTEGER (0..15),
   prach-FreqOffset [3] INTEGER (0..94)
}

PRACH-ConfigSIB ::= SEQUENCE {
   rootSequenceIndex [0] INTEGER (0..837),
   prach-ConfigInfo [1] PRACH-ConfigInfo
}

PDSCH-ConfigCommon ::= SEQUENCE {
   referenceSignalPower [0] INTEGER (-60..50),
   p-b [1] INTEGER (0..3)
}

UL-ReferenceSignalsPUSCH ::= SEQUENCE {
   groupHoppingEnabled [0] BOOLEAN,
   groupAssignmentPUSCH [1] INTEGER (0..29),
   sequenceHoppingEnabled [2] BOOLEAN,
   cyclicShift [3] INTEGER (0..7)
}

PUSCH-ConfigCommon ::= SEQUENCE {
   pusch-ConfigBasic [0] SEQUENCE {
      n-SB [0] INTEGER (1..4),
      hoppingMode [1] ENUMERATED { interSubFrame(0), intraAndInterSubFrame(1) }
         ,
      pusch-HoppingOffset [2] INTEGER (0..98),
      enable64QAM [3] BOOLEAN
   },
   ul-ReferenceSignalsPUSCH [1] UL-ReferenceSignalsPUSCH
}

PUCCH-ConfigCommon ::= SEQUENCE {
   deltaPUCCH-Shift [0] ENUMERATED { ds1(0), ds2(1), ds3(2) },
   nRB-CQI [1] INTEGER (0..98),
   nCS-AN [2] INTEGER (0..7),
   n1PUCCH-AN [3] INTEGER (0..2047)
}

SoundingRS-UL-ConfigCommon ::= CHOICE {
   release [0] NULL,
   setup [1] SEQUENCE {
      srs-BandwidthConfig [0] ENUMERATED { bw0(0), bw1(1), bw2(2), bw3(3), 
         bw4(4), bw5(5), bw6(6), bw7(7) },
      srs-SubframeConfig [1] ENUMERATED { sc0(0), sc1(1), sc2(2), sc3(3), 
         sc4(4), sc5(5), sc6(6), sc7(7), sc8(8), sc9(9), sc10(10), sc11(11), 
         sc12(12), sc13(13), sc14(14), sc15(15) },
      ackNackSRS-SimultaneousTransmission [2] BOOLEAN,
      srs-MaxUpPts [3] ENUMERATED { true(0) } OPTIONAL -- Cond TDD
   }
}

Alpha-r12 ::= ENUMERATED { al0(0), al04(1), al05(2), al06(3), al07(4), al08(5)
   , al09(6), al1(7) }

DeltaFList-PUCCH ::= SEQUENCE {
   deltaF-PUCCH-Format1 [0] ENUMERATED { deltaF-2(0), deltaF0(1), deltaF2(2) },
   deltaF-PUCCH-Format1b [1] ENUMERATED { deltaF1(0), deltaF3(1), deltaF5(2) },
   deltaF-PUCCH-Format2 [2] ENUMERATED { deltaF-2(0), deltaF0(1), deltaF1(2), 
      deltaF2(3) },
   deltaF-PUCCH-Format2a [3] ENUMERATED { deltaF-2(0), deltaF0(1), deltaF2(2) }
      ,
   deltaF-PUCCH-Format2b [4] ENUMERATED { deltaF-2(0), deltaF0(1), deltaF2(2) }
}

UplinkPowerControlCommon ::= SEQUENCE {
   p0-NominalPUSCH [0] INTEGER (-126..24),
   alpha [1] Alpha-r12,
   p0-NominalPUCCH [2] INTEGER (-127..-96),
   deltaFList-PUCCH [3] DeltaFList-PUCCH,
   deltaPreambleMsg3 [4] INTEGER (-1..6)
}

UL-CyclicPrefixLength ::= ENUMERATED { len1(0), len2(1) }

UplinkPowerControlCommon-v1020 ::= SEQUENCE {
   deltaF-PUCCH-Format3-r10 [0] ENUMERATED { deltaF-1(0), deltaF0(1), 
      deltaF1(2), deltaF2(3), deltaF3(4), deltaF4(5), deltaF5(6), deltaF6(7) },
   deltaF-PUCCH-Format1bCS-r10 [1] ENUMERATED { deltaF1(0), deltaF2(1), 
      spare2(2), spare1(3) }
}

RACH-ConfigCommon-v1250 ::= SEQUENCE {
   txFailParams-r12 [0] SEQUENCE {
      connEstFailCount-r12 [0] ENUMERATED { n1(0), n2(1), n3(2), n4(3) },
      connEstFailOffsetValidity-r12 [1] ENUMERATED { s30(0), s60(1), s120(2), 
         s240(3), s300(4), s420(5), s600(6), s900(7) },
      connEstFailOffset-r12 [2] INTEGER (0..15) OPTIONAL -- Need OP
   }
}

PUSCH-ConfigCommon-v1270 ::= SEQUENCE {
   enable64QAM-v1270 [0] ENUMERATED { true(0) }
}

BCCH-Config-v1310 ::= SEQUENCE {
   modificationPeriodCoeff-v1310 [0] ENUMERATED { n64(0) }
}

PCCH-Config-v1310 ::= SEQUENCE {
   paging-narrowBands-r13 [0] INTEGER (1..maxAvailNarrowBands-r13),
   mpdcch-NumRepetition-Paging-r13 [1] ENUMERATED { r1(0), r2(1), r4(2), r8(3)
      , r16(4), r32(5), r64(6), r128(7), r256(8) },
   nB-v1310 [2] ENUMERATED { one64thT(0), one128thT(1), one256thT(2) } OPTIONAL
                          -- Need OR
}

FreqHoppingParameters-r13 ::= SEQUENCE {
   dummy [0] ENUMERATED { nb2(0), nb4(1) } OPTIONAL,
   dummy2 [1] EXPLICIT CHOICE {
      interval-FDD-r13 [0] ENUMERATED { int1(0), int2(1), int4(2), int8(3) },
      interval-TDD-r13 [1] ENUMERATED { int1(0), int5(1), int10(2), int20(3) }
   } OPTIONAL,
   dummy3 [2] EXPLICIT CHOICE {
      interval-FDD-r13 [0] ENUMERATED { int2(0), int4(1), int8(2), int16(3) },
      interval-TDD-r13 [1] ENUMERATED { int5(0), int10(1), int20(2), int40(3) }
   } OPTIONAL,
   interval-ULHoppingConfigCommonModeA-r13 [3] EXPLICIT CHOICE {
      interval-FDD-r13 [0] ENUMERATED { int1(0), int2(1), int4(2), int8(3) },
      interval-TDD-r13 [1] ENUMERATED { int1(0), int5(1), int10(2), int20(3) }
   } OPTIONAL, -- Cond MP-A
   interval-ULHoppingConfigCommonModeB-r13 [4] EXPLICIT CHOICE {
      interval-FDD-r13 [0] ENUMERATED { int2(0), int4(1), int8(2), int16(3) },
      interval-TDD-r13 [1] ENUMERATED { int5(0), int10(1), int20(2), int40(3) }
   } OPTIONAL, -- Cond MP-B
   dummy4 [5] INTEGER (1..maxAvailNarrowBands-r13) OPTIONAL
}

PDSCH-ConfigCommon-v1310 ::= SEQUENCE {
   pdsch-maxNumRepetitionCEmodeA-r13 [0] ENUMERATED { r16(0), r32(1) } OPTIONAL
      , -- Need OR
   pdsch-maxNumRepetitionCEmodeB-r13 [1] ENUMERATED { r192(0), r256(1), r384(2)
      , r512(3), r768(4), r1024(5), r1536(6), r2048(7) } OPTIONAL -- Need OR
}

PUSCH-ConfigCommon-v1310 ::= SEQUENCE {
   pusch-maxNumRepetitionCEmodeA-r13 [0] ENUMERATED { r8(0), r16(1), r32(2) }
       OPTIONAL, -- Need OR
   pusch-maxNumRepetitionCEmodeB-r13 [1] ENUMERATED { r192(0), r256(1), r384(2)
      , r512(3), r768(4), r1024(5), r1536(6), r2048(7) } OPTIONAL, -- Need OR
   pusch-HoppingOffset-v1310 [2] INTEGER (1..maxAvailNarrowBands-r13) OPTIONAL -- Need OR
}

RSRP-Range ::= INTEGER (0..97)

RSRP-ThresholdsPrachInfoList-r13 ::= SEQUENCE (SIZE (1..3)) OF RSRP-Range

PRACH-ParametersCE-r13 ::= SEQUENCE {
   prach-ConfigIndex-r13 [0] INTEGER (0..63),
   prach-FreqOffset-r13 [1] INTEGER (0..94),
   prach-StartingSubframe-r13 [2] ENUMERATED { sf2(0), sf4(1), sf8(2), sf16(3)
      , sf32(4), sf64(5), sf128(6), sf256(7) } OPTIONAL, -- Need OP
   maxNumPreambleAttemptCE-r13 [3] ENUMERATED { n3(0), n4(1), n5(2), n6(3), 
      n7(4), n8(5), n10(6) } OPTIONAL, -- Need OP
   numRepetitionPerPreambleAttempt-r13 [4] ENUMERATED { n1(0), n2(1), n4(2), 
      n8(3), n16(4), n32(5), n64(6), n128(7) },
   mpdcch-NarrowbandsToMonitor-r13 [5] SEQUENCE (SIZE (1..2)) OF INTEGER (1..maxAvailNarrowBands-r13),
   mpdcch-NumRepetition-RA-r13 [6] ENUMERATED { r1(0), r2(1), r4(2), r8(3), 
      r16(4), r32(5), r64(6), r128(7), r256(8) },
   prach-HoppingConfig-r13 [7] ENUMERATED { on(0), off(1) }
}

PRACH-ParametersListCE-r13 ::= SEQUENCE (SIZE (1..maxCE-Level-r13)) OF PRACH-ParametersCE-r13

PRACH-ConfigSIB-v1310 ::= SEQUENCE {
   rsrp-ThresholdsPrachInfoList-r13 [0] RSRP-ThresholdsPrachInfoList-r13,
   mpdcch-startSF-CSS-RA-r13 [1] EXPLICIT CHOICE {
      fdd-r13 [0] ENUMERATED { v1(0), v1dot5(1), v2(2), v2dot5(3), v4(4), v5(5)
         , v8(6), v10(7) },
      tdd-r13 [1] ENUMERATED { v1(0), v2(1), v4(2), v5(3), v8(4), v10(5), 
         v20(6), spare(7) }
   } OPTIONAL, -- Cond MP
   prach-HoppingOffset-r13 [2] INTEGER (0..94) OPTIONAL, -- Need OR
   prach-ParametersListCE-r13 [3] PRACH-ParametersListCE-r13
}

N1PUCCH-AN-InfoList-r13 ::= SEQUENCE (SIZE (1..maxCE-Level-r13)) OF INTEGER (0..2047)

PUCCH-ConfigCommon-v1310 ::= SEQUENCE {
   n1PUCCH-AN-InfoList-r13 [0] N1PUCCH-AN-InfoList-r13 OPTIONAL, -- Need OR
   pucch-NumRepetitionCE-Msg4-Level0-r13 [1] ENUMERATED { n1(0), n2(1), n4(2), 
      n8(3) } OPTIONAL, -- Need OR
   pucch-NumRepetitionCE-Msg4-Level1-r13 [2] ENUMERATED { n1(0), n2(1), n4(2), 
      n8(3) } OPTIONAL, -- Need OR
   pucch-NumRepetitionCE-Msg4-Level2-r13 [3] ENUMERATED { n4(0), n8(1), n16(2)
      , n32(3) } OPTIONAL, -- Need OR
   pucch-NumRepetitionCE-Msg4-Level3-r13 [4] ENUMERATED { n4(0), n8(1), n16(2)
      , n32(3) } OPTIONAL -- Need OR
}

HighSpeedConfig-r14 ::= SEQUENCE {
   highSpeedEnhancedMeasFlag-r14 [0] ENUMERATED { true(0) } OPTIONAL, -- Need OR
   highSpeedEnhancedDemodulationFlag-r14 [1] ENUMERATED { true(0) } OPTIONAL -- Need OR
}

PRACH-Config-v1430 ::= SEQUENCE {
   rootSequenceIndexHighSpeed-r14 [0] INTEGER (0..837),
   zeroCorrelationZoneConfigHighSpeed-r14 [1] INTEGER (0..12),
   prach-ConfigIndexHighSpeed-r14 [2] INTEGER (0..63),
   prach-FreqOffsetHighSpeed-r14 [3] INTEGER (0..94)
}

PUCCH-ConfigCommon-v1430 ::= SEQUENCE {
   pucch-NumRepetitionCE-Msg4-Level3-r14 [0] ENUMERATED { n64(0), n128(1) }
       OPTIONAL -- Need OR
}

EDT-PRACH-ParametersCE-r15 ::= SEQUENCE {
   edt-PRACH-ParametersCE-r15 [0] SEQUENCE {
      prach-ConfigIndex-r15 [0] INTEGER (0..63),
      prach-FreqOffset-r15 [1] INTEGER (0..94),
      prach-StartingSubframe-r15 [2] ENUMERATED { sf2(0), sf4(1), sf8(2), 
         sf16(3), sf32(4), sf64(5), sf128(6), sf256(7) } OPTIONAL, -- Need OP
      mpdcch-NarrowbandsToMonitor-r15 [3] SEQUENCE (SIZE (1..2)) OF INTEGER (1..maxAvailNarrowBands-r13)
   } OPTIONAL -- Need OR
}

PRACH-ConfigSIB-v1530 ::= SEQUENCE {
   edt-PRACH-ParametersListCE-r15 [0] SEQUENCE (SIZE (1..maxCE-Level-r13)) OF 
      EDT-PRACH-ParametersCE-r15
}

RSS-Config-r15 ::= SEQUENCE {
   duration-r15 [0] ENUMERATED { sf8(0), sf16(1), sf32(2), sf40(3) },
   freqLocation-r15 [1] INTEGER (0..98),
   periodicity-r15 [2] ENUMERATED { ms160(0), ms320(1), ms640(2), ms1280(3) },
   powerBoost-r15 [3] ENUMERATED { dB0(0), dB3(1), dB4dot8(2), dB6(3) },
   timeOffset-r15 [4] INTEGER (0..31)
}

WUS-Config-r15 ::= SEQUENCE {
   maxDurationFactor-r15 [0] ENUMERATED { one32th(0), one16th(1), one8th(2), 
      one4th(3) },
   numPOs-r15 [1] ENUMERATED { n1(0), n2(1), n4(2), spare1(3) } DEFAULT n1,
   freqLocation-r15 [2] ENUMERATED { n0(0), n2(1), n4(2), spare1(3) },
   timeOffsetDRX-r15 [3] ENUMERATED { ms40(0), ms80(1), ms160(2), ms240(3) },
   timeOffset-eDRX-Short-r15 [4] ENUMERATED { ms40(0), ms80(1), ms160(2), 
      ms240(3) },
   timeOffset-eDRX-Long-r15 [5] ENUMERATED { ms1000(0), ms2000(1) } OPTIONAL -- Need OP
}

HighSpeedConfig-v1530 ::= SEQUENCE {
   highSpeedMeasGapCE-ModeA-r15 [0] ENUMERATED { true(0) }
}

DeltaFList-SPUCCH-r15 ::= CHOICE {
   release [0] NULL,
   setup [1] SEQUENCE {
      deltaF-slotSPUCCH-Format1-r15 [0] ENUMERATED { deltaF-1(0), deltaF0(1), 
         deltaF1(2), deltaF2(3), deltaF3(4), deltaF4(5), deltaF5(6), deltaF6(7)
          } OPTIONAL, --Need OR
      deltaF-slotSPUCCH-Format1a-r15 [1] ENUMERATED { deltaF1(0), deltaF2(1), 
         deltaF3(2), deltaF4(3), deltaF5(4), deltaF6(5), deltaF7(6), deltaF8(7)
          } OPTIONAL, --Need OR
      deltaF-slotSPUCCH-Format1b-r15 [2] ENUMERATED { deltaF3(0), deltaF4(1), 
         deltaF5(2), deltaF6(3), deltaF7(4), deltaF8(5), deltaF9(6), 
         deltaF10(7) } OPTIONAL, --Need OR
      deltaF-slotSPUCCH-Format3-r15 [3] ENUMERATED { deltaF4(0), deltaF5(1), 
         deltaF6(2), deltaF7(3), deltaF8(4), deltaF9(5), deltaF10(6), 
         deltaF11(7) } OPTIONAL, --Need OR
      deltaF-slotSPUCCH-RM-Format4-r15 [4] ENUMERATED { deltaF13(0), 
         deltaF14(1), deltaF15(2), deltaF16(3), deltaF17(4), deltaF18(5), 
         deltaF19(6), deltaF20(7) } OPTIONAL,
--Need OR
      deltaF-slotSPUCCH-TBCC-Format4-r15 [5] ENUMERATED { deltaF10(0), 
         deltaF11(1), deltaF12(2), deltaF13(3), deltaF14(4), deltaF15(5), 
         deltaF16(6), deltaF17(7) } OPTIONAL,
--Need OR
      deltaF-subslotSPUCCH-Format1and1a-r15 [6] ENUMERATED { deltaF5(0), 
         deltaF6(1), deltaF7(2), deltaF8(3), deltaF9(4), deltaF10(5), 
         deltaF11(6), deltaF12(7) } OPTIONAL,
--Need OR
      deltaF-subslotSPUCCH-Format1b-r15 [7] ENUMERATED { deltaF6(0), deltaF7(1)
         , deltaF8(2), deltaF9(3), deltaF10(4), deltaF11(5), deltaF12(6), 
         deltaF13(7) } OPTIONAL,
--Need OR
      deltaF-subslotSPUCCH-RM-Format4-r15 [8] ENUMERATED { deltaF15(0), 
         deltaF16(1), deltaF17(2), deltaF18(3), deltaF19(4), deltaF20(5), 
         deltaF21(6), deltaF22(7) } OPTIONAL,
--Need OR
      deltaF-subslotSPUCCH-TBCC-Format4-r15 [9] ENUMERATED { deltaF10(0), 
         deltaF11(1), deltaF12(2), deltaF13(3), deltaF14(4), deltaF15(5), 
         deltaF16(6), deltaF17(7) } OPTIONAL,
      ...
   }
}

UplinkPowerControlCommon-v1530 ::= SEQUENCE {
   deltaFList-SPUCCH-r15 [0] EXPLICIT DeltaFList-SPUCCH-r15
}

WUS-Config-v1560 ::= SEQUENCE {
   powerBoost-r15 [0] ENUMERATED { dB0(0), dB1dot8(1), dB3(2), dB4dot8(3) }
}

RadioResourceConfigCommonSIB ::= SEQUENCE {
   rach-ConfigCommon [0] RACH-ConfigCommon,
   bcch-Config [1] BCCH-Config,
   pcch-Config [2] PCCH-Config,
   prach-Config [3] PRACH-ConfigSIB,
   pdsch-ConfigCommon [4] PDSCH-ConfigCommon,
   pusch-ConfigCommon [5] PUSCH-ConfigCommon,
   pucch-ConfigCommon [6] PUCCH-ConfigCommon,
   soundingRS-UL-ConfigCommon [7] EXPLICIT SoundingRS-UL-ConfigCommon,
   uplinkPowerControlCommon [8] UplinkPowerControlCommon,
   ul-CyclicPrefixLength [9] UL-CyclicPrefixLength,
   ...,
   [[
      uplinkPowerControlCommon-v1020 [10] UplinkPowerControlCommon-v1020
          OPTIONAL
   ]],
   [[
      rach-ConfigCommon-v1250 [11] RACH-ConfigCommon-v1250 OPTIONAL
   ]],
   [[
      pusch-ConfigCommon-v1270 [12] PUSCH-ConfigCommon-v1270 OPTIONAL
   ]],
   [[
      bcch-Config-v1310 [13] BCCH-Config-v1310 OPTIONAL,
      pcch-Config-v1310 [14] PCCH-Config-v1310 OPTIONAL,
      freqHoppingParameters-r13 [15] FreqHoppingParameters-r13 OPTIONAL,
      pdsch-ConfigCommon-v1310 [16] PDSCH-ConfigCommon-v1310 OPTIONAL,
      pusch-ConfigCommon-v1310 [17] PUSCH-ConfigCommon-v1310 OPTIONAL,
      prach-ConfigCommon-v1310 [18] PRACH-ConfigSIB-v1310 OPTIONAL,
      pucch-ConfigCommon-v1310 [19] PUCCH-ConfigCommon-v1310 OPTIONAL
   ]],
   [[
      highSpeedConfig-r14 [20] HighSpeedConfig-r14 OPTIONAL,
      prach-Config-v1430 [21] PRACH-Config-v1430 OPTIONAL,
      pucch-ConfigCommon-v1430 [22] PUCCH-ConfigCommon-v1430 OPTIONAL
   ]],
   [[
      prach-Config-v1530 [23] PRACH-ConfigSIB-v1530 OPTIONAL,
      ce-RSS-Config-r15 [24] RSS-Config-r15 OPTIONAL,
      wus-Config-r15 [25] WUS-Config-r15 OPTIONAL,
      highSpeedConfig-v1530 [26] HighSpeedConfig-v1530 OPTIONAL
   ]],
   [[
      uplinkPowerControlCommon-v1540 [27] UplinkPowerControlCommon-v1530
          OPTIONAL
   ]],
   [[
      wus-Config-v1560 [28] WUS-Config-v1560 OPTIONAL
   ]]
}

UE-TimersAndConstants ::= SEQUENCE {
   t300 [0] ENUMERATED { ms100(0), ms200(1), ms300(2), ms400(3), ms600(4), 
      ms1000(5), ms1500(6), ms2000(7) },
   t301 [1] ENUMERATED { ms100(0), ms200(1), ms300(2), ms400(3), ms600(4), 
      ms1000(5), ms1500(6), ms2000(7) },
   t310 [2] ENUMERATED { ms0(0), ms50(1), ms100(2), ms200(3), ms500(4), 
      ms1000(5), ms2000(6) },
   n310 [3] ENUMERATED { n1(0), n2(1), n3(2), n4(3), n6(4), n8(5), n10(6), 
      n20(7) },
   t311 [4] ENUMERATED { ms1000(0), ms3000(1), ms5000(2), ms10000(3), 
      ms15000(4), ms20000(5), ms30000(6) },
   n311 [5] ENUMERATED { n1(0), n2(1), n3(2), n4(3), n5(4), n6(5), n8(6), 
      n10(7) },
   ...,
   [[
      t300-v1310 [6] ENUMERATED { ms2500(0), ms3000(1), ms3500(2), ms4000(3), 
         ms5000(4), ms6000(5), ms8000(6), ms10000(7) } OPTIONAL,
      t301-v1310 [7] ENUMERATED { ms2500(0), ms3000(1), ms3500(2), ms4000(3), 
         ms5000(4), ms6000(5), ms8000(6), ms10000(7) } OPTIONAL
   ]],
   [[
      t310-v1330 [8] ENUMERATED { ms4000(0), ms6000(1) } OPTIONAL
   ]],
   [[
      t300-r15 [9] ENUMERATED { ms4000(0), ms6000(1), ms8000(2), ms10000(3), 
         ms15000(4), ms25000(5), ms40000(6), ms60000(7) } OPTIONAL
   ]]
}

ARFCN-ValueEUTRA ::= INTEGER (0..maxEARFCN)

AdditionalSpectrumEmission ::= INTEGER (1..32)

MBSFN-SubframeConfig ::= SEQUENCE {
   radioframeAllocationPeriod [0] ENUMERATED { n1(0), n2(1), n4(2), n8(3), 
      n16(4), n32(5) },
   radioframeAllocationOffset [1] INTEGER (0..7),
   subframeAllocation [2] EXPLICIT CHOICE {
      oneFrame [0] BIT STRING  (SIZE (6)),
      fourFrames [1] BIT STRING  (SIZE (24))
   }
}

MBSFN-SubframeConfigList ::= SEQUENCE (SIZE (1..maxMBSFN-Allocations)) OF MBSFN-SubframeConfig

TimeAlignmentTimer ::= ENUMERATED { sf500(0), sf750(1), sf1280(2), sf1920(3), 
   sf2560(4), sf5120(5), sf10240(6), infinity(7) }

ARFCN-ValueEUTRA-v9e0 ::= INTEGER (maxEARFCN-Plus1..maxEARFCN2)

AdditionalSpectrumEmission-v10l0 ::= INTEGER (33..288)

UplinkPowerControlCommon-v1310 ::= SEQUENCE {
   deltaF-PUCCH-Format4-r13 [0] ENUMERATED { deltaF16(0), deltaF15(1), 
      deltaF14(2), deltaF13(3), deltaF12(4), deltaF11(5), deltaF10(6), 
      spare1(7) } OPTIONAL, -- Need OR
   deltaF-PUCCH-Format5-13 [1] ENUMERATED { deltaF13(0), deltaF12(1), 
      deltaF11(2), deltaF10(3), deltaF9(4), deltaF8(5), deltaF7(6), spare1(7) }
       OPTIONAL -- Need OR
}

SystemInformationBlockType2-v13c0-IEs ::= SEQUENCE {
   uplinkPowerControlCommon-v13c0 [0] UplinkPowerControlCommon-v1310 OPTIONAL, -- Need OR
--Following field is for non-critical extensions from REL-13
   nonCriticalExtension [1] SEQUENCE {

   } OPTIONAL
}

SystemInformationBlockType2-v10n0-IEs ::= SEQUENCE {
--Following field is for non-critical extensions up-to REL-12
   lateNonCriticalExtension [0] OCTET STRING OPTIONAL,
   nonCriticalExtension [1] SystemInformationBlockType2-v13c0-IEs OPTIONAL
}

SystemInformationBlockType2-v10m0-IEs ::= SEQUENCE {
   freqInfo-v10l0 [0] SEQUENCE {
      additionalSpectrumEmission-v10l0 [0] AdditionalSpectrumEmission-v10l0
   } OPTIONAL,
   multiBandInfoList-v10l0 [1] SEQUENCE (SIZE (1..maxMultiBands)) OF 
      AdditionalSpectrumEmission-v10l0 OPTIONAL,
   nonCriticalExtension [2] SystemInformationBlockType2-v10n0-IEs OPTIONAL
}

SystemInformationBlockType2-v9i0-IEs ::= SEQUENCE {
--Following field is for any non-critical extensions from REL-9
   nonCriticalExtension [0] OCTET STRING (CONTAINING 
      SystemInformationBlockType2-v10m0-IEs) OPTIONAL,
   dummy [1] SEQUENCE {

   } OPTIONAL
}

SystemInformationBlockType2-v9e0-IEs ::= SEQUENCE {
   ul-CarrierFreq-v9e0 [0] ARFCN-ValueEUTRA-v9e0 OPTIONAL, -- Cond ul-FreqMax
   nonCriticalExtension [1] SystemInformationBlockType2-v9i0-IEs OPTIONAL
}

SystemInformationBlockType2-v8h0-IEs ::= SEQUENCE {
   multiBandInfoList [0] SEQUENCE (SIZE (1..maxMultiBands)) OF AdditionalSpectrumEmission
       OPTIONAL, -- Need OR
   nonCriticalExtension [1] SystemInformationBlockType2-v9e0-IEs OPTIONAL
}

AC-BarringPerPLMN-r12 ::= SEQUENCE {
   plmn-IdentityIndex-r12 [0] INTEGER (1..maxPLMN-r11),
   ac-BarringInfo-r12 [1] SEQUENCE {
      ac-BarringForEmergency-r12 [0] BOOLEAN,
      ac-BarringForMO-Signalling-r12 [1] AC-BarringConfig OPTIONAL, -- Need OP
      ac-BarringForMO-Data-r12 [2] AC-BarringConfig OPTIONAL -- Need OP
   } OPTIONAL, -- Need OP
   ac-BarringSkipForMMTELVoice-r12 [2] ENUMERATED { true(0) } OPTIONAL, -- Need OP
   ac-BarringSkipForMMTELVideo-r12 [3] ENUMERATED { true(0) } OPTIONAL, -- Need OP
   ac-BarringSkipForSMS-r12 [4] ENUMERATED { true(0) } OPTIONAL, -- Need OP
   ac-BarringForCSFB-r12 [5] AC-BarringConfig OPTIONAL, -- Need OP
   ssac-BarringForMMTEL-Voice-r12 [6] AC-BarringConfig OPTIONAL, -- Need OP
   ssac-BarringForMMTEL-Video-r12 [7] AC-BarringConfig OPTIONAL -- Need OP
}

AC-BarringPerPLMN-List-r12 ::= SEQUENCE (SIZE (1..maxPLMN-r11)) OF AC-BarringPerPLMN-r12

BarringPerACDC-Category-r13 ::= SEQUENCE {
   acdc-Category-r13 [0] INTEGER (1..maxACDC-Cat-r13),
   acdc-BarringConfig-r13 [1] SEQUENCE {
      ac-BarringFactor-r13 [0] ENUMERATED { p00(0), p05(1), p10(2), p15(3), 
         p20(4), p25(5), p30(6), p40(7), p50(8), p60(9), p70(10), p75(11), 
         p80(12), p85(13), p90(14), p95(15) },
      ac-BarringTime-r13 [1] ENUMERATED { s4(0), s8(1), s16(2), s32(3), s64(4)
         , s128(5), s256(6), s512(7) }
   } OPTIONAL -- Need OP
}

BarringPerACDC-CategoryList-r13 ::= SEQUENCE (SIZE (1..maxACDC-Cat-r13)) OF 
   BarringPerACDC-Category-r13

ACDC-BarringForCommon-r13 ::= SEQUENCE {
   acdc-HPLMNonly-r13 [0] BOOLEAN,
   barringPerACDC-CategoryList-r13 [1] BarringPerACDC-CategoryList-r13
}

ACDC-BarringPerPLMN-r13 ::= SEQUENCE {
   plmn-IdentityIndex-r13 [0] INTEGER (1..maxPLMN-r11),
   acdc-OnlyForHPLMN-r13 [1] BOOLEAN,
   barringPerACDC-CategoryList-r13 [2] BarringPerACDC-CategoryList-r13
}

ACDC-BarringPerPLMN-List-r13 ::= SEQUENCE (SIZE (1..maxPLMN-r11)) OF 
   ACDC-BarringPerPLMN-r13

UDT-Restricting-r13 ::= SEQUENCE {
   udt-Restricting-r13 [0] ENUMERATED { true(0) } OPTIONAL, --Need OR
   udt-RestrictingTime-r13 [1] ENUMERATED { s4(0), s8(1), s16(2), s32(3), 
      s64(4), s128(5), s256(6), s512(7) } OPTIONAL --Need OR
}

UDT-RestrictingPerPLMN-r13 ::= SEQUENCE {
   plmn-IdentityIndex-r13 [0] INTEGER (1..maxPLMN-r11),
   udt-Restricting-r13 [1] UDT-Restricting-r13 OPTIONAL --Need OR
}

UDT-RestrictingPerPLMN-List-r13 ::= SEQUENCE (SIZE (1..maxPLMN-r11)) OF 
   UDT-RestrictingPerPLMN-r13

CIOT-OptimisationPLMN-r13 ::= SEQUENCE {
   up-CIoT-EPS-Optimisation-r13 [0] ENUMERATED { true(0) } OPTIONAL, -- Need OP
   cp-CIoT-EPS-Optimisation-r13 [1] ENUMERATED { true(0) } OPTIONAL, -- Need OP
   attachWithoutPDN-Connectivity-r13 [2] ENUMERATED { true(0) } OPTIONAL -- Need OP
}

CIOT-EPS-OptimisationInfo-r13 ::= SEQUENCE (SIZE (1..maxPLMN-r11)) OF 
   CIOT-OptimisationPLMN-r13

MBSFN-SubframeConfig-v1430 ::= SEQUENCE {
   subframeAllocation-v1430 [0] EXPLICIT CHOICE {
      oneFrame-v1430 [0] BIT STRING  (SIZE (2)),
      fourFrames-v1430 [1] BIT STRING  (SIZE (8))
   }
}

MBSFN-SubframeConfigList-v1430 ::= SEQUENCE (SIZE (1..maxMBSFN-Allocations)) OF 
   MBSFN-SubframeConfig-v1430

PLMN-Info-r15 ::= SEQUENCE {
   upperLayerIndication-r15 [0] ENUMERATED { true(0) } OPTIONAL -- Need OR
}

PLMN-InfoList-r15 ::= SEQUENCE (SIZE (1..maxPLMN-r11)) OF PLMN-Info-r15

SystemInformationBlockType2 ::= SEQUENCE {
   ac-BarringInfo [0] SEQUENCE {
      ac-BarringForEmergency [0] BOOLEAN,
      ac-BarringForMO-Signalling [1] AC-BarringConfig OPTIONAL, -- Need OP
      ac-BarringForMO-Data [2] AC-BarringConfig OPTIONAL -- Need OP
   } OPTIONAL, -- Need OP
   radioResourceConfigCommon [1] RadioResourceConfigCommonSIB,
   ue-TimersAndConstants [2] UE-TimersAndConstants,
   freqInfo [3] SEQUENCE {
      ul-CarrierFreq [0] ARFCN-ValueEUTRA OPTIONAL, -- Need OP
      ul-Bandwidth [1] ENUMERATED { n6(0), n15(1), n25(2), n50(3), n75(4), 
         n100(5) } OPTIONAL,
                         -- Need OP
      additionalSpectrumEmission [2] AdditionalSpectrumEmission
   },
   mbsfn-SubframeConfigList [4] MBSFN-SubframeConfigList OPTIONAL, -- Need OR
   timeAlignmentTimerCommon [5] TimeAlignmentTimer,
   ...,
   lateNonCriticalExtension [6] OCTET STRING (CONTAINING 
      SystemInformationBlockType2-v8h0-IEs) OPTIONAL,
   [[
      ssac-BarringForMMTEL-Voice-r9 [7] AC-BarringConfig OPTIONAL,
      ssac-BarringForMMTEL-Video-r9 [8] AC-BarringConfig OPTIONAL
   ]],
   [[
      ac-BarringForCSFB-r10 [9] AC-BarringConfig OPTIONAL
   ]],
   [[
      ac-BarringSkipForMMTELVoice-r12 [10] ENUMERATED { true(0) } OPTIONAL,
      ac-BarringSkipForMMTELVideo-r12 [11] ENUMERATED { true(0) } OPTIONAL,
      ac-BarringSkipForSMS-r12 [12] ENUMERATED { true(0) } OPTIONAL,
      ac-BarringPerPLMN-List-r12 [13] AC-BarringPerPLMN-List-r12 OPTIONAL
   ]],
   [[
      voiceServiceCauseIndication-r12 [14] ENUMERATED { true(0) } OPTIONAL
   ]],
   [[
      acdc-BarringForCommon-r13 [15] ACDC-BarringForCommon-r13 OPTIONAL,
      acdc-BarringPerPLMN-List-r13 [16] ACDC-BarringPerPLMN-List-r13 OPTIONAL
   ]],
   [[
      udt-RestrictingForCommon-r13 [17] UDT-Restricting-r13 OPTIONAL,
      udt-RestrictingPerPLMN-List-r13 [18] UDT-RestrictingPerPLMN-List-r13
          OPTIONAL,
      cIoT-EPS-OptimisationInfo-r13 [19] CIOT-EPS-OptimisationInfo-r13 OPTIONAL
         ,
      useFullResumeID-r13 [20] ENUMERATED { true(0) } OPTIONAL
   ]],
   [[
      unicastFreqHoppingInd-r13 [21] ENUMERATED { true(0) } OPTIONAL
   ]],
   [[
      mbsfn-SubframeConfigList-v1430 [22] MBSFN-SubframeConfigList-v1430
          OPTIONAL,
      videoServiceCauseIndication-r14 [23] ENUMERATED { true(0) } OPTIONAL
   ]],
   [[
      plmn-InfoList-r15 [24] PLMN-InfoList-r15 OPTIONAL
   ]],
   [[
      cp-EDT-r15 [25] ENUMERATED { true(0) } OPTIONAL,
      up-EDT-r15 [26] ENUMERATED { true(0) } OPTIONAL,
      idleModeMeasurements-r15 [27] ENUMERATED { true(0) } OPTIONAL,
      reducedCP-LatencyEnabled-r15 [28] ENUMERATED { true(0) } OPTIONAL
   ]],
   [[
      mbms-ROM-ServiceIndication-r15 [29] ENUMERATED { true(0) } OPTIONAL
   ]]
}

MobilityStateParameters ::= SEQUENCE {
   t-Evaluation [0] ENUMERATED { s30(0), s60(1), s120(2), s180(3), s240(4), 
      spare3(5), spare2(6), spare1(7) },
   t-HystNormal [1] ENUMERATED { s30(0), s60(1), s120(2), s180(3), s240(4), 
      spare3(5), spare2(6), spare1(7) },
   n-CellChangeMedium [2] INTEGER (1..16),
   n-CellChangeHigh [3] INTEGER (1..16)
}

ReselectionThreshold ::= INTEGER (0..31)

CellReselectionPriority ::= INTEGER (0..7)

Q-RxLevMin ::= INTEGER (-70..-22)

P-Max ::= INTEGER (-30..33)

AllowedMeasBandwidth ::= ENUMERATED { mbw6(0), mbw15(1), mbw25(2), mbw50(3), 
   mbw75(4), mbw100(5) }

PresenceAntennaPort1 ::= BOOLEAN

NeighCellConfig ::= BIT STRING  (SIZE (2))

T-Reselection ::= INTEGER (0..7)

SpeedStateScaleFactors ::= SEQUENCE {
   sf-Medium [0] ENUMERATED { oDot25(0), oDot5(1), oDot75(2), lDot0(3) },
   sf-High [1] ENUMERATED { oDot25(0), oDot5(1), oDot75(2), lDot0(3) }
}

NS-PmaxValue-r10 ::= SEQUENCE {
   additionalPmax-r10 [0] P-Max OPTIONAL, -- Need OP
   additionalSpectrumEmission [1] AdditionalSpectrumEmission
}

NS-PmaxList-r10 ::= SEQUENCE (SIZE (1..maxNS-Pmax-r10)) OF NS-PmaxValue-r10

MultiBandInfoList-v10j0 ::= SEQUENCE (SIZE (1..maxMultiBands)) OF NS-PmaxList-r10

NS-PmaxValue-v10l0 ::= SEQUENCE {
   additionalSpectrumEmission-v10l0 [0] AdditionalSpectrumEmission-v10l0
       OPTIONAL -- Need OP
}

NS-PmaxList-v10l0 ::= SEQUENCE (SIZE (1..maxNS-Pmax-r10)) OF NS-PmaxValue-v10l0

MultiBandInfoList-v10l0 ::= SEQUENCE (SIZE (1..maxMultiBands)) OF NS-PmaxList-v10l0

SystemInformationBlockType3-v10l0-IEs ::= SEQUENCE {
   freqBandInfo-v10l0 [0] NS-PmaxList-v10l0 OPTIONAL, -- Need OR
   multiBandInfoList-v10l0 [1] MultiBandInfoList-v10l0 OPTIONAL, -- Need OR
   nonCriticalExtension [2] SEQUENCE {

   } OPTIONAL
}

-- Late non critical extensions
SystemInformationBlockType3-v10j0-IEs ::= SEQUENCE {
   freqBandInfo-r10 [0] NS-PmaxList-r10 OPTIONAL, -- Need OR
   multiBandInfoList-v10j0 [1] MultiBandInfoList-v10j0 OPTIONAL, -- Need OR
   nonCriticalExtension [2] SystemInformationBlockType3-v10l0-IEs OPTIONAL
}

ReselectionThresholdQ-r9 ::= INTEGER (0..31)

Q-QualMin-r9 ::= INTEGER (-34..-3)

CellReselectionSubPriority-r13 ::= ENUMERATED { oDot2(0), oDot4(1), oDot6(2), 
   oDot8(3) }

CellReselectionServingFreqInfo-v1310 ::= SEQUENCE {
   cellReselectionSubPriority-r13 [0] CellReselectionSubPriority-r13
}

RedistributionServingInfo-r13 ::= SEQUENCE {
   redistributionFactorServing-r13 [0] INTEGER (0..10),
   redistributionFactorCell-r13 [1] ENUMERATED { true(0) } OPTIONAL, --Need OP
   t360-r13 [2] ENUMERATED { min4(0), min8(1), min16(2), min32(3), infinity(4)
      , spare3(5), spare2(6), spare1(7) },
   redistrOnPagingOnly-r13 [3] ENUMERATED { true(0) } OPTIONAL --Need OP
}

CellSelectionInfoCE-r13 ::= SEQUENCE {
   q-RxLevMinCE-r13 [0] Q-RxLevMin,
   q-QualMinRSRQ-CE-r13 [1] Q-QualMin-r9 OPTIONAL -- Need OR
}

T-ReselectionEUTRA-CE-r13 ::= INTEGER (0..15)

CellSelectionInfoCE1-r13 ::= SEQUENCE {
   q-RxLevMinCE1-r13 [0] Q-RxLevMin,
   q-QualMinRSRQ-CE1-r13 [1] Q-QualMin-r9 OPTIONAL -- Need OR
}

CellSelectionInfoCE1-v1360 ::= SEQUENCE {
   delta-RxLevMinCE1-v1360 [0] INTEGER (-8..-1)
}

CellReselectionInfoCommon-v1460 ::= SEQUENCE {
   s-SearchDeltaP-r14 [0] ENUMERATED { dB6(0), dB9(1), dB12(2), dB15(3) }
}

CellReselectionInfoHSDN-r15 ::= SEQUENCE {
   cellEquivalentSize-r15 [0] INTEGER (2..16)
}

CellSelectionInfoCE-v1530 ::= SEQUENCE {
   powerClass14dBm-Offset-r15 [0] ENUMERATED { dB-6(0), dB-3(1), dB3(2), dB6(3)
      , dB9(4), dB12(5) }
}

SystemInformationBlockType3 ::= SEQUENCE {
   cellReselectionInfoCommon [0] SEQUENCE {
      q-Hyst [0] ENUMERATED { dB0(0), dB1(1), dB2(2), dB3(3), dB4(4), dB5(5), 
         dB6(6), dB8(7), dB10(8), dB12(9), dB14(10), dB16(11), dB18(12), 
         dB20(13), dB22(14), dB24(15) },
      speedStateReselectionPars [1] SEQUENCE {
         mobilityStateParameters [0] MobilityStateParameters,
         q-HystSF [1] SEQUENCE {
            sf-Medium [0] ENUMERATED { dB-6(0), dB-4(1), dB-2(2), dB0(3) },
            sf-High [1] ENUMERATED { dB-6(0), dB-4(1), dB-2(2), dB0(3) }
         }
      } OPTIONAL -- Need OP
   },
   cellReselectionServingFreqInfo [1] SEQUENCE {
      s-NonIntraSearch [0] ReselectionThreshold OPTIONAL, -- Need OP
      threshServingLow [1] ReselectionThreshold,
      cellReselectionPriority [2] CellReselectionPriority
   },
   intraFreqCellReselectionInfo [2] SEQUENCE {
      q-RxLevMin [0] Q-RxLevMin,
      p-Max [1] P-Max OPTIONAL, -- Need OP
      s-IntraSearch [2] ReselectionThreshold OPTIONAL, -- Need OP
      allowedMeasBandwidth [3] AllowedMeasBandwidth OPTIONAL, -- Need OP
      presenceAntennaPort1 [4] PresenceAntennaPort1,
      neighCellConfig [5] NeighCellConfig,
      t-ReselectionEUTRA [6] T-Reselection,
      t-ReselectionEUTRA-SF [7] SpeedStateScaleFactors OPTIONAL -- Need OP
   },
   ...,
   lateNonCriticalExtension [3] OCTET STRING (CONTAINING 
      SystemInformationBlockType3-v10j0-IEs) OPTIONAL,
   [[
      s-IntraSearch-v920 [4] SEQUENCE {
         s-IntraSearchP-r9 [0] ReselectionThreshold,
         s-IntraSearchQ-r9 [1] ReselectionThresholdQ-r9
      } OPTIONAL,
      s-NonIntraSearch-v920 [5] SEQUENCE {
         s-NonIntraSearchP-r9 [0] ReselectionThreshold,
         s-NonIntraSearchQ-r9 [1] ReselectionThresholdQ-r9
      } OPTIONAL,
      q-QualMin-r9 [6] Q-QualMin-r9 OPTIONAL,
      threshServingLowQ-r9 [7] ReselectionThresholdQ-r9 OPTIONAL
   ]],
   [[
      q-QualMinWB-r11 [8] Q-QualMin-r9 OPTIONAL
   ]],
   [[
      q-QualMinRSRQ-OnAllSymbols-r12 [9] Q-QualMin-r9 OPTIONAL
   ]],
   [[
      cellReselectionServingFreqInfo-v1310 [10] 
         CellReselectionServingFreqInfo-v1310 OPTIONAL,
      redistributionServingInfo-r13 [11] RedistributionServingInfo-r13 OPTIONAL
         ,
      cellSelectionInfoCE-r13 [12] CellSelectionInfoCE-r13 OPTIONAL,
      t-ReselectionEUTRA-CE-r13 [13] T-ReselectionEUTRA-CE-r13 OPTIONAL
   ]],
   [[
      cellSelectionInfoCE1-r13 [14] CellSelectionInfoCE1-r13 OPTIONAL
   ]],
   [[
      cellSelectionInfoCE1-v1360 [15] CellSelectionInfoCE1-v1360 OPTIONAL
   ]],
   [[
      cellReselectionInfoCommon-v1460 [16] CellReselectionInfoCommon-v1460
          OPTIONAL
   ]],
   [[
      cellReselectionInfoHSDN-r15 [17] CellReselectionInfoHSDN-r15 OPTIONAL,
      cellSelectionInfoCE-v1530 [18] CellSelectionInfoCE-v1530 OPTIONAL,
      crs-IntfMitigNeighCellsCE-r15 [19] ENUMERATED { enabled(0) } OPTIONAL
   ]]
}

PhysCellId ::= INTEGER (0..503)

Q-OffsetRange ::= ENUMERATED { dB-24(0), dB-22(1), dB-20(2), dB-18(3), dB-16(4)
   , dB-14(5), dB-12(6), dB-10(7), dB-8(8), dB-6(9), dB-5(10), dB-4(11), 
   dB-3(12), dB-2(13), dB-1(14), dB0(15), dB1(16), dB2(17), dB3(18), dB4(19), 
   dB5(20), dB6(21), dB8(22), dB10(23), dB12(24), dB14(25), dB16(26), dB18(27)
   , dB20(28), dB22(29), dB24(30) }

IntraFreqNeighCellInfo ::= SEQUENCE {
   physCellId [0] PhysCellId,
   q-OffsetCell [1] Q-OffsetRange,
   ...
}

IntraFreqNeighCellList ::= SEQUENCE (SIZE (1..maxCellIntra)) OF IntraFreqNeighCellInfo

PhysCellIdRange ::= SEQUENCE {
   start [0] PhysCellId,
   range [1] ENUMERATED { n4(0), n8(1), n12(2), n16(3), n24(4), n32(5), n48(6)
      , n64(7), n84(8), n96(9), n128(10), n168(11), n252(12), n504(13), 
      spare2(14), spare1(15) } OPTIONAL -- Need OP
}

IntraFreqBlackCellList ::= SEQUENCE (SIZE (1..maxCellBlack)) OF PhysCellIdRange

IntraFreqNeighHSDN-CellList-r15 ::= SEQUENCE (SIZE (1..maxCellIntra)) OF PhysCellIdRange

SystemInformationBlockType4 ::= SEQUENCE {
   intraFreqNeighCellList [0] IntraFreqNeighCellList OPTIONAL, -- Need OR
   intraFreqBlackCellList [1] IntraFreqBlackCellList OPTIONAL, -- Need OR
   csg-PhysCellIdRange [2] PhysCellIdRange OPTIONAL,
   ...,
   lateNonCriticalExtension [3] OCTET STRING OPTIONAL,
   [[
      intraFreqNeighHSDN-CellList-r15 [4] IntraFreqNeighHSDN-CellList-r15
          OPTIONAL
   ]]
}

InterFreqNeighCellInfo ::= SEQUENCE {
   physCellId [0] PhysCellId,
   q-OffsetCell [1] Q-OffsetRange
}

InterFreqNeighCellList ::= SEQUENCE (SIZE (1..maxCellInter)) OF InterFreqNeighCellInfo

InterFreqBlackCellList ::= SEQUENCE (SIZE (1..maxCellBlack)) OF PhysCellIdRange

InterFreqCarrierFreqInfo ::= SEQUENCE {
   dl-CarrierFreq [0] ARFCN-ValueEUTRA,
   q-RxLevMin [1] Q-RxLevMin,
   p-Max [2] P-Max OPTIONAL, -- Need OP
   t-ReselectionEUTRA [3] T-Reselection,
   t-ReselectionEUTRA-SF [4] SpeedStateScaleFactors OPTIONAL, -- Need OP
   threshX-High [5] ReselectionThreshold,
   threshX-Low [6] ReselectionThreshold,
   allowedMeasBandwidth [7] AllowedMeasBandwidth,
   presenceAntennaPort1 [8] PresenceAntennaPort1,
   cellReselectionPriority [9] CellReselectionPriority OPTIONAL, -- Need OP
   neighCellConfig [10] NeighCellConfig,
   q-OffsetFreq [11] Q-OffsetRange DEFAULT dB0,
   interFreqNeighCellList [12] InterFreqNeighCellList OPTIONAL, -- Need OR
   interFreqBlackCellList [13] InterFreqBlackCellList OPTIONAL,
   ...,
   [[
      q-QualMin-r9 [14] Q-QualMin-r9 OPTIONAL,
      threshX-Q-r9 [15] SEQUENCE {
         threshX-HighQ-r9 [0] ReselectionThresholdQ-r9,
         threshX-LowQ-r9 [1] ReselectionThresholdQ-r9
      } OPTIONAL
   ]],
   [[
      q-QualMinWB-r11 [16] Q-QualMin-r9 OPTIONAL
   ]]
}

InterFreqCarrierFreqList ::= SEQUENCE (SIZE (1..maxFreq)) OF InterFreqCarrierFreqInfo

FreqBandIndicator ::= INTEGER (1..maxFBI)

MultiBandInfoList ::= SEQUENCE (SIZE (1..maxMultiBands)) OF FreqBandIndicator

InterFreqCarrierFreqInfo-v8h0 ::= SEQUENCE {
   multiBandInfoList [0] MultiBandInfoList OPTIONAL -- Need OR
}

FreqBandIndicator-v9e0 ::= INTEGER (maxFBI-Plus1..maxFBI2)

MultiBandInfo-v9e0 ::= SEQUENCE {
   freqBandIndicator-v9e0 [0] FreqBandIndicator-v9e0 OPTIONAL -- Need OP
}

MultiBandInfoList-v9e0 ::= SEQUENCE (SIZE (1..maxMultiBands)) OF MultiBandInfo-v9e0

InterFreqCarrierFreqInfo-v9e0 ::= SEQUENCE {
   dl-CarrierFreq-v9e0 [0] ARFCN-ValueEUTRA-v9e0 OPTIONAL, -- Cond dl-FreqMax
   multiBandInfoList-v9e0 [1] MultiBandInfoList-v9e0 OPTIONAL -- Need OR
}

InterFreqCarrierFreqInfo-v10j0 ::= SEQUENCE {
   freqBandInfo-r10 [0] NS-PmaxList-r10 OPTIONAL, -- Need OR
   multiBandInfoList-v10j0 [1] MultiBandInfoList-v10j0 OPTIONAL -- Need OR
}

InterFreqCarrierFreqInfo-v10l0 ::= SEQUENCE {
   freqBandInfo-v10l0 [0] NS-PmaxList-v10l0 OPTIONAL, -- Need OR
   multiBandInfoList-v10l0 [1] MultiBandInfoList-v10l0 OPTIONAL -- Need OR
}

InterFreqCarrierFreqInfo-v1360 ::= SEQUENCE {
   cellSelectionInfoCE1-v1360 [0] CellSelectionInfoCE1-v1360 OPTIONAL -- Cond QrxlevminCE1
}

InterFreqCarrierFreqList-v13a0 ::= SEQUENCE (SIZE (1..maxFreq)) OF 
   InterFreqCarrierFreqInfo-v1360

SystemInformationBlockType5-v13a0-IEs ::= SEQUENCE {
--Late non critical extensions from REL-10 upto REL-12
   lateNonCriticalExtension [0] OCTET STRING OPTIONAL, -- Need OR
   interFreqCarrierFreqList-v13a0 [1] InterFreqCarrierFreqList-v13a0 OPTIONAL, -- Need OR
--Late non critical extensions from REL-13
   nonCriticalExtension [2] SEQUENCE {

   } OPTIONAL
}

SystemInformationBlockType5-v10l0-IEs ::= SEQUENCE {
   interFreqCarrierFreqList-v10l0 [0] SEQUENCE (SIZE (1..maxFreq)) OF 
      InterFreqCarrierFreqInfo-v10l0 OPTIONAL, -- Need OR
   nonCriticalExtension [1] SystemInformationBlockType5-v13a0-IEs OPTIONAL
}

SystemInformationBlockType5-v10j0-IEs ::= SEQUENCE {
   interFreqCarrierFreqList-v10j0 [0] SEQUENCE (SIZE (1..maxFreq)) OF 
      InterFreqCarrierFreqInfo-v10j0 OPTIONAL, -- Need OR
   nonCriticalExtension [1] SystemInformationBlockType5-v10l0-IEs OPTIONAL
}

SystemInformationBlockType5-v9e0-IEs ::= SEQUENCE {
   interFreqCarrierFreqList-v9e0 [0] SEQUENCE (SIZE (1..maxFreq)) OF 
      InterFreqCarrierFreqInfo-v9e0 OPTIONAL, -- Need OR
   nonCriticalExtension [1] SystemInformationBlockType5-v10j0-IEs OPTIONAL
}

-- Late non critical extensions
SystemInformationBlockType5-v8h0-IEs ::= SEQUENCE {
   interFreqCarrierFreqList-v8h0 [0] SEQUENCE (SIZE (1..maxFreq)) OF 
      InterFreqCarrierFreqInfo-v8h0 OPTIONAL, -- Need OP
   nonCriticalExtension [1] SystemInformationBlockType5-v9e0-IEs OPTIONAL
}

InterFreqCarrierFreqInfo-v1250 ::= SEQUENCE {
   reducedMeasPerformance-r12 [0] ENUMERATED { true(0) } OPTIONAL, -- Need OP
   q-QualMinRSRQ-OnAllSymbols-r12 [1] Q-QualMin-r9 OPTIONAL -- Cond RSRQ2
}

InterFreqCarrierFreqList-v1250 ::= SEQUENCE (SIZE (1..maxFreq)) OF 
   InterFreqCarrierFreqInfo-v1250

ARFCN-ValueEUTRA-r9 ::= INTEGER (0..maxEARFCN2)

FreqBandIndicator-r11 ::= INTEGER (1..maxFBI2)

MultiBandInfoList-r11 ::= SEQUENCE (SIZE (1..maxMultiBands)) OF FreqBandIndicator-r11

InterFreqCarrierFreqInfo-r12 ::= SEQUENCE {
   dl-CarrierFreq-r12 [0] ARFCN-ValueEUTRA-r9,
   q-RxLevMin-r12 [1] Q-RxLevMin,
   p-Max-r12 [2] P-Max OPTIONAL, -- Need OP
   t-ReselectionEUTRA-r12 [3] T-Reselection,
   t-ReselectionEUTRA-SF-r12 [4] SpeedStateScaleFactors OPTIONAL, -- Need OP
   threshX-High-r12 [5] ReselectionThreshold,
   threshX-Low-r12 [6] ReselectionThreshold,
   allowedMeasBandwidth-r12 [7] AllowedMeasBandwidth,
   presenceAntennaPort1-r12 [8] PresenceAntennaPort1,
   cellReselectionPriority-r12 [9] CellReselectionPriority OPTIONAL, -- Need OP
   neighCellConfig-r12 [10] NeighCellConfig,
   q-OffsetFreq-r12 [11] Q-OffsetRange DEFAULT dB0,
   interFreqNeighCellList-r12 [12] InterFreqNeighCellList OPTIONAL, -- Need OR
   interFreqBlackCellList-r12 [13] InterFreqBlackCellList OPTIONAL, -- Need OR
   q-QualMin-r12 [14] Q-QualMin-r9 OPTIONAL, -- Need OP
   threshX-Q-r12 [15] SEQUENCE {
      threshX-HighQ-r12 [0] ReselectionThresholdQ-r9,
      threshX-LowQ-r12 [1] ReselectionThresholdQ-r9
   } OPTIONAL, -- Cond RSRQ
   q-QualMinWB-r12 [16] Q-QualMin-r9 OPTIONAL, -- Cond WB-RSRQ
   multiBandInfoList-r12 [17] MultiBandInfoList-r11 OPTIONAL, -- Need OR
   reducedMeasPerformance-r12 [18] ENUMERATED { true(0) } OPTIONAL, -- Need OP
   q-QualMinRSRQ-OnAllSymbols-r12 [19] Q-QualMin-r9 OPTIONAL,
   ...
}

InterFreqCarrierFreqListExt-r12 ::= SEQUENCE (SIZE (1..maxFreq)) OF 
   InterFreqCarrierFreqInfo-r12

InterFreqCarrierFreqListExt-v1280 ::= SEQUENCE (SIZE (1..maxFreq)) OF 
   InterFreqCarrierFreqInfo-v10j0

RedistributionFactor-r13 ::= INTEGER (1..10)

RedistributionNeighCell-r13 ::= SEQUENCE {
   physCellId-r13 [0] PhysCellId,
   redistributionFactorCell-r13 [1] RedistributionFactor-r13
}

RedistributionNeighCellList-r13 ::= SEQUENCE (SIZE (1..maxCellInter)) OF 
   RedistributionNeighCell-r13

RedistributionInterFreqInfo-r13 ::= SEQUENCE {
   redistributionFactorFreq-r13 [0] RedistributionFactor-r13 OPTIONAL, --Need OP
   redistributionNeighCellList-r13 [1] RedistributionNeighCellList-r13 OPTIONAL
       --Need OP
}

InterFreqCarrierFreqInfo-v1310 ::= SEQUENCE {
   cellReselectionSubPriority-r13 [0] CellReselectionSubPriority-r13 OPTIONAL, -- Need OP
   redistributionInterFreqInfo-r13 [1] RedistributionInterFreqInfo-r13 OPTIONAL
      , --Need OP
   cellSelectionInfoCE-r13 [2] CellSelectionInfoCE-r13 OPTIONAL, -- Need OP
   t-ReselectionEUTRA-CE-r13 [3] T-ReselectionEUTRA-CE-r13 OPTIONAL -- Need OP
}

InterFreqCarrierFreqList-v1310 ::= SEQUENCE (SIZE (1..maxFreq)) OF 
   InterFreqCarrierFreqInfo-v1310

InterFreqCarrierFreqListExt-v1310 ::= SEQUENCE (SIZE (1..maxFreq)) OF 
   InterFreqCarrierFreqInfo-v1310

InterFreqCarrierFreqInfo-v1350 ::= SEQUENCE {
   cellSelectionInfoCE1-r13 [0] CellSelectionInfoCE1-r13 OPTIONAL -- Need OP
}

InterFreqCarrierFreqList-v1350 ::= SEQUENCE (SIZE (1..maxFreq)) OF 
   InterFreqCarrierFreqInfo-v1350

InterFreqCarrierFreqListExt-v1350 ::= SEQUENCE (SIZE (1..maxFreq)) OF 
   InterFreqCarrierFreqInfo-v1350

InterFreqCarrierFreqListExt-v1360 ::= SEQUENCE (SIZE (1..maxFreq)) OF 
   InterFreqCarrierFreqInfo-v1360

InterFreqNeighHSDN-CellList-r15 ::= SEQUENCE (SIZE (1..maxCellInter)) OF PhysCellIdRange

InterFreqCarrierFreqInfo-v1530 ::= SEQUENCE {
   hsdn-Indication-r15 [0] BOOLEAN,
   interFreqNeighHSDN-CellList-r15 [1] InterFreqNeighHSDN-CellList-r15 OPTIONAL
      , -- Need OR
   cellSelectionInfoCE-v1530 [2] CellSelectionInfoCE-v1530 OPTIONAL -- Need OP
}

InterFreqCarrierFreqList-v1530 ::= SEQUENCE (SIZE (1..maxFreq)) OF 
   InterFreqCarrierFreqInfo-v1530

InterFreqCarrierFreqListExt-v1530 ::= SEQUENCE (SIZE (1..maxFreq)) OF 
   InterFreqCarrierFreqInfo-v1530

CellList-r15 ::= SEQUENCE (SIZE (1..maxCellMeasIdle-r15)) OF PhysCellIdRange

RSRQ-Range-r13 ::= INTEGER (-30..46)

MeasIdleCarrierEUTRA-r15 ::= SEQUENCE {
   carrierFreq-r15 [0] ARFCN-ValueEUTRA-r9,
   allowedMeasBandwidth-r15 [1] AllowedMeasBandwidth,
   validityArea-r15 [2] CellList-r15 OPTIONAL, -- Need OR
   measCellList-r15 [3] CellList-r15 OPTIONAL, -- Need OR
   reportQuantities [4] ENUMERATED { rsrp(0), rsrq(1), both(2) },
   qualityThreshold-r15 [5] SEQUENCE {
      idleRSRP-Threshold-r15 [0] RSRP-Range OPTIONAL, -- Need OR
      idleRSRQ-Threshold-r15 [1] RSRQ-Range-r13 OPTIONAL -- Need OR
   } OPTIONAL,
   ...
}

EUTRA-CarrierList-r15 ::= SEQUENCE (SIZE (1..maxFreqIdle-r15)) OF MeasIdleCarrierEUTRA-r15

MeasIdleConfigSIB-r15 ::= SEQUENCE {
   measIdleCarrierListEUTRA-r15 [0] EUTRA-CarrierList-r15,
   ...
}

SystemInformationBlockType5 ::= SEQUENCE {
   interFreqCarrierFreqList [0] InterFreqCarrierFreqList,
   ...,
   lateNonCriticalExtension [1] OCTET STRING (CONTAINING 
      SystemInformationBlockType5-v8h0-IEs) OPTIONAL,
   [[
      interFreqCarrierFreqList-v1250 [2] InterFreqCarrierFreqList-v1250
          OPTIONAL,
      interFreqCarrierFreqListExt-r12 [3] InterFreqCarrierFreqListExt-r12
          OPTIONAL
   ]],
   [[
      interFreqCarrierFreqListExt-v1280 [4] InterFreqCarrierFreqListExt-v1280
          OPTIONAL
   ]],
   [[
      interFreqCarrierFreqList-v1310 [5] InterFreqCarrierFreqList-v1310
          OPTIONAL,
      interFreqCarrierFreqListExt-v1310 [6] InterFreqCarrierFreqListExt-v1310
          OPTIONAL
   ]],
   [[
      interFreqCarrierFreqList-v1350 [7] InterFreqCarrierFreqList-v1350
          OPTIONAL,
      interFreqCarrierFreqListExt-v1350 [8] InterFreqCarrierFreqListExt-v1350
          OPTIONAL
   ]],
   [[
      interFreqCarrierFreqListExt-v1360 [9] InterFreqCarrierFreqListExt-v1360
          OPTIONAL
   ]],
   [[
      scptm-FreqOffset-r14 [10] INTEGER (1..8) OPTIONAL
   ]],
   [[
      interFreqCarrierFreqList-v1530 [11] InterFreqCarrierFreqList-v1530
          OPTIONAL,
      interFreqCarrierFreqListExt-v1530 [12] InterFreqCarrierFreqListExt-v1530
          OPTIONAL,
      measIdleConfigSIB-r15 [13] MeasIdleConfigSIB-r15 OPTIONAL
   ]]
}

ARFCN-ValueUTRA ::= INTEGER (0..16383)

CarrierFreqUTRA-FDD ::= SEQUENCE {
   carrierFreq [0] ARFCN-ValueUTRA,
   cellReselectionPriority [1] CellReselectionPriority OPTIONAL, -- Need OP
   threshX-High [2] ReselectionThreshold,
   threshX-Low [3] ReselectionThreshold,
   q-RxLevMin [4] INTEGER (-60..-13),
   p-MaxUTRA [5] INTEGER (-50..33),
   q-QualMin [6] INTEGER (-24..0),
   ...,
   [[
      threshX-Q-r9 [7] SEQUENCE {
         threshX-HighQ-r9 [0] ReselectionThresholdQ-r9,
         threshX-LowQ-r9 [1] ReselectionThresholdQ-r9
      } OPTIONAL
   ]]
}

CarrierFreqListUTRA-FDD ::= SEQUENCE (SIZE (1..maxUTRA-FDD-Carrier)) OF CarrierFreqUTRA-FDD

CarrierFreqUTRA-TDD ::= SEQUENCE {
   carrierFreq [0] ARFCN-ValueUTRA,
   cellReselectionPriority [1] CellReselectionPriority OPTIONAL, -- Need OP
   threshX-High [2] ReselectionThreshold,
   threshX-Low [3] ReselectionThreshold,
   q-RxLevMin [4] INTEGER (-60..-13),
   p-MaxUTRA [5] INTEGER (-50..33),
   ...
}

CarrierFreqListUTRA-TDD ::= SEQUENCE (SIZE (1..maxUTRA-TDD-Carrier)) OF CarrierFreqUTRA-TDD

FreqBandIndicator-UTRA-FDD ::= INTEGER (1..86)

CarrierFreqInfoUTRA-FDD-v8h0 ::= SEQUENCE {
   multiBandInfoList [0] SEQUENCE (SIZE (1..maxMultiBands)) OF FreqBandIndicator-UTRA-FDD
       OPTIONAL -- Need OR
}

SystemInformationBlockType6-v8h0-IEs ::= SEQUENCE {
   carrierFreqListUTRA-FDD-v8h0 [0] SEQUENCE (SIZE (1..maxUTRA-FDD-Carrier)) OF 
      CarrierFreqInfoUTRA-FDD-v8h0 OPTIONAL, -- Cond UTRA-FDD
   nonCriticalExtension [1] SEQUENCE {

   } OPTIONAL
}

CarrierFreqInfoUTRA-v1250 ::= SEQUENCE {
   reducedMeasPerformance-r12 [0] ENUMERATED { true(0) } OPTIONAL -- Need OP
}

CarrierFreqUTRA-FDD-Ext-r12 ::= SEQUENCE {
   carrierFreq-r12 [0] ARFCN-ValueUTRA,
   cellReselectionPriority-r12 [1] CellReselectionPriority OPTIONAL, -- Need OP
   threshX-High-r12 [2] ReselectionThreshold,
   threshX-Low-r12 [3] ReselectionThreshold,
   q-RxLevMin-r12 [4] INTEGER (-60..-13),
   p-MaxUTRA-r12 [5] INTEGER (-50..33),
   q-QualMin-r12 [6] INTEGER (-24..0),
   threshX-Q-r12 [7] SEQUENCE {
      threshX-HighQ-r12 [0] ReselectionThresholdQ-r9,
      threshX-LowQ-r12 [1] ReselectionThresholdQ-r9
   } OPTIONAL, -- Cond RSRQ
   multiBandInfoList-r12 [8] SEQUENCE (SIZE (1..maxMultiBands)) OF FreqBandIndicator-UTRA-FDD
       OPTIONAL, -- Need OR
   reducedMeasPerformance-r12 [9] ENUMERATED { true(0) } OPTIONAL,
   ...
}

CarrierFreqListUTRA-FDD-Ext-r12 ::= SEQUENCE (SIZE (1..maxUTRA-FDD-Carrier)) OF 
   CarrierFreqUTRA-FDD-Ext-r12

CarrierFreqUTRA-TDD-r12 ::= SEQUENCE {
   carrierFreq-r12 [0] ARFCN-ValueUTRA,
   cellReselectionPriority-r12 [1] CellReselectionPriority OPTIONAL, -- Need OP
   threshX-High-r12 [2] ReselectionThreshold,
   threshX-Low-r12 [3] ReselectionThreshold,
   q-RxLevMin-r12 [4] INTEGER (-60..-13),
   p-MaxUTRA-r12 [5] INTEGER (-50..33),
   reducedMeasPerformance-r12 [6] ENUMERATED { true(0) } OPTIONAL,
   ...
}

CarrierFreqListUTRA-TDD-Ext-r12 ::= SEQUENCE (SIZE (1..maxUTRA-TDD-Carrier)) OF 
   CarrierFreqUTRA-TDD-r12

SystemInformationBlockType6 ::= SEQUENCE {
   carrierFreqListUTRA-FDD [0] CarrierFreqListUTRA-FDD OPTIONAL, -- Need OR
   carrierFreqListUTRA-TDD [1] CarrierFreqListUTRA-TDD OPTIONAL, -- Need OR
   t-ReselectionUTRA [2] T-Reselection,
   t-ReselectionUTRA-SF [3] SpeedStateScaleFactors OPTIONAL,
   ...,
   lateNonCriticalExtension [4] OCTET STRING (CONTAINING 
      SystemInformationBlockType6-v8h0-IEs) OPTIONAL,
   [[
      carrierFreqListUTRA-FDD-v1250 [5] SEQUENCE (SIZE (1..maxUTRA-FDD-Carrier)) OF 
         CarrierFreqInfoUTRA-v1250 OPTIONAL,
      carrierFreqListUTRA-TDD-v1250 [6] SEQUENCE (SIZE (1..maxUTRA-TDD-Carrier)) OF 
         CarrierFreqInfoUTRA-v1250 OPTIONAL,
      carrierFreqListUTRA-FDD-Ext-r12 [7] CarrierFreqListUTRA-FDD-Ext-r12
          OPTIONAL,
      carrierFreqListUTRA-TDD-Ext-r12 [8] CarrierFreqListUTRA-TDD-Ext-r12
          OPTIONAL
   ]]
}

ARFCN-ValueGERAN ::= INTEGER (0..1023)

BandIndicatorGERAN ::= ENUMERATED { dcs1800(0), pcs1900(1) }

ExplicitListOfARFCNs ::= SEQUENCE (SIZE (0..31)) OF ARFCN-ValueGERAN

CarrierFreqsGERAN ::= SEQUENCE {
   startingARFCN [0] ARFCN-ValueGERAN,
   bandIndicator [1] BandIndicatorGERAN,
   followingARFCNs [2] EXPLICIT CHOICE {
      explicitListOfARFCNs [0] ExplicitListOfARFCNs,
      equallySpacedARFCNs [1] SEQUENCE {
         arfcn-Spacing [0] INTEGER (1..8),
         numberOfFollowingARFCNs [1] INTEGER (0..31)
      },
      variableBitMapOfARFCNs [2] OCTET STRING (SIZE (1..16))
   }
}

CarrierFreqsInfoGERAN ::= SEQUENCE {
   carrierFreqs [0] CarrierFreqsGERAN,
   commonInfo [1] SEQUENCE {
      cellReselectionPriority [0] CellReselectionPriority OPTIONAL, -- Need OP
      ncc-Permitted [1] BIT STRING  (SIZE (8)),
      q-RxLevMin [2] INTEGER (0..45),
      p-MaxGERAN [3] INTEGER (0..39) OPTIONAL, -- Need OP
      threshX-High [4] ReselectionThreshold,
      threshX-Low [5] ReselectionThreshold
   },
   ...
}

CarrierFreqsInfoListGERAN ::= SEQUENCE (SIZE (1..maxGNFG)) OF CarrierFreqsInfoGERAN

SystemInformationBlockType7 ::= SEQUENCE {
   t-ReselectionGERAN [0] T-Reselection,
   t-ReselectionGERAN-SF [1] SpeedStateScaleFactors OPTIONAL, -- Need OR
   carrierFreqsInfoList [2] CarrierFreqsInfoListGERAN OPTIONAL,
   ...,
   lateNonCriticalExtension [3] OCTET STRING OPTIONAL
}

SystemTimeInfoCDMA2000 ::= SEQUENCE {
   cdma-EUTRA-Synchronisation [0] BOOLEAN,
   cdma-SystemTime [1] EXPLICIT CHOICE {
      synchronousSystemTime [0] BIT STRING  (SIZE (39)),
      asynchronousSystemTime [1] BIT STRING  (SIZE (49))
   }
}

PreRegistrationZoneIdHRPD ::= INTEGER (0..255)

SecondaryPreRegistrationZoneIdListHRPD ::= SEQUENCE (SIZE (1..2)) OF 
   PreRegistrationZoneIdHRPD

PreRegistrationInfoHRPD ::= SEQUENCE {
   preRegistrationAllowed [0] BOOLEAN,
   preRegistrationZoneId [1] PreRegistrationZoneIdHRPD OPTIONAL, -- cond PreRegAllowed
   secondaryPreRegistrationZoneIdList [2] 
      SecondaryPreRegistrationZoneIdListHRPD OPTIONAL -- Need OR
}

BandclassCDMA2000 ::= ENUMERATED { bc0(0), bc1(1), bc2(2), bc3(3), bc4(4), 
   bc5(5), bc6(6), bc7(7), bc8(8), bc9(9), bc10(10), bc11(11), bc12(12), 
   bc13(13), bc14(14), bc15(15), bc16(16), bc17(17), bc18-v9a0(18), 
   bc19-v9a0(19), bc20-v9a0(20), bc21-v9a0(21), spare10(22), spare9(23), 
   spare8(24), spare7(25), spare6(26), spare5(27), spare4(28), spare3(29), 
   spare2(30), spare1(31), ... }

BandClassInfoCDMA2000 ::= SEQUENCE {
   bandClass [0] BandclassCDMA2000,
   cellReselectionPriority [1] CellReselectionPriority OPTIONAL, -- Need OP
   threshX-High [2] INTEGER (0..63),
   threshX-Low [3] INTEGER (0..63),
   ...
}

BandClassListCDMA2000 ::= SEQUENCE (SIZE (1..maxCDMA-BandClass)) OF BandClassInfoCDMA2000

ARFCN-ValueCDMA2000 ::= INTEGER (0..2047)

PhysCellIdCDMA2000 ::= INTEGER (0..maxPNOffset)

PhysCellIdListCDMA2000 ::= SEQUENCE (SIZE (1..16)) OF PhysCellIdCDMA2000

NeighCellsPerBandclassCDMA2000 ::= SEQUENCE {
   arfcn [0] ARFCN-ValueCDMA2000,
   physCellIdList [1] PhysCellIdListCDMA2000
}

NeighCellsPerBandclassListCDMA2000 ::= SEQUENCE (SIZE (1..16)) OF 
   NeighCellsPerBandclassCDMA2000

NeighCellCDMA2000 ::= SEQUENCE {
   bandClass [0] BandclassCDMA2000,
   neighCellsPerFreqList [1] NeighCellsPerBandclassListCDMA2000
}

NeighCellListCDMA2000 ::= SEQUENCE (SIZE (1..16)) OF NeighCellCDMA2000

CellReselectionParametersCDMA2000 ::= SEQUENCE {
   bandClassList [0] BandClassListCDMA2000,
   neighCellList [1] NeighCellListCDMA2000,
   t-ReselectionCDMA2000 [2] T-Reselection,
   t-ReselectionCDMA2000-SF [3] SpeedStateScaleFactors OPTIONAL -- Need OP
}

CSFB-RegistrationParam1XRTT ::= SEQUENCE {
   sid [0] BIT STRING  (SIZE (15)),
   nid [1] BIT STRING  (SIZE (16)),
   multipleSID [2] BOOLEAN,
   multipleNID [3] BOOLEAN,
   homeReg [4] BOOLEAN,
   foreignSIDReg [5] BOOLEAN,
   foreignNIDReg [6] BOOLEAN,
   parameterReg [7] BOOLEAN,
   powerUpReg [8] BOOLEAN,
   registrationPeriod [9] BIT STRING  (SIZE (7)),
   registrationZone [10] BIT STRING  (SIZE (12)),
   totalZone [11] BIT STRING  (SIZE (3)),
   zoneTimer [12] BIT STRING  (SIZE (3))
}

PhysCellIdListCDMA2000-v920 ::= SEQUENCE (SIZE (0..24)) OF PhysCellIdCDMA2000

NeighCellsPerBandclassCDMA2000-v920 ::= SEQUENCE {
   physCellIdList-v920 [0] PhysCellIdListCDMA2000-v920
}

NeighCellsPerBandclassListCDMA2000-v920 ::= SEQUENCE (SIZE (1..16)) OF 
   NeighCellsPerBandclassCDMA2000-v920

NeighCellCDMA2000-v920 ::= SEQUENCE {
   neighCellsPerFreqList-v920 [0] NeighCellsPerBandclassListCDMA2000-v920
}

NeighCellListCDMA2000-v920 ::= SEQUENCE (SIZE (1..16)) OF NeighCellCDMA2000-v920

CellReselectionParametersCDMA2000-v920 ::= SEQUENCE {
   neighCellList-v920 [0] NeighCellListCDMA2000-v920
}

CSFB-RegistrationParam1XRTT-v920 ::= SEQUENCE {
   powerDownReg-r9 [0] ENUMERATED { true(0) }
}

AC-BarringConfig1XRTT-r9 ::= SEQUENCE {
   ac-Barring0to9-r9 [0] INTEGER (0..63),
   ac-Barring10-r9 [1] INTEGER (0..7),
   ac-Barring11-r9 [2] INTEGER (0..7),
   ac-Barring12-r9 [3] INTEGER (0..7),
   ac-Barring13-r9 [4] INTEGER (0..7),
   ac-Barring14-r9 [5] INTEGER (0..7),
   ac-Barring15-r9 [6] INTEGER (0..7),
   ac-BarringMsg-r9 [7] INTEGER (0..7),
   ac-BarringReg-r9 [8] INTEGER (0..7),
   ac-BarringEmg-r9 [9] INTEGER (0..7)
}

NeighCellsPerBandclassCDMA2000-r11 ::= SEQUENCE {
   arfcn [0] ARFCN-ValueCDMA2000,
   physCellIdList-r11 [1] SEQUENCE (SIZE (1..40)) OF PhysCellIdCDMA2000
}

NeighCellCDMA2000-r11 ::= SEQUENCE {
   bandClass [0] BandclassCDMA2000,
   neighFreqInfoList-r11 [1] SEQUENCE (SIZE (1..16)) OF 
      NeighCellsPerBandclassCDMA2000-r11
}

CellReselectionParametersCDMA2000-r11 ::= SEQUENCE {
   bandClassList [0] BandClassListCDMA2000,
   neighCellList-r11 [1] SEQUENCE (SIZE (1..16)) OF NeighCellCDMA2000-r11,
   t-ReselectionCDMA2000 [2] T-Reselection,
   t-ReselectionCDMA2000-SF [3] SpeedStateScaleFactors OPTIONAL -- Need OP
}

ParametersCDMA2000-r11 ::= SEQUENCE {
   systemTimeInfo-r11 [0] EXPLICIT CHOICE {
      explicitValue [0] SystemTimeInfoCDMA2000,
      defaultValue [1] NULL
   } OPTIONAL, -- Need OR
   searchWindowSize-r11 [1] INTEGER (0..15),
   parametersHRPD-r11 [2] SEQUENCE {
      preRegistrationInfoHRPD-r11 [0] PreRegistrationInfoHRPD,
      cellReselectionParametersHRPD-r11 [1] 
         CellReselectionParametersCDMA2000-r11 OPTIONAL -- Need OR
   } OPTIONAL, -- Need OR
   parameters1XRTT-r11 [3] SEQUENCE {
      csfb-RegistrationParam1XRTT-r11 [0] CSFB-RegistrationParam1XRTT OPTIONAL,
          -- Need OP
      csfb-RegistrationParam1XRTT-Ext-r11 [1] CSFB-RegistrationParam1XRTT-v920
          OPTIONAL, -- Cond REG-1XRTT-PerPLMN
      longCodeState1XRTT-r11 [2] BIT STRING  (SIZE (42)) OPTIONAL, -- Cond PerPLMN-LC
      cellReselectionParameters1XRTT-r11 [3] 
         CellReselectionParametersCDMA2000-r11 OPTIONAL, -- Need OR
      ac-BarringConfig1XRTT-r11 [4] AC-BarringConfig1XRTT-r9 OPTIONAL, -- Cond REG-1XRTT-PerPLMN
      csfb-SupportForDualRxUEs-r11 [5] BOOLEAN OPTIONAL, -- Need OR
      csfb-DualRxTxSupport-r11 [6] ENUMERATED { true(0) } OPTIONAL -- Cond REG-1XRTT-PerPLMN
   } OPTIONAL,
   ...
}

SIB8-PerPLMN-r11 ::= SEQUENCE {
   plmn-Identity-r11 [0] INTEGER (1..maxPLMN-r11),
   parametersCDMA2000-r11 [1] EXPLICIT CHOICE {
      explicitValue [0] ParametersCDMA2000-r11,
      defaultValue [1] NULL
   }
}

SIB8-PerPLMN-List-r11 ::= SEQUENCE (SIZE (1..maxPLMN-r11)) OF SIB8-PerPLMN-r11

SystemInformationBlockType8 ::= SEQUENCE {
   systemTimeInfo [0] SystemTimeInfoCDMA2000 OPTIONAL, -- Need OR
   searchWindowSize [1] INTEGER (0..15) OPTIONAL, -- Need OR
   parametersHRPD [2] SEQUENCE {
      preRegistrationInfoHRPD [0] PreRegistrationInfoHRPD,
      cellReselectionParametersHRPD [1] CellReselectionParametersCDMA2000
          OPTIONAL -- Need OR
   } OPTIONAL, -- Need OR
   parameters1XRTT [3] SEQUENCE {
      csfb-RegistrationParam1XRTT [0] CSFB-RegistrationParam1XRTT OPTIONAL, -- Need OP
      longCodeState1XRTT [1] BIT STRING  (SIZE (42)) OPTIONAL, -- Need OR
      cellReselectionParameters1XRTT [2] CellReselectionParametersCDMA2000
          OPTIONAL -- Need OR
   } OPTIONAL,
   ...,
   lateNonCriticalExtension [4] OCTET STRING OPTIONAL,
   [[
      csfb-SupportForDualRxUEs-r9 [5] BOOLEAN OPTIONAL,
      cellReselectionParametersHRPD-v920 [6] 
         CellReselectionParametersCDMA2000-v920 OPTIONAL,
      cellReselectionParameters1XRTT-v920 [7] 
         CellReselectionParametersCDMA2000-v920 OPTIONAL,
      csfb-RegistrationParam1XRTT-v920 [8] CSFB-RegistrationParam1XRTT-v920
          OPTIONAL,
      ac-BarringConfig1XRTT-r9 [9] AC-BarringConfig1XRTT-r9 OPTIONAL
   ]],
   [[
      csfb-DualRxTxSupport-r10 [10] ENUMERATED { true(0) } OPTIONAL
   ]],
   [[
      sib8-PerPLMN-List-r11 [11] SIB8-PerPLMN-List-r11 OPTIONAL
   ]]
}

SystemInformationBlockType9 ::= SEQUENCE {
   hnb-Name [0] OCTET STRING (SIZE (1..48)) OPTIONAL,
   ...,
   lateNonCriticalExtension [1] OCTET STRING OPTIONAL
}

SystemInformationBlockType10 ::= SEQUENCE {
   messageIdentifier [0] BIT STRING  (SIZE (16)),
   serialNumber [1] BIT STRING  (SIZE (16)),
   warningType [2] OCTET STRING (SIZE (2)),
   dummy [3] OCTET STRING (SIZE (50)) OPTIONAL,
   ...,
   lateNonCriticalExtension [4] OCTET STRING OPTIONAL
}

SystemInformationBlockType11 ::= SEQUENCE {
   messageIdentifier [0] BIT STRING  (SIZE (16)),
   serialNumber [1] BIT STRING  (SIZE (16)),
   warningMessageSegmentType [2] ENUMERATED { notLastSegment(0), lastSegment(1)
       },
   warningMessageSegmentNumber [3] INTEGER (0..63),
   warningMessageSegment [4] OCTET STRING,
   dataCodingScheme [5] OCTET STRING (SIZE (1)) OPTIONAL,
   ...,
   lateNonCriticalExtension [6] OCTET STRING OPTIONAL
}

SystemInformationBlockType12-r9 ::= SEQUENCE {
   messageIdentifier-r9 [0] BIT STRING  (SIZE (16)),
   serialNumber-r9 [1] BIT STRING  (SIZE (16)),
   warningMessageSegmentType-r9 [2] ENUMERATED { notLastSegment(0), 
      lastSegment(1) },
   warningMessageSegmentNumber-r9 [3] INTEGER (0..63),
   warningMessageSegment-r9 [4] OCTET STRING,
   dataCodingScheme-r9 [5] OCTET STRING (SIZE (1)) OPTIONAL, -- Cond Segment1
   lateNonCriticalExtension [6] OCTET STRING OPTIONAL,
   ...,
   [[
      warningAreaCoordinatesSegment-r15 [7] OCTET STRING OPTIONAL
   ]]
}

MBSFN-AreaId-r12 ::= INTEGER (0..255)

MBSFN-AreaInfo-r9 ::= SEQUENCE {
   mbsfn-AreaId-r9 [0] MBSFN-AreaId-r12,
   non-MBSFNregionLength [1] ENUMERATED { s1(0), s2(1) },
   notificationIndicator-r9 [2] INTEGER (0..7),
   mcch-Config-r9 [3] SEQUENCE {
      mcch-RepetitionPeriod-r9 [0] ENUMERATED { rf32(0), rf64(1), rf128(2), 
         rf256(3) },
      mcch-Offset-r9 [1] INTEGER (0..10),
      mcch-ModificationPeriod-r9 [2] ENUMERATED { rf512(0), rf1024(1) },
      sf-AllocInfo-r9 [3] BIT STRING  (SIZE (6)),
      signallingMCS-r9 [4] ENUMERATED { n2(0), n7(1), n13(2), n19(3) }
   },
   ...,
   [[
      mcch-Config-r14 [4] SEQUENCE {
         mcch-RepetitionPeriod-v1430 [0] ENUMERATED { rf1(0), rf2(1), rf4(2), 
            rf8(3), rf16(4) } OPTIONAL, -- Need OR
         mcch-ModificationPeriod-v1430 [1] ENUMERATED { rf1(0), rf2(1), rf4(2)
            , rf8(3), rf16(4), rf32(5), rf64(6), rf128(7), rf256(8), spare7(9)
             } OPTIONAL -- Need OR
      } OPTIONAL,
      subcarrierSpacingMBMS-r14 [5] ENUMERATED { khz-7dot5(0), khz-1dot25(1) }
          OPTIONAL
   ]]
}

MBSFN-AreaInfoList-r9 ::= SEQUENCE (SIZE (1..maxMBSFN-Area)) OF MBSFN-AreaInfo-r9

MBMS-NotificationConfig-r9 ::= SEQUENCE {
   notificationRepetitionCoeff-r9 [0] ENUMERATED { n2(0), n4(1) },
   notificationOffset-r9 [1] INTEGER (0..10),
   notificationSF-Index-r9 [2] INTEGER (1..6)
}

MBMS-NotificationConfig-v1430 ::= SEQUENCE {
   notificationSF-Index-v1430 [0] INTEGER (7..10)
}

SystemInformationBlockType13-r9 ::= SEQUENCE {
   mbsfn-AreaInfoList-r9 [0] MBSFN-AreaInfoList-r9,
   notificationConfig-r9 [1] MBMS-NotificationConfig-r9,
   lateNonCriticalExtension [2] OCTET STRING OPTIONAL,
   ...,
   [[
      notificationConfig-v1430 [3] MBMS-NotificationConfig-v1430 OPTIONAL
   ]]
}

EAB-Config-r11 ::= SEQUENCE {
   eab-Category-r11 [0] ENUMERATED { a(0), b(1), c(2) },
   eab-BarringBitmap-r11 [1] BIT STRING  (SIZE (10))
}

EAB-ConfigPLMN-r11 ::= SEQUENCE {
   eab-Config-r11 [0] EAB-Config-r11 OPTIONAL -- Need OR
}

SystemInformationBlockType14-r11 ::= SEQUENCE {
   eab-Param-r11 [0] EXPLICIT CHOICE {
      eab-Common-r11 [0] EAB-Config-r11,
      eab-PerPLMN-List-r11 [1] SEQUENCE (SIZE (1..maxPLMN-r11)) OF EAB-ConfigPLMN-r11
   } OPTIONAL, -- Need OR
   lateNonCriticalExtension [1] OCTET STRING OPTIONAL,
   ...,
   [[
      eab-PerRSRP-r15 [2] ENUMERATED { thresh0(0), thresh1(1), thresh2(2), 
         thresh3(3) } OPTIONAL
   ]]
}

MBMS-SAI-r11 ::= INTEGER (0..65535)

MBMS-SAI-List-r11 ::= SEQUENCE (SIZE (1..maxSAI-MBMS-r11)) OF MBMS-SAI-r11

MBMS-SAI-InterFreq-r11 ::= SEQUENCE {
   dl-CarrierFreq-r11 [0] ARFCN-ValueEUTRA-r9,
   mbms-SAI-List-r11 [1] MBMS-SAI-List-r11
}

MBMS-SAI-InterFreqList-r11 ::= SEQUENCE (SIZE (1..maxFreq)) OF MBMS-SAI-InterFreq-r11

MBMS-SAI-InterFreq-v1140 ::= SEQUENCE {
   multiBandInfoList-r11 [0] MultiBandInfoList-r11 OPTIONAL -- Need OR
}

MBMS-SAI-InterFreqList-v1140 ::= SEQUENCE (SIZE (1..maxFreq)) OF 
   MBMS-SAI-InterFreq-v1140

MBMS-CarrierType-r14 ::= SEQUENCE {
   carrierType-r14 [0] ENUMERATED { mbms(0), fembmsMixed(1), fembmsDedicated(2)
       },
   frameOffset-r14 [1] INTEGER (0..3) OPTIONAL -- Need OR
}

MBMS-InterFreqCarrierTypeList-r14 ::= SEQUENCE (SIZE (1..maxFreq)) OF 
   MBMS-CarrierType-r14

SystemInformationBlockType15-r11 ::= SEQUENCE {
   mbms-SAI-IntraFreq-r11 [0] MBMS-SAI-List-r11 OPTIONAL, -- Need OR
   mbms-SAI-InterFreqList-r11 [1] MBMS-SAI-InterFreqList-r11 OPTIONAL, -- Need OR
   lateNonCriticalExtension [2] OCTET STRING OPTIONAL,
   ...,
   [[
      mbms-SAI-InterFreqList-v1140 [3] MBMS-SAI-InterFreqList-v1140 OPTIONAL
   ]],
   [[
      mbms-IntraFreqCarrierType-r14 [4] MBMS-CarrierType-r14 OPTIONAL,
      mbms-InterFreqCarrierTypeList-r14 [5] MBMS-InterFreqCarrierTypeList-r14
          OPTIONAL
   ]]
}

ReferenceTime-r15 ::= SEQUENCE {
   refDays-r15 [0] INTEGER (0..72999),
   refSeconds-r15 [1] INTEGER (0..86399),
   refMilliSeconds-r15 [2] INTEGER (0..999),
   refQuarterMicroSeconds-r15 [3] INTEGER (0..3999)
}

TimeReferenceInfo-r15 ::= SEQUENCE {
   time-r15 [0] ReferenceTime-r15,
   uncertainty-r15 [1] INTEGER (0..12) OPTIONAL, -- Need OR
   timeInfoType-r15 [2] ENUMERATED { localClock(0) } OPTIONAL, -- Need OR
   referenceSFN-r15 [3] INTEGER (0..1023) OPTIONAL -- Cond TimeRef
}

SystemInformationBlockType16-r11 ::= SEQUENCE {
   timeInfo-r11 [0] SEQUENCE {
      timeInfoUTC-r11 [0] INTEGER (0..549755813887),
      dayLightSavingTime-r11 [1] BIT STRING  (SIZE (2)) OPTIONAL, -- Need OR
      leapSeconds-r11 [2] INTEGER (-127..128) OPTIONAL, -- Need OR
      localTimeOffset-r11 [3] INTEGER (-63..64) OPTIONAL -- Need OR
   } OPTIONAL, -- Need OR
   lateNonCriticalExtension [1] OCTET STRING OPTIONAL,
   ...,
   [[
      timeReferenceInfo-r15 [2] TimeReferenceInfo-r15 OPTIONAL
   ]]
}

RSRQ-Range ::= INTEGER (0..34)

WLAN-backhaulRate-r12 ::= ENUMERATED { r0(0), r4(1), r8(2), r16(3), r32(4), 
   r64(5), r128(6), r256(7), r512(8), r1024(9), r2048(10), r4096(11), r8192(12)
   , r16384(13), r32768(14), r65536(15), r131072(16), r262144(17), r524288(18)
   , r1048576(19), r2097152(20), r4194304(21), r8388608(22), r16777216(23), 
   r33554432(24), r67108864(25), r134217728(26), r268435456(27), r536870912(28)
   , r1073741824(29), r2147483648(30), r4294967296(31) }

WLAN-OffloadConfig-r12 ::= SEQUENCE {
   thresholdRSRP-r12 [0] SEQUENCE {
      thresholdRSRP-Low-r12 [0] RSRP-Range,
      thresholdRSRP-High-r12 [1] RSRP-Range
   } OPTIONAL, -- Need OR
   thresholdRSRQ-r12 [1] SEQUENCE {
      thresholdRSRQ-Low-r12 [0] RSRQ-Range,
      thresholdRSRQ-High-r12 [1] RSRQ-Range
   } OPTIONAL, -- Need OR
   thresholdRSRQ-OnAllSymbolsWithWB-r12 [2] SEQUENCE {
      thresholdRSRQ-OnAllSymbolsWithWB-Low-r12 [0] RSRQ-Range,
      thresholdRSRQ-OnAllSymbolsWithWB-High-r12 [1] RSRQ-Range
   } OPTIONAL, -- Need OP
   thresholdRSRQ-OnAllSymbols-r12 [3] SEQUENCE {
      thresholdRSRQ-OnAllSymbolsLow-r12 [0] RSRQ-Range,
      thresholdRSRQ-OnAllSymbolsHigh-r12 [1] RSRQ-Range
   } OPTIONAL, -- Need OP
   thresholdRSRQ-WB-r12 [4] SEQUENCE {
      thresholdRSRQ-WB-Low-r12 [0] RSRQ-Range,
      thresholdRSRQ-WB-High-r12 [1] RSRQ-Range
   } OPTIONAL, -- Need OP
   thresholdChannelUtilization-r12 [5] SEQUENCE {
      thresholdChannelUtilizationLow-r12 [0] INTEGER (0..255),
      thresholdChannelUtilizationHigh-r12 [1] INTEGER (0..255)
   } OPTIONAL, -- Need OR
   thresholdBackhaul-Bandwidth-r12 [6] SEQUENCE {
      thresholdBackhaulDL-BandwidthLow-r12 [0] WLAN-backhaulRate-r12,
      thresholdBackhaulDL-BandwidthHigh-r12 [1] WLAN-backhaulRate-r12,
      thresholdBackhaulUL-BandwidthLow-r12 [2] WLAN-backhaulRate-r12,
      thresholdBackhaulUL-BandwidthHigh-r12 [3] WLAN-backhaulRate-r12
   } OPTIONAL, -- Need OR
   thresholdWLAN-RSSI-r12 [7] SEQUENCE {
      thresholdWLAN-RSSI-Low-r12 [0] INTEGER (0..255),
      thresholdWLAN-RSSI-High-r12 [1] INTEGER (0..255)
   } OPTIONAL, -- Need OR
   offloadPreferenceIndicator-r12 [8] BIT STRING  (SIZE (16)) OPTIONAL, -- Need OR
   t-SteeringWLAN-r12 [9] T-Reselection OPTIONAL,
   ...
}

WLAN-Identifiers-r12 ::= SEQUENCE {
   ssid-r12 [0] OCTET STRING (SIZE (1..32)) OPTIONAL, -- Need OR
   bssid-r12 [1] OCTET STRING (SIZE (6)) OPTIONAL, -- Need OR
   hessid-r12 [2] OCTET STRING (SIZE (6)) OPTIONAL,
   ...
}

WLAN-Id-List-r12 ::= SEQUENCE (SIZE (1..maxWLAN-Id-r12)) OF WLAN-Identifiers-r12

WLAN-OffloadInfoPerPLMN-r12 ::= SEQUENCE {
   wlan-OffloadConfigCommon-r12 [0] WLAN-OffloadConfig-r12 OPTIONAL, -- Need OR
   wlan-Id-List-r12 [1] WLAN-Id-List-r12 OPTIONAL,
   ...
}

SystemInformationBlockType17-r12 ::= SEQUENCE {
   wlan-OffloadInfoPerPLMN-List-r12 [0] SEQUENCE (SIZE (1..maxPLMN-r11)) OF 
      WLAN-OffloadInfoPerPLMN-r12 OPTIONAL, -- Need OR
   lateNonCriticalExtension [1] OCTET STRING OPTIONAL,
   ...
}

SL-CP-Len-r12 ::= ENUMERATED { normal(0), extended(1) }

SL-PeriodComm-r12 ::= ENUMERATED { sf40(0), sf60(1), sf70(2), sf80(3), sf120(4)
   , sf140(5), sf160(6), sf240(7), sf280(8), sf320(9), spare6(10), spare5(11), 
   spare4(12), spare3(13), spare2(14), spare(15) }

SL-OffsetIndicator-r12 ::= CHOICE {
   small-r12 [0] INTEGER (0..319),
   large-r12 [1] INTEGER (0..10239)
}

SubframeBitmapSL-r12 ::= CHOICE {
   bs4-r12 [0] BIT STRING  (SIZE (4)),
   bs8-r12 [1] BIT STRING  (SIZE (8)),
   bs12-r12 [2] BIT STRING  (SIZE (12)),
   bs16-r12 [3] BIT STRING  (SIZE (16)),
   bs30-r12 [4] BIT STRING  (SIZE (30)),
   bs40-r12 [5] BIT STRING  (SIZE (40)),
   bs42-r12 [6] BIT STRING  (SIZE (42))
}

SL-TF-ResourceConfig-r12 ::= SEQUENCE {
   prb-Num-r12 [0] INTEGER (1..100),
   prb-Start-r12 [1] INTEGER (0..99),
   prb-End-r12 [2] INTEGER (0..99),
   offsetIndicator-r12 [3] EXPLICIT SL-OffsetIndicator-r12,
   subframeBitmap-r12 [4] EXPLICIT SubframeBitmapSL-r12
}

SL-HoppingConfigComm-r12 ::= SEQUENCE {
   hoppingParameter-r12 [0] INTEGER (0..504),
   numSubbands-r12 [1] ENUMERATED { ns1(0), ns2(1), ns4(2) },
   rb-Offset-r12 [2] INTEGER (0..110)
}

SL-TRPT-Subset-r12 ::= BIT STRING  (SIZE (3..5))

TDD-Config ::= SEQUENCE {
   subframeAssignment [0] ENUMERATED { sa0(0), sa1(1), sa2(2), sa3(3), sa4(4), 
      sa5(5), sa6(6) },
   specialSubframePatterns [1] ENUMERATED { ssp0(0), ssp1(1), ssp2(2), ssp3(3)
      , ssp4(4), ssp5(5), ssp6(6), ssp7(7), ssp8(8) }
}

P0-SL-r12 ::= INTEGER (-126..31)

SL-TxParameters-r12 ::= SEQUENCE {
   alpha-r12 [0] Alpha-r12,
   p0-r12 [1] P0-SL-r12
}

SL-Priority-r13 ::= INTEGER (1..8)

SL-PriorityList-r13 ::= SEQUENCE (SIZE (1..maxSL-Prio-r13)) OF SL-Priority-r13

SL-CommResourcePool-r12 ::= SEQUENCE {
   sc-CP-Len-r12 [0] SL-CP-Len-r12,
   sc-Period-r12 [1] SL-PeriodComm-r12,
   sc-TF-ResourceConfig-r12 [2] SL-TF-ResourceConfig-r12,
   data-CP-Len-r12 [3] SL-CP-Len-r12,
   dataHoppingConfig-r12 [4] SL-HoppingConfigComm-r12,
   ue-SelectedResourceConfig-r12 [5] SEQUENCE {
      data-TF-ResourceConfig-r12 [0] SL-TF-ResourceConfig-r12,
      trpt-Subset-r12 [1] SL-TRPT-Subset-r12 OPTIONAL -- Need OP
   } OPTIONAL, -- Need OR
   rxParametersNCell-r12 [6] SEQUENCE {
      tdd-Config-r12 [0] TDD-Config OPTIONAL, -- Need OP
      syncConfigIndex-r12 [1] INTEGER (0..15)
   } OPTIONAL, -- Need OR
   txParameters-r12 [7] SEQUENCE {
      sc-TxParameters-r12 [0] SL-TxParameters-r12,
      dataTxParameters-r12 [1] SL-TxParameters-r12
   } OPTIONAL,
   ...,
   [[
      priorityList-r13 [8] SL-PriorityList-r13 OPTIONAL
   ]]
}

SL-CommRxPoolList-r12 ::= SEQUENCE (SIZE (1..maxSL-RxPool-r12)) OF SL-CommResourcePool-r12

SL-CommTxPoolList-r12 ::= SEQUENCE (SIZE (1..maxSL-TxPool-r12)) OF SL-CommResourcePool-r12

SL-OffsetIndicatorSync-r12 ::= INTEGER (0..39)

SLSSID-r12 ::= INTEGER (0..167)

RSRP-RangeSL-r12 ::= INTEGER (0..13)

SL-OffsetIndicatorSync-v1430 ::= INTEGER (40..159)

SL-OffsetIndicatorSync-r14 ::= INTEGER (0..159)

SL-SyncConfig-r12 ::= SEQUENCE {
   syncCP-Len-r12 [0] SL-CP-Len-r12,
   syncOffsetIndicator-r12 [1] SL-OffsetIndicatorSync-r12,
   slssid-r12 [2] SLSSID-r12,
   txParameters-r12 [3] SEQUENCE {
      syncTxParameters-r12 [0] SL-TxParameters-r12,
      syncTxThreshIC-r12 [1] RSRP-RangeSL-r12,
      syncInfoReserved-r12 [2] BIT STRING  (SIZE (19)) OPTIONAL -- Need OR
   } OPTIONAL, -- Need OR
   rxParamsNCell-r12 [4] SEQUENCE {
      physCellId-r12 [0] PhysCellId,
      discSyncWindow-r12 [1] ENUMERATED { w1(0), w2(1) }
   } OPTIONAL,
   ...,
   [[
      syncTxPeriodic-r13 [5] ENUMERATED { true(0) } OPTIONAL
   ]],
   [[
      syncOffsetIndicator-v1430 [6] SL-OffsetIndicatorSync-v1430 OPTIONAL,
      gnss-Sync-r14 [7] ENUMERATED { true(0) } OPTIONAL
   ]],
   [[
      syncOffsetIndicator2-r14 [8] SL-OffsetIndicatorSync-r14 OPTIONAL,
      syncOffsetIndicator3-r14 [9] SL-OffsetIndicatorSync-r14 OPTIONAL
   ]],
   [[
      slss-TxDisabled-r15 [10] ENUMERATED { true(0) } OPTIONAL
   ]]
}

SL-SyncConfigList-r12 ::= SEQUENCE (SIZE (1..maxSL-SyncConfig-r12)) OF SL-SyncConfig-r12

SL-CommTxPoolListExt-r13 ::= SEQUENCE (SIZE (1..maxSL-TxPool-v1310)) OF SL-CommResourcePool-r12

SystemInformationBlockType18-r12 ::= SEQUENCE {
   commConfig-r12 [0] SEQUENCE {
      commRxPool-r12 [0] SL-CommRxPoolList-r12,
      commTxPoolNormalCommon-r12 [1] SL-CommTxPoolList-r12 OPTIONAL, -- Need OR
      commTxPoolExceptional-r12 [2] SL-CommTxPoolList-r12 OPTIONAL, -- Need OR
      commSyncConfig-r12 [3] SL-SyncConfigList-r12 OPTIONAL -- Need OR
   } OPTIONAL, -- Need OR
   lateNonCriticalExtension [1] OCTET STRING OPTIONAL,
   ...,
   [[
      commTxPoolNormalCommonExt-r13 [2] SL-CommTxPoolListExt-r13 OPTIONAL,
      commTxResourceUC-ReqAllowed-r13 [3] ENUMERATED { true(0) } OPTIONAL,
      commTxAllowRelayCommon-r13 [4] ENUMERATED { true(0) } OPTIONAL
   ]]
}

RSRP-RangeSL2-r12 ::= INTEGER (0..7)

SL-PoolSelectionConfig-r12 ::= SEQUENCE {
   threshLow-r12 [0] RSRP-RangeSL2-r12,
   threshHigh-r12 [1] RSRP-RangeSL2-r12
}

PhysCellIdList-r13 ::= SEQUENCE (SIZE (1..maxSL-DiscCells-r13)) OF PhysCellId

TDD-Config-v1130 ::= SEQUENCE {
   specialSubframePatterns-v1130 [0] ENUMERATED { ssp7(0), ssp9(1) }
}

SL-DiscResourcePool-r12 ::= SEQUENCE {
   cp-Len-r12 [0] SL-CP-Len-r12,
   discPeriod-r12 [1] ENUMERATED { rf32(0), rf64(1), rf128(2), rf256(3), 
      rf512(4), rf1024(5), rf16-v1310(6), spare(7) },
   numRetx-r12 [2] INTEGER (0..3),
   numRepetition-r12 [3] INTEGER (1..50),
   tf-ResourceConfig-r12 [4] SL-TF-ResourceConfig-r12,
   txParameters-r12 [5] SEQUENCE {
      txParametersGeneral-r12 [0] SL-TxParameters-r12,
      ue-SelectedResourceConfig-r12 [1] SEQUENCE {
         poolSelection-r12 [0] EXPLICIT CHOICE {
            rsrpBased-r12 [0] SL-PoolSelectionConfig-r12,
            random-r12 [1] NULL
         },
         txProbability-r12 [1] ENUMERATED { p25(0), p50(1), p75(2), p100(3) }
      } OPTIONAL -- Need OR
   } OPTIONAL, -- Cond Tx
   rxParameters-r12 [6] SEQUENCE {
      tdd-Config-r12 [0] TDD-Config OPTIONAL, -- Need OR
      syncConfigIndex-r12 [1] INTEGER (0..15)
   } OPTIONAL,
   ...,
   [[
      discPeriod-v1310 [7] EXPLICIT CHOICE {
         release [0] NULL,
         setup [1] ENUMERATED { rf4(0), rf6(1), rf7(2), rf8(3), rf12(4), 
            rf14(5), rf24(6), rf28(7) }
      } OPTIONAL,
      rxParamsAddNeighFreq-r13 [8] EXPLICIT CHOICE {
         release [0] NULL,
         setup [1] SEQUENCE {
            physCellId-r13 [0] PhysCellIdList-r13
         }
      } OPTIONAL,
      txParamsAddNeighFreq-r13 [9] EXPLICIT CHOICE {
         release [0] NULL,
         setup [1] SEQUENCE {
            physCellId-r13 [0] PhysCellIdList-r13,
            p-Max [1] P-Max OPTIONAL, -- Need OP
            tdd-Config-r13 [2] TDD-Config OPTIONAL, -- Cond TDD-OR
            tdd-Config-v1130 [3] TDD-Config-v1130 OPTIONAL, -- Cond TDD-OR
            freqInfo [4] SEQUENCE {
               ul-CarrierFreq [0] ARFCN-ValueEUTRA OPTIONAL, -- Need OP
               ul-Bandwidth [1] ENUMERATED { n6(0), n15(1), n25(2), n50(3), 
                  n75(4), n100(5) } OPTIONAL,
                   -- Need OP
               additionalSpectrumEmission [2] AdditionalSpectrumEmission
            },
            referenceSignalPower [5] INTEGER (-60..50),
            syncConfigIndex-r13 [6] INTEGER (0..15) OPTIONAL -- Need OR
         }
      } OPTIONAL
   ]],
   [[
      txParamsAddNeighFreq-v1370 [10] EXPLICIT CHOICE {
         release [0] NULL,
         setup [1] SEQUENCE {
            freqInfo-v1370 [0] SEQUENCE {
               additionalSpectrumEmission-v1370 [0] 
                  AdditionalSpectrumEmission-v10l0
            }
         }
      } OPTIONAL
   ]]
}

SL-DiscRxPoolList-r12 ::= SEQUENCE (SIZE (1..maxSL-RxPool-r12)) OF SL-DiscResourcePool-r12

SL-DiscTxPoolList-r12 ::= SEQUENCE (SIZE (1..maxSL-TxPool-r12)) OF SL-DiscResourcePool-r12

SL-DiscTxPowerInfo-r12 ::= SEQUENCE {
   discMaxTxPower-r12 [0] P-Max,
   ...
}

SL-DiscTxPowerInfoList-r12 ::= SEQUENCE (SIZE (maxSL-DiscPowerClass-r12)) OF SL-DiscTxPowerInfo-r12

MCC-MNC-Digit ::= INTEGER (0..9)

MCC ::= SEQUENCE (SIZE (3)) OF MCC-MNC-Digit

MNC ::= SEQUENCE (SIZE (2..3)) OF MCC-MNC-Digit

PLMN-Identity ::= SEQUENCE {
   mcc [0] MCC OPTIONAL, -- Cond MCC
   mnc [1] MNC
}

PLMN-IdentityInfo2-r12 ::= CHOICE {
   plmn-Index-r12 [0] INTEGER (1..maxPLMN-r11),
   plmnIdentity-r12 [1] PLMN-Identity
}

PLMN-IdentityList4-r12 ::= SEQUENCE (SIZE (1..maxPLMN-r11)) OF PLMN-IdentityInfo2-r12

SL-CarrierFreqInfo-r12 ::= SEQUENCE {
   carrierFreq-r12 [0] ARFCN-ValueEUTRA-r9,
   plmn-IdentityList-r12 [1] PLMN-IdentityList4-r12 OPTIONAL -- Need OP
}

SL-CarrierFreqInfoList-r12 ::= SEQUENCE (SIZE (1..maxFreq)) OF SL-CarrierFreqInfo-r12

SL-DiscTxResourcesInterFreq-r13 ::= CHOICE {
   acquireSI-FromCarrier-r13 [0] NULL,
   discTxPoolCommon-r13 [1] SL-DiscTxPoolList-r12,
   requestDedicated-r13 [2] NULL,
   noTxOnCarrier-r13 [3] NULL
}

SL-ResourcesInterFreq-r13 ::= SEQUENCE {
   discRxResourcesInterFreq-r13 [0] SL-DiscRxPoolList-r12 OPTIONAL, -- Need OR
   discTxResourcesInterFreq-r13 [1] EXPLICIT SL-DiscTxResourcesInterFreq-r13
       OPTIONAL -- Need OR
}

SL-SyncConfigNFreq-r13 ::= SEQUENCE {
   asyncParameters-r13 [0] SEQUENCE {
      syncCP-Len-r13 [0] SL-CP-Len-r12,
      syncOffsetIndicator-r13 [1] SL-OffsetIndicatorSync-r12,
      slssid-r13 [2] SLSSID-r12
   } OPTIONAL, -- Need OR
   txParameters-r13 [1] SEQUENCE {
      syncTxParameters-r13 [0] SL-TxParameters-r12,
      syncTxThreshIC-r13 [1] RSRP-RangeSL-r12,
      syncInfoReserved-r13 [2] BIT STRING  (SIZE (19)) OPTIONAL, -- Need OR
      syncTxPeriodic-r13 [3] ENUMERATED { true(0) } OPTIONAL -- Need OR
   } OPTIONAL, -- Need OR
   rxParameters-r13 [2] SEQUENCE {
      discSyncWindow-r13 [0] ENUMERATED { w1(0), w2(1) }
   } OPTIONAL,
   ...,
   [[
      syncOffsetIndicator-v1430 [3] SL-OffsetIndicatorSync-v1430 OPTIONAL,
      gnss-Sync-r14 [4] ENUMERATED { true(0) } OPTIONAL
   ]],
   [[
      syncOffsetIndicator2-r14 [5] SL-OffsetIndicatorSync-r14 OPTIONAL,
      syncOffsetIndicator3-r14 [6] SL-OffsetIndicatorSync-r14 OPTIONAL
   ]],
   [[
      slss-TxDisabled-r15 [7] ENUMERATED { true(0) } OPTIONAL
   ]]
}

SL-SyncConfigListNFreq-r13 ::= SEQUENCE (SIZE (1..maxSL-SyncConfig-r12)) OF SL-SyncConfigNFreq-r13

CellSelectionInfoNFreq-r13 ::= SEQUENCE {
--Cell selection information as in SIB1
   q-RxLevMin-r13 [0] Q-RxLevMin,
   q-RxLevMinOffset [1] INTEGER (1..8) OPTIONAL, -- Need OP
--Cell re-selection information as in SIB3
   q-Hyst-r13 [2] ENUMERATED { dB0(0), dB1(1), dB2(2), dB3(3), dB4(4), dB5(5), 
      dB6(6), dB8(7), dB10(8), dB12(9), dB14(10), dB16(11), dB18(12), dB20(13)
      , dB22(14), dB24(15) },
   q-RxLevMinReselection-r13 [3] Q-RxLevMin,
   t-ReselectionEUTRA-r13 [4] T-Reselection
}

SL-DiscConfigOtherInterFreq-r13 ::= SEQUENCE {
   txPowerInfo-r13 [0] SL-DiscTxPowerInfoList-r12 OPTIONAL, -- Cond Tx
   refCarrierCommon-r13 [1] ENUMERATED { pCell(0) } OPTIONAL, -- Need OR
   discSyncConfig-r13 [2] SL-SyncConfigListNFreq-r13 OPTIONAL, -- Need OR
   discCellSelectionInfo-r13 [3] CellSelectionInfoNFreq-r13 OPTIONAL -- Need OR
}

SL-CarrierFreqInfo-v1310 ::= SEQUENCE {
   discResourcesNonPS-r13 [0] SL-ResourcesInterFreq-r13 OPTIONAL, -- Need OR
   discResourcesPS-r13 [1] SL-ResourcesInterFreq-r13 OPTIONAL, -- Need OR
   discConfigOther-r13 [2] SL-DiscConfigOtherInterFreq-r13 OPTIONAL,
   ...
}

SL-CarrierFreqInfoList-v1310 ::= SEQUENCE (SIZE (1..maxFreq)) OF 
   SL-CarrierFreqInfo-v1310

RSRP-RangeSL4-r13 ::= INTEGER (0..49)

SL-DiscConfigRelayUE-r13 ::= SEQUENCE {
   threshHigh-r13 [0] RSRP-RangeSL4-r13 OPTIONAL, -- Need OR
   threshLow-r13 [1] RSRP-RangeSL4-r13 OPTIONAL, -- Need OR
   hystMax-r13 [2] ENUMERATED { dB0(0), dB3(1), dB6(2), dB9(3), dB12(4), 
      dBinf(5) } OPTIONAL, -- Cond ThreshHigh
   hystMin-r13 [3] ENUMERATED { dB0(0), dB3(1), dB6(2), dB9(3), dB12(4) }
       OPTIONAL -- Cond ThreshLow
}

FilterCoefficient ::= ENUMERATED { fc0(0), fc1(1), fc2(2), fc3(3), fc4(4), 
   fc5(5), fc6(6), fc7(7), fc8(8), fc9(9), fc11(10), fc13(11), fc15(12), 
   fc17(13), fc19(14), spare1(15), ... }

ReselectionInfoRelay-r13 ::= SEQUENCE {
   q-RxLevMin-r13 [0] Q-RxLevMin,
--Note that the mapping of invidual values may be different for PC5, but the granularity/
--number of values is same as for Uu
   filterCoefficient-r13 [1] FilterCoefficient,
   minHyst-r13 [2] ENUMERATED { dB0(0), dB3(1), dB6(2), dB9(3), dB12(4), 
      dBinf(5) } OPTIONAL -- Need OR
}

SL-DiscConfigRemoteUE-r13 ::= SEQUENCE {
   threshHigh-r13 [0] RSRP-RangeSL4-r13 OPTIONAL, -- Need OR
   hystMax-r13 [1] ENUMERATED { dB0(0), dB3(1), dB6(2), dB9(3), dB12(4) }
       OPTIONAL, -- Cond ThreshHigh
   reselectionInfoIC-r13 [2] ReselectionInfoRelay-r13
}

SystemInformationBlockType19-r12 ::= SEQUENCE {
   discConfig-r12 [0] SEQUENCE {
      discRxPool-r12 [0] SL-DiscRxPoolList-r12,
      discTxPoolCommon-r12 [1] SL-DiscTxPoolList-r12 OPTIONAL, -- Need OR
      discTxPowerInfo-r12 [2] SL-DiscTxPowerInfoList-r12 OPTIONAL, -- Cond Tx
      discSyncConfig-r12 [3] SL-SyncConfigList-r12 OPTIONAL -- Need OR
   } OPTIONAL, -- Need OR
   discInterFreqList-r12 [1] SL-CarrierFreqInfoList-r12 OPTIONAL, -- Need OR
   lateNonCriticalExtension [2] OCTET STRING OPTIONAL,
   ...,
   [[
      discConfig-v1310 [3] SEQUENCE {
         discInterFreqList-v1310 [0] SL-CarrierFreqInfoList-v1310 OPTIONAL, -- Need OR
         gapRequestsAllowedCommon [1] ENUMERATED { true(0) } OPTIONAL -- Need OR
      } OPTIONAL,
      discConfigRelay-r13 [4] SEQUENCE {
         relayUE-Config-r13 [0] SL-DiscConfigRelayUE-r13,
         remoteUE-Config-r13 [1] SL-DiscConfigRemoteUE-r13
      } OPTIONAL,
      discConfigPS-13 [5] SEQUENCE {
         discRxPoolPS-r13 [0] SL-DiscRxPoolList-r12,
         discTxPoolPS-Common-r13 [1] SL-DiscTxPoolList-r12 OPTIONAL -- Need OR
      } OPTIONAL
   ]]
}

SC-MCCH-SchedulingInfo-r14 ::= SEQUENCE {
   onDurationTimerSCPTM-r14 [0] ENUMERATED { psf10(0), psf20(1), psf100(2), 
      psf300(3), psf500(4), psf1000(5), psf1200(6), psf1600(7) },
   drx-InactivityTimerSCPTM-r14 [1] ENUMERATED { psf0(0), psf1(1), psf2(2), 
      psf4(3), psf8(4), psf16(5), psf32(6), psf64(7), psf128(8), psf256(9), 
      ps512(10), psf1024(11), psf2048(12), psf4096(13), psf8192(14), 
      psf16384(15) },
   schedulingPeriodStartOffsetSCPTM-r14 [2] EXPLICIT CHOICE {
      sf10 [0] INTEGER (0..9),
      sf20 [1] INTEGER (0..19),
      sf32 [2] INTEGER (0..31),
      sf40 [3] INTEGER (0..39),
      sf64 [4] INTEGER (0..63),
      sf80 [5] INTEGER (0..79),
      sf128 [6] INTEGER (0..127),
      sf160 [7] INTEGER (0..159),
      sf256 [8] INTEGER (0..255),
      sf320 [9] INTEGER (0..319),
      sf512 [10] INTEGER (0..511),
      sf640 [11] INTEGER (0..639),
      sf1024 [12] INTEGER (0..1023),
      sf2048 [13] INTEGER (0..2047),
      sf4096 [14] INTEGER (0..4095),
      sf8192 [15] INTEGER (0..8191)
   },
   ...
}

SystemInformationBlockType20-r13 ::= SEQUENCE {
   sc-mcch-RepetitionPeriod-r13 [0] ENUMERATED { rf2(0), rf4(1), rf8(2), 
      rf16(3), rf32(4), rf64(5), rf128(6), rf256(7) },
   sc-mcch-Offset-r13 [1] INTEGER (0..10),
   sc-mcch-FirstSubframe-r13 [2] INTEGER (0..9),
   sc-mcch-duration-r13 [3] INTEGER (2..9) OPTIONAL,
   sc-mcch-ModificationPeriod-r13 [4] ENUMERATED { rf2(0), rf4(1), rf8(2), 
      rf16(3), rf32(4), rf64(5), rf128(6), rf256(7), rf512(8), rf1024(9), 
      r2048(10), rf4096(11), rf8192(12), rf16384(13), rf32768(14), rf65536(15)
       },
   lateNonCriticalExtension [5] OCTET STRING OPTIONAL,
   ...,
   [[
      br-BCCH-Config-r14 [6] SEQUENCE {
         dummy [0] ENUMERATED { rf1(0) },
         dummy2 [1] ENUMERATED { rf1(0) },
         mpdcch-Narrowband-SC-MCCH-r14 [2] INTEGER (1..maxAvailNarrowBands-r13),
         mpdcch-NumRepetition-SC-MCCH-r14 [3] ENUMERATED { r1(0), r2(1), r4(2)
            , r8(3), r16(4), r32(5), r64(6), r128(7), r256(8) },
         mpdcch-StartSF-SC-MCCH-r14 [4] EXPLICIT CHOICE {
            fdd-r14 [0] ENUMERATED { v1(0), v1dot5(1), v2(2), v2dot5(3), v4(4)
               , v5(5), v8(6), v10(7) },
            tdd-r14 [1] ENUMERATED { v1(0), v2(1), v4(2), v5(3), v8(4), v10(5)
               , v20(6) }
         },
         mpdcch-PDSCH-HoppingConfig-SC-MCCH-r14 [5] ENUMERATED { off(0), 
            ce-ModeA(1), ce-ModeB(2) },
         sc-mcch-CarrierFreq-r14 [6] ARFCN-ValueEUTRA-r9,
         sc-mcch-Offset-BR-r14 [7] INTEGER (0..10),
         sc-mcch-RepetitionPeriod-BR-r14 [8] ENUMERATED { rf32(0), rf128(1), 
            rf512(2), rf1024(3), rf2048(4), rf4096(5), rf8192(6), rf16384(7) },
         sc-mcch-ModificationPeriod-BR-r14 [9] ENUMERATED { rf32(0), rf128(1), 
            rf256(2), rf512(3), rf1024(4), rf2048(5), rf4096(6), rf8192(7), 
            rf16384(8), rf32768(9), rf65536(10), rf131072(11), rf262144(12), 
            rf524288(13), rf1048576(14) }
      } OPTIONAL,
      sc-mcch-SchedulingInfo-r14 [7] SC-MCCH-SchedulingInfo-r14 OPTIONAL,
      pdsch-maxNumRepetitionCEmodeA-SC-MTCH-r14 [8] ENUMERATED { r16(0), r32(1)
          } OPTIONAL,
      pdsch-maxNumRepetitionCEmodeB-SC-MTCH-r14 [9] ENUMERATED { r192(0), 
         r256(1), r384(2), r512(3), r768(4), r1024(5), r1536(6), r2048(7) }
          OPTIONAL
   ]],
   [[
      sc-mcch-RepetitionPeriod-v1470 [10] ENUMERATED { rf1(0) } OPTIONAL,
      sc-mcch-ModificationPeriod-v1470 [11] ENUMERATED { rf1(0) } OPTIONAL
   ]]
}

SubframeBitmapSL-r14 ::= CHOICE {
   bs10-r14 [0] BIT STRING  (SIZE (10)),
   bs16-r14 [1] BIT STRING  (SIZE (16)),
   bs20-r14 [2] BIT STRING  (SIZE (20)),
   bs30-r14 [3] BIT STRING  (SIZE (30)),
   bs40-r14 [4] BIT STRING  (SIZE (40)),
   bs50-r14 [5] BIT STRING  (SIZE (50)),
   bs60-r14 [6] BIT STRING  (SIZE (60)),
   bs100-r14 [7] BIT STRING  (SIZE (100))
}

SL-V2X-TxPoolReportIdentity-r14 ::= INTEGER (1..maxSL-PoolToMeasure-r14)

Tx-ConfigIndex-r14 ::= INTEGER (0..maxSL-V2X-TxConfig-1-r14)

SL-PPPP-TxConfigIndex-r14 ::= SEQUENCE {
   priorityThreshold-r14 [0] SL-Priority-r13,
   defaultTxConfigIndex-r14 [1] INTEGER (0..maxCBR-Level-1-r14),
   cbr-ConfigIndex-r14 [2] INTEGER (0..maxSL-V2X-CBRConfig-1-r14),
   tx-ConfigIndexList-r14 [3] SEQUENCE (SIZE (1..maxCBR-Level-r14)) OF Tx-ConfigIndex-r14
}

SL-CBR-PPPP-TxConfigList-r14 ::= SEQUENCE (SIZE (1..8)) OF 
   SL-PPPP-TxConfigIndex-r14

SL-P2X-ResourceSelectionConfig-r14 ::= SEQUENCE {
   partialSensing-r14 [0] ENUMERATED { true(0) } OPTIONAL, -- Need OR
   randomSelection-r14 [1] ENUMERATED { true(0) } OPTIONAL -- Need OR
}

SL-SyncAllowed-r14 ::= SEQUENCE {
   gnss-Sync-r14 [0] ENUMERATED { true(0) } OPTIONAL, -- Need OR
   enb-Sync-r14 [1] ENUMERATED { true(0) } OPTIONAL, -- Need OR
   ue-Sync-r14 [2] ENUMERATED { true(0) } OPTIONAL -- Need OR
}

SL-RestrictResourceReservationPeriod-r14 ::= ENUMERATED { v0dot2(0), v0dot5(1)
   , v1(2), v2(3), v3(4), v4(5), v5(6), v6(7), v7(8), v8(9), v9(10), v10(11), 
   spare4(12), spare3(13), spare2(14), spare1(15) }

SL-RestrictResourceReservationPeriodList-r14 ::= SEQUENCE (SIZE (1..maxReservationPeriod-r14)) OF 
   SL-RestrictResourceReservationPeriod-r14

SL-MinT2Value-r15 ::= SEQUENCE {
   priorityList-r15 [0] SL-PriorityList-r13,
   minT2Value-r15 [1] INTEGER (10..20)
}

SL-MinT2ValueList-r15 ::= SEQUENCE (SIZE (1..maxSL-Prio-r13)) OF SL-MinT2Value-r15

MCS-PSSCH-Range-r15 ::= SEQUENCE {
   minMCS-PSSCH-r15 [0] INTEGER (0..31),
   maxMCS-PSSCH-r15 [1] INTEGER (0..31)
}

SL-PPPP-TxConfigIndex-v1530 ::= SEQUENCE {
   mcs-PSSCH-RangeList-r15 [0] SEQUENCE (SIZE (1..maxCBR-Level-r14)) OF MCS-PSSCH-Range-r15
       OPTIONAL --Need OR
}

SL-CBR-PPPP-TxConfigList-v1530 ::= SEQUENCE (SIZE (1..8)) OF 
   SL-PPPP-TxConfigIndex-v1530

SL-CommResourcePoolV2X-r14 ::= SEQUENCE {
   sl-OffsetIndicator-r14 [0] EXPLICIT SL-OffsetIndicator-r12 OPTIONAL, -- Need OR
   sl-Subframe-r14 [1] EXPLICIT SubframeBitmapSL-r14,
   adjacencyPSCCH-PSSCH-r14 [2] BOOLEAN,
   sizeSubchannel-r14 [3] ENUMERATED { n4(0), n5(1), n6(2), n8(3), n9(4), 
      n10(5), n12(6), n15(7), n16(8), n18(9), n20(10), n25(11), n30(12), 
      n48(13), n50(14), n72(15), n75(16), n96(17), n100(18), spare13(19), 
      spare12(20), spare11(21), spare10(22), spare9(23), spare8(24), spare7(25)
      , spare6(26), spare5(27), spare4(28), spare3(29), spare2(30), spare1(31)
       },
   numSubchannel-r14 [4] ENUMERATED { n1(0), n3(1), n5(2), n8(3), n10(4), 
      n15(5), n20(6), spare1(7) },
   startRB-Subchannel-r14 [5] INTEGER (0..99),
   startRB-PSCCH-Pool-r14 [6] INTEGER (0..99) OPTIONAL, -- Need OR
   rxParametersNCell-r14 [7] SEQUENCE {
      tdd-Config-r14 [0] TDD-Config OPTIONAL, -- Need OP
      syncConfigIndex-r14 [1] INTEGER (0..15)
   } OPTIONAL, -- Need OR
   dataTxParameters-r14 [8] SL-TxParameters-r12 OPTIONAL, -- Cond Tx
   zoneID-r14 [9] INTEGER (0..7) OPTIONAL, -- Need OR
   threshS-RSSI-CBR-r14 [10] INTEGER (0..45) OPTIONAL, -- Need OR
   poolReportId-r14 [11] SL-V2X-TxPoolReportIdentity-r14 OPTIONAL, -- Need OR
   cbr-pssch-TxConfigList-r14 [12] SL-CBR-PPPP-TxConfigList-r14 OPTIONAL, -- Need OR
   resourceSelectionConfigP2X-r14 [13] SL-P2X-ResourceSelectionConfig-r14
       OPTIONAL, -- Cond P2X
   syncAllowed-r14 [14] SL-SyncAllowed-r14 OPTIONAL, -- Need OR
   restrictResourceReservationPeriod-r14 [15] 
      SL-RestrictResourceReservationPeriodList-r14 OPTIONAL,
   ...,
   [[
      sl-MinT2ValueList-r15 [16] SL-MinT2ValueList-r15 OPTIONAL,
      cbr-pssch-TxConfigList-v1530 [17] SL-CBR-PPPP-TxConfigList-v1530 OPTIONAL
   ]]
}

SL-CommRxPoolListV2X-r14 ::= SEQUENCE (SIZE (1..maxSL-V2X-RxPool-r14)) OF SL-CommResourcePoolV2X-r14
   

SL-CommTxPoolListV2X-r14 ::= SEQUENCE (SIZE (1..maxSL-V2X-TxPool-r14)) OF SL-CommResourcePoolV2X-r14
   

SL-SyncConfigListV2X-r14 ::= SEQUENCE (SIZE (1..maxSL-V2X-SyncConfig-r14)) OF SL-SyncConfig-r12

PLMN-IdentityInfo ::= SEQUENCE {
   plmn-Identity [0] PLMN-Identity,
   cellReservedForOperatorUse [1] ENUMERATED { reserved(0), notReserved(1) }
}

PLMN-IdentityList ::= SEQUENCE (SIZE (1..maxPLMN-r11)) OF PLMN-IdentityInfo

SL-TypeTxSync-r14 ::= ENUMERATED { gnss(0), enb(1), ue(2) }

SL-SyncConfigListNFreqV2X-r14 ::= SEQUENCE (SIZE (1..maxSL-V2X-SyncConfig-r14)) OF 
   SL-SyncConfigNFreq-r13

SL-TxPower-r14 ::= CHOICE {
   minusinfinity-r14 [0] NULL,
   txPower-r14 [1] INTEGER (-41..31)
}

SL-PSSCH-TxParameters-r14 ::= SEQUENCE {
   minMCS-PSSCH-r14 [0] INTEGER (0..31),
   maxMCS-PSSCH-r14 [1] INTEGER (0..31),
   minSubChannel-NumberPSSCH-r14 [2] INTEGER (1..20),
   maxSubchannel-NumberPSSCH-r14 [3] INTEGER (1..20),
   allowedRetxNumberPSSCH-r14 [4] ENUMERATED { n0(0), n1(1), both(2), spare1(3)
       },
   maxTxPower-r14 [5] EXPLICIT SL-TxPower-r14 OPTIONAL -- Cond CBR
}

SL-PSSCH-TxParameters-v1530 ::= SEQUENCE {
   minMCS-PSSCH-r15 [0] INTEGER (0..31),
   maxMCS-PSSCH-r15 [1] INTEGER (0..31)
}

SL-PSSCH-TxConfig-r14 ::= SEQUENCE {
   typeTxSync-r14 [0] SL-TypeTxSync-r14 OPTIONAL, -- Need OR
   thresUE-Speed-r14 [1] ENUMERATED { kmph60(0), kmph80(1), kmph100(2), 
      kmph120(3), kmph140(4), kmph160(5), kmph180(6), kmph200(7) },
   parametersAboveThres-r14 [2] SL-PSSCH-TxParameters-r14,
   parametersBelowThres-r14 [3] SL-PSSCH-TxParameters-r14,
   ...,
   [[
      parametersAboveThres-v1530 [4] SL-PSSCH-TxParameters-v1530 OPTIONAL,
      parametersBelowThres-v1530 [5] SL-PSSCH-TxParameters-v1530 OPTIONAL
   ]]
}

SL-PSSCH-TxConfigList-r14 ::= SEQUENCE (SIZE (1..maxPSSCH-TxConfig-r14)) OF SL-PSSCH-TxConfig-r14

SL-ThresPSSCH-RSRP-r14 ::= INTEGER (0..66)

SL-ThresPSSCH-RSRP-List-r14 ::= SEQUENCE (SIZE (64)) OF SL-ThresPSSCH-RSRP-r14

SL-CommTxPoolSensingConfig-r14 ::= SEQUENCE {
   pssch-TxConfigList-r14 [0] SL-PSSCH-TxConfigList-r14,
   thresPSSCH-RSRP-List-r14 [1] SL-ThresPSSCH-RSRP-List-r14,
   restrictResourceReservationPeriod-r14 [2] 
      SL-RestrictResourceReservationPeriodList-r14 OPTIONAL, -- Need OR
   probResourceKeep-r14 [3] ENUMERATED { v0(0), v0dot2(1), v0dot4(2), v0dot6(3)
      , v0dot8(4), spare3(5), spare2(6), spare1(7) },
   p2x-SensingConfig-r14 [4] SEQUENCE {
      minNumCandidateSF-r14 [0] INTEGER (1..13),
      gapCandidateSensing-r14 [1] BIT STRING  (SIZE (10))
   } OPTIONAL, -- Need OR
   sl-ReselectAfter-r14 [5] ENUMERATED { n1(0), n2(1), n3(2), n4(3), n5(4), 
      n6(5), n7(6), n8(7), n9(8), spare7(9), spare6(10), spare5(11), spare4(12)
      , spare3(13), spare2(14), spare1(15) } OPTIONAL -- Need OR
}

SL-ZoneConfig-r14 ::= SEQUENCE {
   zoneLength-r14 [0] ENUMERATED { m5(0), m10(1), m20(2), m50(3), m100(4), 
      m200(5), m500(6), spare1(7) },
   zoneWidth-r14 [1] ENUMERATED { m5(0), m10(1), m20(2), m50(3), m100(4), 
      m200(5), m500(6), spare1(7) },
   zoneIdLongiMod-r14 [2] INTEGER (1..4),
   zoneIdLatiMod-r14 [3] INTEGER (1..4)
}

SL-V2X-InterFreqUE-Config-r14 ::= SEQUENCE {
   physCellIdList-r14 [0] PhysCellIdList-r13 OPTIONAL, -- Need OR
   typeTxSync-r14 [1] SL-TypeTxSync-r14 OPTIONAL, -- Need OR
   v2x-SyncConfig-r14 [2] SL-SyncConfigListNFreqV2X-r14 OPTIONAL, -- Need OR
   v2x-CommRxPool-r14 [3] SL-CommRxPoolListV2X-r14 OPTIONAL, -- Need OR
   v2x-CommTxPoolNormal-r14 [4] SL-CommTxPoolListV2X-r14 OPTIONAL, -- Need OR
   p2x-CommTxPoolNormal-r14 [5] SL-CommTxPoolListV2X-r14 OPTIONAL, -- Need OR
   v2x-CommTxPoolExceptional-r14 [6] SL-CommResourcePoolV2X-r14 OPTIONAL, -- Need OR
   v2x-ResourceSelectionConfig-r14 [7] SL-CommTxPoolSensingConfig-r14 OPTIONAL,
       -- Need OR
   zoneConfig-r14 [8] SL-ZoneConfig-r14 OPTIONAL, -- Need OR
   offsetDFN-r14 [9] INTEGER (0..1000) OPTIONAL,
   ...
}

SL-V2X-UE-ConfigList-r14 ::= SEQUENCE (SIZE (1..maxCellIntra)) OF 
   SL-V2X-InterFreqUE-Config-r14

SL-CBR-r14 ::= INTEGER (0..100)

SL-V2X-FreqSelectionConfig-r15 ::= SEQUENCE {
   priorityList-r15 [0] SL-PriorityList-r13,
   threshCBR-FreqReselection-r15 [1] SL-CBR-r14 OPTIONAL, -- Need OR
   threshCBR-FreqKeeping-r15 [2] SL-CBR-r14 OPTIONAL -- Need OR
}

SL-V2X-FreqSelectionConfigList-r15 ::= SEQUENCE (SIZE (1..8)) OF 
   SL-V2X-FreqSelectionConfig-r15

SL-InterFreqInfoV2X-r14 ::= SEQUENCE {
   plmn-IdentityList-r14 [0] PLMN-IdentityList OPTIONAL, -- Need OP
   v2x-CommCarrierFreq-r14 [1] ARFCN-ValueEUTRA-r9,
   sl-MaxTxPower-r14 [2] P-Max OPTIONAL, -- Need OR
   sl-Bandwidth-r14 [3] ENUMERATED { n6(0), n15(1), n25(2), n50(3), n75(4), 
      n100(5) } OPTIONAL, -- Need OR
   v2x-SchedulingPool-r14 [4] SL-CommResourcePoolV2X-r14 OPTIONAL, -- Need OR
   v2x-UE-ConfigList-r14 [5] SL-V2X-UE-ConfigList-r14 OPTIONAL,
   ...,
   [[
      additionalSpectrumEmissionV2X-r14 [6] EXPLICIT CHOICE {
         additionalSpectrumEmission-r14 [0] AdditionalSpectrumEmission,
         additionalSpectrumEmission-v1440 [1] AdditionalSpectrumEmission-v10l0
      } OPTIONAL
   ]],
   [[
      v2x-FreqSelectionConfigList-r15 [7] SL-V2X-FreqSelectionConfigList-r15
          OPTIONAL
   ]]
}

SL-InterFreqInfoListV2X-r14 ::= SEQUENCE (SIZE (0..maxFreqV2X-1-r14)) OF SL-InterFreqInfoV2X-r14
   

SL-AnchorCarrierFreqList-V2X-r14 ::= SEQUENCE (SIZE (1..maxFreqV2X-r14)) OF 
   ARFCN-ValueEUTRA-r9

SL-CBR-Levels-Config-r14 ::= SEQUENCE (SIZE (1..maxCBR-Level-r14)) OF SL-CBR-r14

SL-CBR-PSSCH-TxConfig-r14 ::= SEQUENCE {
   cr-Limit-r14 [0] INTEGER (0..10000),
   tx-Parameters-r14 [1] SL-PSSCH-TxParameters-r14
}

SL-CBR-CommonTxConfigList-r14 ::= SEQUENCE {
   cbr-RangeCommonConfigList-r14 [0] SEQUENCE (SIZE (1..maxSL-V2X-CBRConfig-r14)) OF 
      SL-CBR-Levels-Config-r14,
   sl-CBR-PSSCH-TxConfigList-r14 [1] SEQUENCE (SIZE (1..maxSL-V2X-TxConfig-r14)) OF 
      SL-CBR-PSSCH-TxConfig-r14
}

SL-V2X-ConfigCommon-r14 ::= SEQUENCE {
   v2x-CommRxPool-r14 [0] SL-CommRxPoolListV2X-r14 OPTIONAL, -- Need OR
   v2x-CommTxPoolNormalCommon-r14 [1] SL-CommTxPoolListV2X-r14 OPTIONAL, -- Need OR
   p2x-CommTxPoolNormalCommon-r14 [2] SL-CommTxPoolListV2X-r14 OPTIONAL, -- Need OR
   v2x-CommTxPoolExceptional-r14 [3] SL-CommResourcePoolV2X-r14 OPTIONAL, -- Need OR
   v2x-SyncConfig-r14 [4] SL-SyncConfigListV2X-r14 OPTIONAL, -- Need OR
   v2x-InterFreqInfoList-r14 [5] SL-InterFreqInfoListV2X-r14 OPTIONAL, -- Need OR
   v2x-ResourceSelectionConfig-r14 [6] SL-CommTxPoolSensingConfig-r14 OPTIONAL,
       -- Need OR
   zoneConfig-r14 [7] SL-ZoneConfig-r14 OPTIONAL, -- Need OR
   typeTxSync-r14 [8] SL-TypeTxSync-r14 OPTIONAL, -- Need OR
   thresSL-TxPrioritization-r14 [9] SL-Priority-r13 OPTIONAL, -- Need OR
   anchorCarrierFreqList-r14 [10] SL-AnchorCarrierFreqList-V2X-r14 OPTIONAL, -- Need OR
   offsetDFN-r14 [11] INTEGER (0..1000) OPTIONAL, -- Need OR
   cbr-CommonTxConfigList-r14 [12] SL-CBR-CommonTxConfigList-r14 OPTIONAL -- Need OR
}

SystemInformationBlockType21-r14 ::= SEQUENCE {
   sl-V2X-ConfigCommon-r14 [0] SL-V2X-ConfigCommon-r14 OPTIONAL, -- Need OR
   lateNonCriticalExtension [1] OCTET STRING OPTIONAL,
   ...
}

ARFCN-ValueNR-r15 ::= INTEGER (0..3279165)

FreqBandIndicatorNR-r15 ::= INTEGER (1..maxFBI-NR-r15)

MultiFrequencyBandListNR-r15 ::= SEQUENCE (SIZE (1..maxMultiBandsNR-r15)) OF 
   FreqBandIndicatorNR-r15

MTC-SSB-NR-r15 ::= SEQUENCE {
   periodicityAndOffset-r15 [0] EXPLICIT CHOICE {
      sf5-r15 [0] INTEGER (0..4),
      sf10-r15 [1] INTEGER (0..9),
      sf20-r15 [2] INTEGER (0..19),
      sf40-r15 [3] INTEGER (0..39),
      sf80-r15 [4] INTEGER (0..79),
      sf160-r15 [5] INTEGER (0..159)
   },
   ssb-Duration-r15 [1] ENUMERATED { sf1(0), sf2(1), sf3(2), sf4(3), sf5(4) }
}

SS-RSSI-Measurement-r15 ::= SEQUENCE {
   measurementSlots-r15 [0] BIT STRING  (SIZE (1..80)),
   endSymbol-r15 [1] INTEGER (0..3)
}

P-MaxNR-r15 ::= INTEGER (-30..33)

AdditionalSpectrumEmissionNR-r15 ::= INTEGER (0..7)

NS-PmaxValueNR-r15 ::= SEQUENCE {
   additionalPmaxNR-r15 [0] P-MaxNR-r15 OPTIONAL, -- Need ON
   additionalSpectrumEmissionNR-r15 [1] AdditionalSpectrumEmissionNR-r15
}

NS-PmaxListNR-r15 ::= SEQUENCE (SIZE (1..8)) OF NS-PmaxValueNR-r15

MaxRS-IndexCellQualNR-r15 ::= INTEGER (1..maxRS-IndexCellQual-r15)

RSRP-RangeNR-r15 ::= INTEGER (0..127)

RSRQ-RangeNR-r15 ::= INTEGER (0..127)

RS-SINR-RangeNR-r15 ::= INTEGER (0..127)

ThresholdListNR-r15 ::= SEQUENCE {
   nr-RSRP-r15 [0] RSRP-RangeNR-r15 OPTIONAL, -- Need OR
   nr-RSRQ-r15 [1] RSRQ-RangeNR-r15 OPTIONAL, -- Need OR
   nr-SINR-r15 [2] RS-SINR-RangeNR-r15 OPTIONAL -- Need OR
}

MultiBandNsPmaxListNR-1-v1550 ::= SEQUENCE (SIZE (1..maxMultiBandsNR-1-r15)) OF NS-PmaxListNR-r15

MultiBandNsPmaxListNR-v1550 ::= SEQUENCE (SIZE (1..maxMultiBandsNR-r15)) OF NS-PmaxListNR-r15

SSB-ToMeasure-r15 ::= CHOICE {
   shortBitmap-r15 [0] BIT STRING  (SIZE (4)),
   mediumBitmap-r15 [1] BIT STRING  (SIZE (8)),
   longBitmap-r15 [2] BIT STRING  (SIZE (64))
}

CarrierFreqNR-r15 ::= SEQUENCE {
   carrierFreq-r15 [0] ARFCN-ValueNR-r15,
   multiBandInfoList-r15 [1] MultiFrequencyBandListNR-r15 OPTIONAL, -- Need OR
   multiBandInfoListSUL-r15 [2] MultiFrequencyBandListNR-r15 OPTIONAL, -- Need OR
   measTimingConfig-r15 [3] MTC-SSB-NR-r15 OPTIONAL, -- Need OR
   subcarrierSpacingSSB-r15 [4] ENUMERATED { kHz15(0), kHz30(1), kHz120(2), 
      kHz240(3) },
   ss-RSSI-Measurement-r15 [5] SS-RSSI-Measurement-r15 OPTIONAL, -- Cond RSRQ2
   cellReselectionPriority-r15 [6] CellReselectionPriority OPTIONAL, -- Need OP
   cellReselectionSubPriority-r15 [7] CellReselectionSubPriority-r13 OPTIONAL, -- Need OR
   threshX-High-r15 [8] ReselectionThreshold,
   threshX-Low-r15 [9] ReselectionThreshold,
   threshX-Q-r15 [10] SEQUENCE {
      threshX-HighQ-r15 [0] ReselectionThresholdQ-r9,
      threshX-LowQ-r15 [1] ReselectionThresholdQ-r9
   } OPTIONAL, -- Cond RSRQ
   q-RxLevMin-r15 [11] INTEGER (-70..-22),
   q-RxLevMinSUL-r15 [12] INTEGER (-70..-22) OPTIONAL, -- Need OR
   p-MaxNR-r15 [13] P-MaxNR-r15,
   ns-PmaxListNR-r15 [14] NS-PmaxListNR-r15 OPTIONAL, -- Need OR
   q-QualMin-r15 [15] INTEGER (-43..-12) OPTIONAL, -- Need OP
   deriveSSB-IndexFromCell-r15 [16] BOOLEAN,
   maxRS-IndexCellQual-r15 [17] MaxRS-IndexCellQualNR-r15 OPTIONAL, -- Need OR
   threshRS-Index-r15 [18] ThresholdListNR-r15 OPTIONAL,
   ...,
   [[
      multiBandNsPmaxListNR-v1550 [19] MultiBandNsPmaxListNR-1-v1550 OPTIONAL,
      multiBandNsPmaxListNR-SUL-v1550 [20] MultiBandNsPmaxListNR-v1550 OPTIONAL
         ,
      ssb-ToMeasure-r15 [21] EXPLICIT SSB-ToMeasure-r15 OPTIONAL
   ]]
}

CarrierFreqListNR-r15 ::= SEQUENCE (SIZE (1..maxFreq)) OF CarrierFreqNR-r15

SystemInformationBlockType24-r15 ::= SEQUENCE {
   carrierFreqListNR-r15 [0] CarrierFreqListNR-r15 OPTIONAL, -- Need OR
   t-ReselectionNR-r15 [1] T-Reselection,
   t-ReselectionNR-SF-r15 [2] SpeedStateScaleFactors OPTIONAL, -- Need OR
   lateNonCriticalExtension [3] OCTET STRING OPTIONAL,
   ...
}

UAC-BarringInfoSetIndex-r15 ::= INTEGER (1..maxBarringInfoSet-r15)

UAC-BarringPerCat-r15 ::= SEQUENCE {
   accessCategory-r15 [0] INTEGER (1..maxAccessCat-1-r15),
   uac-barringInfoSetIndex-r15 [1] UAC-BarringInfoSetIndex-r15
}

UAC-BarringPerCatList-r15 ::= SEQUENCE (SIZE (1..maxAccessCat-1-r15)) OF UAC-BarringPerCat-r15

UAC-BarringPerPLMN-r15 ::= SEQUENCE {
   plmn-IdentityIndex-r15 [0] INTEGER (1..maxPLMN-r11),
   uac-AC-BarringListType-r15 [1] EXPLICIT CHOICE {
      uac-ImplicitAC-BarringList-r15 [0] SEQUENCE (SIZE (maxAccessCat-1-r15)) OF 
         UAC-BarringInfoSetIndex-r15,
      uac-ExplicitAC-BarringList-r15 [1] UAC-BarringPerCatList-r15
   } OPTIONAL -- Need OR
}

UAC-BarringPerPLMN-List-r15 ::= SEQUENCE (SIZE (1..maxPLMN-r11)) OF UAC-BarringPerPLMN-r15

UAC-BarringInfoSet-r15 ::= SEQUENCE {
   uac-BarringFactor-r15 [0] ENUMERATED { p00(0), p05(1), p10(2), p15(3), 
      p20(4), p25(5), p30(6), p40(7), p50(8), p60(9), p70(10), p75(11), p80(12)
      , p85(13), p90(14), p95(15) },
   uac-BarringTime-r15 [1] ENUMERATED { s4(0), s8(1), s16(2), s32(3), s64(4), 
      s128(5), s256(6), s512(7) },
   uac-BarringForAccessIdentity-r15 [2] BIT STRING  (SIZE (7))
}

UAC-BarringInfoSetList-r15 ::= SEQUENCE (SIZE (1..maxBarringInfoSet-r15)) OF UAC-BarringInfoSet-r15

UAC-AC1-SelectAssistInfo-r15 ::= ENUMERATED { a(0), b(1), c(2) }

SystemInformationBlockType25-r15 ::= SEQUENCE {
   uac-BarringForCommon-r15 [0] UAC-BarringPerCatList-r15 OPTIONAL, -- Need OP
   uac-BarringPerPLMN-List-r15 [1] UAC-BarringPerPLMN-List-r15 OPTIONAL, -- Need OP
   uac-BarringInfoSetList-r15 [2] UAC-BarringInfoSetList-r15,
   uac-AC1-SelectAssistInfo-r15 [3] EXPLICIT CHOICE {
      plmnCommon-r15 [0] UAC-AC1-SelectAssistInfo-r15,
      individualPLMNList-r15 [1] SEQUENCE (SIZE (2..maxPLMN-r11)) OF 
         UAC-AC1-SelectAssistInfo-r15
   } OPTIONAL, -- Need OR
   lateNonCriticalExtension [4] OCTET STRING OPTIONAL,
   ...
}

SL-PPPP-TxConfigIndex-r15 ::= SEQUENCE {
   priorityThreshold-r15 [0] SL-Priority-r13,
   defaultTxConfigIndex-r15 [1] INTEGER (0..maxCBR-Level-1-r14),
   cbr-ConfigIndex-r15 [2] INTEGER (0..maxSL-V2X-CBRConfig-1-r14),
   tx-ConfigIndexList-r15 [3] SEQUENCE (SIZE (1..maxCBR-Level-r14)) OF Tx-ConfigIndex-r14,
   mcs-PSSCH-RangeList-r15 [4] SEQUENCE (SIZE (1..maxCBR-Level-r14)) OF MCS-PSSCH-Range-r15
}

SL-CBR-PPPP-TxConfigList-r15 ::= SEQUENCE (SIZE (1..8)) OF 
   SL-PPPP-TxConfigIndex-r15

SL-Reliability-r15 ::= INTEGER (1..8)

SL-DestinationInfoList-r12 ::= SEQUENCE (SIZE (1..maxSL-Dest-r12)) OF 
   SL-DestinationIdentity-r12

SL-AllowedCarrierFreqList-r15 ::= SEQUENCE {
   allowedCarrierFreqSet1 [0] SEQUENCE (SIZE (1..maxFreqV2X-r14)) OF ARFCN-ValueEUTRA-r9,
   allowedCarrierFreqSet2 [1] SEQUENCE (SIZE (1..maxFreqV2X-r14)) OF ARFCN-ValueEUTRA-r9
}

SL-PPPR-Dest-CarrierFreq ::= SEQUENCE {
   destinationInfoList-r15 [0] SL-DestinationInfoList-r12 OPTIONAL, -- Need OR
   allowedCarrierFreqList-r15 [1] SL-AllowedCarrierFreqList-r15 OPTIONAL -- Need OR
}

SL-PPPR-Dest-CarrierFreqList-r15 ::= SEQUENCE (SIZE (1..maxSL-Dest-r12)) OF 
   SL-PPPR-Dest-CarrierFreq

SL-V2X-PacketDuplicationConfig-r15 ::= SEQUENCE {
   threshSL-Reliability-r15 [0] SL-Reliability-r15,
   allowedCarrierFreqConfig-r15 [1] SL-PPPR-Dest-CarrierFreqList-r15 OPTIONAL,
   ...
}

SL-V2X-SyncFreqList-r15 ::= SEQUENCE (SIZE (1..maxFreqV2X-r14)) OF ARFCN-ValueEUTRA-r9

SystemInformationBlockType26-r15 ::= SEQUENCE {
   v2x-InterFreqInfoList-r15 [0] SL-InterFreqInfoListV2X-r14 OPTIONAL, -- Need OR
   cbr-pssch-TxConfigList-r15 [1] SL-CBR-PPPP-TxConfigList-r15 OPTIONAL, -- Need OR
   v2x-PacketDuplicationConfig-r15 [2] SL-V2X-PacketDuplicationConfig-r15
       OPTIONAL, -- Need OR
   syncFreqList-r15 [3] SL-V2X-SyncFreqList-r15 OPTIONAL, -- Need OR
   slss-TxMultiFreq-r15 [4] ENUMERATED { true(0) } OPTIONAL, -- Need OR
   v2x-FreqSelectionConfigList-r15 [5] SL-V2X-FreqSelectionConfigList-r15
       OPTIONAL, -- Need OR
   threshS-RSSI-CBR-r14 [6] INTEGER (0..45) OPTIONAL,
   ...
}

SystemInformation-v8a0-IEs ::= SEQUENCE {
   lateNonCriticalExtension [0] OCTET STRING OPTIONAL,
   nonCriticalExtension [1] SEQUENCE {

   } OPTIONAL
}

SystemInformation-r8-IEs ::= SEQUENCE {
   sib-TypeAndInfo [0] SEQUENCE (SIZE (1..maxSIB)) OF CHOICE {
      sib2 [0] SystemInformationBlockType2,
      sib3 [1] SystemInformationBlockType3,
      sib4 [2] SystemInformationBlockType4,
      sib5 [3] SystemInformationBlockType5,
      sib6 [4] SystemInformationBlockType6,
      sib7 [5] SystemInformationBlockType7,
      sib8 [6] SystemInformationBlockType8,
      sib9 [7] SystemInformationBlockType9,
      sib10 [8] SystemInformationBlockType10,
      sib11 [9] SystemInformationBlockType11,
      ...,
      sib12-v920 [10] SystemInformationBlockType12-r9,
      sib13-v920 [11] SystemInformationBlockType13-r9,
      sib14-v1130 [12] SystemInformationBlockType14-r11,
      sib15-v1130 [13] SystemInformationBlockType15-r11,
      sib16-v1130 [14] SystemInformationBlockType16-r11,
      sib17-v1250 [15] SystemInformationBlockType17-r12,
      sib18-v1250 [16] SystemInformationBlockType18-r12,
      sib19-v1250 [17] SystemInformationBlockType19-r12,
      sib20-v1310 [18] SystemInformationBlockType20-r13,
      sib21-v1430 [19] SystemInformationBlockType21-r14,
      sib24-v1530 [20] SystemInformationBlockType24-r15,
      sib25-v1530 [21] SystemInformationBlockType25-r15,
      sib26-v1530 [22] SystemInformationBlockType26-r15
   },
   nonCriticalExtension [1] SystemInformation-v8a0-IEs OPTIONAL
}

SystemInformationBlockPos-r15 ::= SEQUENCE {
   assistanceDataSIB-Element-r15 [0] OCTET STRING,
   lateNonCriticalExtension [1] OCTET STRING OPTIONAL,
   ...
}

PosSystemInformation-r15-IEs ::= SEQUENCE {
   posSIB-TypeAndInfo-r15 [0] SEQUENCE (SIZE (1..maxSIB)) OF CHOICE {
      posSib1-1-r15 [0] SystemInformationBlockPos-r15,
      posSib1-2-r15 [1] SystemInformationBlockPos-r15,
      posSib1-3-r15 [2] SystemInformationBlockPos-r15,
      posSib1-4-r15 [3] SystemInformationBlockPos-r15,
      posSib1-5-r15 [4] SystemInformationBlockPos-r15,
      posSib1-6-r15 [5] SystemInformationBlockPos-r15,
      posSib1-7-r15 [6] SystemInformationBlockPos-r15,
      posSib2-1-r15 [7] SystemInformationBlockPos-r15,
      posSib2-2-r15 [8] SystemInformationBlockPos-r15,
      posSib2-3-r15 [9] SystemInformationBlockPos-r15,
      posSib2-4-r15 [10] SystemInformationBlockPos-r15,
      posSib2-5-r15 [11] SystemInformationBlockPos-r15,
      posSib2-6-r15 [12] SystemInformationBlockPos-r15,
      posSib2-7-r15 [13] SystemInformationBlockPos-r15,
      posSib2-8-r15 [14] SystemInformationBlockPos-r15,
      posSib2-9-r15 [15] SystemInformationBlockPos-r15,
      posSib2-10-r15 [16] SystemInformationBlockPos-r15,
      posSib2-11-r15 [17] SystemInformationBlockPos-r15,
      posSib2-12-r15 [18] SystemInformationBlockPos-r15,
      posSib2-13-r15 [19] SystemInformationBlockPos-r15,
      posSib2-14-r15 [20] SystemInformationBlockPos-r15,
      posSib2-15-r15 [21] SystemInformationBlockPos-r15,
      posSib2-16-r15 [22] SystemInformationBlockPos-r15,
      posSib2-17-r15 [23] SystemInformationBlockPos-r15,
      posSib2-18-r15 [24] SystemInformationBlockPos-r15,
      posSib2-19-r15 [25] SystemInformationBlockPos-r15,
      posSib3-1-r15 [26] SystemInformationBlockPos-r15,
      ...
   },
   lateNonCriticalExtension [1] OCTET STRING OPTIONAL,
   nonCriticalExtension [2] SEQUENCE {

   } OPTIONAL
}

SystemInformation ::= SEQUENCE {
   criticalExtensions [0] EXPLICIT CHOICE {
      systemInformation-r8 [0] SystemInformation-r8-IEs,
      criticalExtensionsFuture-r15 [1] EXPLICIT CHOICE {
         posSystemInformation-r15 [0] PosSystemInformation-r15-IEs,
         criticalExtensionsFuture [1] SEQUENCE {

         }
      }
   }
}

SystemInformation-BR-r13 ::= SystemInformation

SystemInformation-MBMS-r14 ::= SystemInformation

TrackingAreaCode ::= BIT STRING  (SIZE (16))

CellIdentity ::= BIT STRING  (SIZE (28))

CSG-Identity ::= BIT STRING  (SIZE (27))

SIB-Type ::= ENUMERATED { sibType3(0), sibType4(1), sibType5(2), sibType6(3), 
   sibType7(4), sibType8(5), sibType9(6), sibType10(7), sibType11(8), 
   sibType12-v920(9), sibType13-v920(10), sibType14-v1130(11), 
   sibType15-v1130(12), sibType16-v1130(13), sibType17-v1250(14), 
   sibType18-v1250(15), ..., sibType19-v1250(16), sibType20-v1310(17), 
   sibType21-v1430(18), sibType24-v1530(19), sibType25-v1530(20), 
   sibType26-v1530(21) }

SIB-MappingInfo ::= SEQUENCE (SIZE (0..maxSIB-1)) OF SIB-Type

SchedulingInfo ::= SEQUENCE {
   si-Periodicity [0] ENUMERATED { rf8(0), rf16(1), rf32(2), rf64(3), rf128(4)
      , rf256(5), rf512(6) },
   sib-MappingInfo [1] SIB-MappingInfo
}

SchedulingInfoList ::= SEQUENCE (SIZE (1..maxSI-Message)) OF SchedulingInfo

SystemInformationBlockType1-v10l0-IEs ::= SEQUENCE {
   freqBandInfo-v10l0 [0] NS-PmaxList-v10l0 OPTIONAL, -- Need OR
   multiBandInfoList-v10l0 [1] MultiBandInfoList-v10l0 OPTIONAL, -- Need OR
   nonCriticalExtension [2] SEQUENCE {

   } OPTIONAL
}

SystemInformationBlockType1-v10j0-IEs ::= SEQUENCE {
   freqBandInfo-r10 [0] NS-PmaxList-r10 OPTIONAL, -- Need OR
   multiBandInfoList-v10j0 [1] MultiBandInfoList-v10j0 OPTIONAL, -- Need OR
   nonCriticalExtension [2] SystemInformationBlockType1-v10l0-IEs OPTIONAL
}

SystemInformationBlockType1-v9e0-IEs ::= SEQUENCE {
   freqBandIndicator-v9e0 [0] FreqBandIndicator-v9e0 OPTIONAL, -- Cond FBI-max
   multiBandInfoList-v9e0 [1] MultiBandInfoList-v9e0 OPTIONAL, -- Cond mFBI-max
   nonCriticalExtension [2] SystemInformationBlockType1-v10j0-IEs OPTIONAL
}

-- Late non critical extensions
SystemInformationBlockType1-v8h0-IEs ::= SEQUENCE {
   multiBandInfoList [0] MultiBandInfoList OPTIONAL, -- Need OR
   nonCriticalExtension [1] SystemInformationBlockType1-v9e0-IEs OPTIONAL
}

CellSelectionInfo-v920 ::= SEQUENCE {
   q-QualMin-r9 [0] Q-QualMin-r9,
   q-QualMinOffset-r9 [1] INTEGER (1..8) OPTIONAL -- Need OP
}

CellSelectionInfo-v1130 ::= SEQUENCE {
   q-QualMinWB-r11 [0] Q-QualMin-r9
}

CellSelectionInfo-v1250 ::= SEQUENCE {
   q-QualMinRSRQ-OnAllSymbols-r12 [0] Q-QualMin-r9
}

SchedulingInfo-BR-r13 ::= SEQUENCE {
   si-Narrowband-r13 [0] INTEGER (1..maxAvailNarrowBands-r13),
   si-TBS-r13 [1] ENUMERATED { b152(0), b208(1), b256(2), b328(3), b408(4), 
      b504(5), b600(6), b712(7), b808(8), b936(9) }
}

SchedulingInfoList-BR-r13 ::= SEQUENCE (SIZE (1..maxSI-Message)) OF SchedulingInfo-BR-r13

SystemInfoValueTagSI-r13 ::= INTEGER (0..3)

SystemInfoValueTagList-r13 ::= SEQUENCE (SIZE (1..maxSI-Message)) OF SystemInfoValueTagSI-r13
   

TDD-Config-v1430 ::= SEQUENCE {
   specialSubframePatterns-v1430 [0] ENUMERATED { ssp10(0) }
}

CellAccessRelatedInfo-r14 ::= SEQUENCE {
   plmn-IdentityList-r14 [0] PLMN-IdentityList,
   trackingAreaCode-r14 [1] TrackingAreaCode,
   cellIdentity-r14 [2] CellIdentity
}

TDD-Config-v1450 ::= SEQUENCE {
   specialSubframePatterns-v1450 [0] ENUMERATED { ssp10-CRS-LessDwPTS(0) }
}

PLMN-IdentityInfo-v1530 ::= SEQUENCE {
   cellReservedForOperatorUse-CRS-r15 [0] ENUMERATED { reserved(0), 
      notReserved(1) }
}

PLMN-IdentityList-v1530 ::= SEQUENCE (SIZE (1..maxPLMN-r11)) OF PLMN-IdentityInfo-v1530

GNSS-ID-r15 ::= SEQUENCE {
   gnss-id-r15 [0] ENUMERATED { gps(0), sbas(1), qzss(2), galileo(3), 
      glonass(4), bds(5), ... },
   ...
}

SBAS-ID-r15 ::= SEQUENCE {
   sbas-id-r15 [0] ENUMERATED { waas(0), egnos(1), msas(2), gagan(3), ... },
   ...
}

PosSIB-Type-r15 ::= SEQUENCE {
   encrypted-r15 [0] ENUMERATED { true(0) } OPTIONAL, -- Need OP
   gnss-id-r15 [1] GNSS-ID-r15 OPTIONAL, -- Need OP
   sbas-id-r15 [2] SBAS-ID-r15 OPTIONAL, -- Need OP
   posSibType-r15 [3] ENUMERATED { posSibType1-1(0), posSibType1-2(1), 
      posSibType1-3(2), posSibType1-4(3), posSibType1-5(4), posSibType1-6(5), 
      posSibType1-7(6), posSibType2-1(7), posSibType2-2(8), posSibType2-3(9), 
      posSibType2-4(10), posSibType2-5(11), posSibType2-6(12), 
      posSibType2-7(13), posSibType2-8(14), posSibType2-9(15), 
      posSibType2-10(16), posSibType2-11(17), posSibType2-12(18), 
      posSibType2-13(19), posSibType2-14(20), posSibType2-15(21), 
      posSibType2-16(22), posSibType2-17(23), posSibType2-18(24), 
      posSibType2-19(25), posSibType3-1(26), ... },
   ...
}

PosSIB-MappingInfo-r15 ::= SEQUENCE (SIZE (1..maxSIB)) OF PosSIB-Type-r15

PosSchedulingInfo-r15 ::= SEQUENCE {
   posSI-Periodicity-r15 [0] ENUMERATED { rf8(0), rf16(1), rf32(2), rf64(3), 
      rf128(4), rf256(5), rf512(6) },
   posSIB-MappingInfo-r15 [1] PosSIB-MappingInfo-r15
}

PosSchedulingInfoList-r15 ::= SEQUENCE (SIZE (1..maxSI-Message)) OF PosSchedulingInfo-r15

PLMN-IdentityInfo-r15 ::= SEQUENCE {
   plmn-Identity-5GC-r15 [0] EXPLICIT CHOICE {
      plmn-Identity-r15 [0] PLMN-Identity,
      plmn-Index-r15 [1] INTEGER (1..maxPLMN-r11)
   },
   cellReservedForOperatorUse-r15 [1] ENUMERATED { reserved(0), notReserved(1)
       },
   cellReservedForOperatorUse-CRS-r15 [2] ENUMERATED { reserved(0), 
      notReserved(1) }
}

PLMN-IdentityList-r15 ::= SEQUENCE (SIZE (1..maxPLMN-r11)) OF PLMN-IdentityInfo-r15

RAN-AreaCode-r15 ::= INTEGER (0..255)

TrackingAreaCode-5GC-r15 ::= BIT STRING  (SIZE (24))

CellIdentity-5GC-r15 ::= CHOICE {
   cellIdentity-r15 [0] CellIdentity,
   cellId-Index-r15 [1] INTEGER (1..maxPLMN-r11)
}

CellAccessRelatedInfo-5GC-r15 ::= SEQUENCE {
   plmn-IdentityList-r15 [0] PLMN-IdentityList-r15,
   ran-AreaCode-r15 [1] RAN-AreaCode-r15 OPTIONAL, -- Need OR
   trackingAreaCode-5GC-r15 [2] TrackingAreaCode-5GC-r15,
   cellIdentity-5GC-r15 [3] EXPLICIT CellIdentity-5GC-r15
}

SystemInformationBlockType1-v1540-IEs ::= SEQUENCE {
   si-posOffset-r15 [0] ENUMERATED { true(0) } OPTIONAL, -- Need ON
   nonCriticalExtension [1] SEQUENCE {

   } OPTIONAL
}

SystemInformationBlockType1-v1530-IEs ::= SEQUENCE {
   hsdn-Cell-r15 [0] ENUMERATED { true(0) } OPTIONAL, -- Need OR
   cellSelectionInfoCE-v1530 [1] CellSelectionInfoCE-v1530 OPTIONAL, -- Need OP
   crs-IntfMitigConfig-r15 [2] EXPLICIT CHOICE {
      crs-IntfMitigEnabled-15 [0] NULL,
      crs-IntfMitigNumPRBs-r15 [1] ENUMERATED { n6(0), n24(1) }
   } OPTIONAL, -- Need OR
   cellBarred-CRS-r15 [3] ENUMERATED { barred(0), notBarred(1) },
   plmn-IdentityList-v1530 [4] PLMN-IdentityList-v1530 OPTIONAL, -- Need OR
   posSchedulingInfoList-r15 [5] PosSchedulingInfoList-r15 OPTIONAL, -- Need OR
   cellAccessRelatedInfo-5GC-r15 [6] SEQUENCE {
      cellBarred-5GC-r15 [0] ENUMERATED { barred(0), notBarred(1) },
      cellBarred-5GC-CRS-r15 [1] ENUMERATED { barred(0), notBarred(1) },
      cellAccessRelatedInfoList-5GC-r15 [2] SEQUENCE (SIZE (1..maxPLMN-r11)) OF 
         CellAccessRelatedInfo-5GC-r15
   } OPTIONAL, -- Need OP
   ims-EmergencySupport5GC-r15 [7] ENUMERATED { true(0) } OPTIONAL, -- Need OR
   eCallOverIMS-Support5GC-r15 [8] ENUMERATED { true(0) } OPTIONAL, -- Need OR
   nonCriticalExtension [9] SystemInformationBlockType1-v1540-IEs OPTIONAL
}

SystemInformationBlockType1-v1450-IEs ::= SEQUENCE {
   tdd-Config-v1450 [0] TDD-Config-v1450 OPTIONAL, -- Cond TDD-OR
   nonCriticalExtension [1] SystemInformationBlockType1-v1530-IEs OPTIONAL
}

SystemInformationBlockType1-v1430-IEs ::= SEQUENCE {
   eCallOverIMS-Support-r14 [0] ENUMERATED { true(0) } OPTIONAL, -- Need OR
   tdd-Config-v1430 [1] TDD-Config-v1430 OPTIONAL, -- Cond TDD-OR
   cellAccessRelatedInfoList-r14 [2] SEQUENCE (SIZE (1..maxPLMN-1-r14)) OF 
      CellAccessRelatedInfo-r14 OPTIONAL, -- Need OR
   nonCriticalExtension [3] SystemInformationBlockType1-v1450-IEs OPTIONAL
}

SystemInformationBlockType1-v1360-IEs ::= SEQUENCE {
   cellSelectionInfoCE1-v1360 [0] CellSelectionInfoCE1-v1360 OPTIONAL, -- Cond QrxlevminCE1
   nonCriticalExtension [1] SystemInformationBlockType1-v1430-IEs OPTIONAL
}

SystemInformationBlockType1-v1350-IEs ::= SEQUENCE {
   cellSelectionInfoCE1-r13 [0] CellSelectionInfoCE1-r13 OPTIONAL, -- Need OP
   nonCriticalExtension [1] SystemInformationBlockType1-v1360-IEs OPTIONAL
}

SystemInformationBlockType1-v1320-IEs ::= SEQUENCE {
   freqHoppingParametersDL-r13 [0] SEQUENCE {
      mpdcch-pdsch-HoppingNB-r13 [0] ENUMERATED { nb2(0), nb4(1) } OPTIONAL, -- Need OR
      interval-DLHoppingConfigCommonModeA-r13 [1] EXPLICIT CHOICE {
         interval-FDD-r13 [0] ENUMERATED { int1(0), int2(1), int4(2), int8(3) }
            ,
         interval-TDD-r13 [1] ENUMERATED { int1(0), int5(1), int10(2), int20(3)
             }
      } OPTIONAL, -- Need OR
      interval-DLHoppingConfigCommonModeB-r13 [2] EXPLICIT CHOICE {
         interval-FDD-r13 [0] ENUMERATED { int2(0), int4(1), int8(2), int16(3)
             },
         interval-TDD-r13 [1] ENUMERATED { int5(0), int10(1), int20(2), 
            int40(3) }
      } OPTIONAL, -- Need OR
      mpdcch-pdsch-HoppingOffset-r13 [3] INTEGER (1..maxAvailNarrowBands-r13) OPTIONAL -- Need OR
   } OPTIONAL, -- Cond Hopping
   nonCriticalExtension [1] SystemInformationBlockType1-v1350-IEs OPTIONAL
}

SystemInformationBlockType1-v1310-IEs ::= SEQUENCE {
   hyperSFN-r13 [0] BIT STRING  (SIZE (10)) OPTIONAL, -- Need OR
   eDRX-Allowed-r13 [1] ENUMERATED { true(0) } OPTIONAL, -- Need OR
   cellSelectionInfoCE-r13 [2] CellSelectionInfoCE-r13 OPTIONAL, -- Need OP
   bandwidthReducedAccessRelatedInfo-r13 [3] SEQUENCE {
      si-WindowLength-BR-r13 [0] ENUMERATED { ms20(0), ms40(1), ms60(2), 
         ms80(3), ms120(4), ms160(5), ms200(6), spare(7) },
      si-RepetitionPattern-r13 [1] ENUMERATED { everyRF(0), every2ndRF(1), 
         every4thRF(2), every8thRF(3) },
      schedulingInfoList-BR-r13 [2] SchedulingInfoList-BR-r13 OPTIONAL, -- Cond SI-BR
      fdd-DownlinkOrTddSubframeBitmapBR-r13 [3] EXPLICIT CHOICE {
         subframePattern10-r13 [0] BIT STRING  (SIZE (10)),
         subframePattern40-r13 [1] BIT STRING  (SIZE (40))
      } OPTIONAL, -- Need OP
      fdd-UplinkSubframeBitmapBR-r13 [4] BIT STRING  (SIZE (10)) OPTIONAL, -- Need OP
      startSymbolBR-r13 [5] INTEGER (1..4),
      si-HoppingConfigCommon-r13 [6] ENUMERATED { on(0), off(1) },
      si-ValidityTime-r13 [7] ENUMERATED { true(0) } OPTIONAL, -- Need OP
      systemInfoValueTagList-r13 [8] SystemInfoValueTagList-r13 OPTIONAL -- Need OR
   } OPTIONAL, -- Cond BW-reduced
   nonCriticalExtension [4] SystemInformationBlockType1-v1320-IEs OPTIONAL
}

SystemInformationBlockType1-v1250-IEs ::= SEQUENCE {
   cellAccessRelatedInfo-v1250 [0] SEQUENCE {
      category0Allowed-r12 [0] ENUMERATED { true(0) } OPTIONAL -- Need OP
   },
   cellSelectionInfo-v1250 [1] CellSelectionInfo-v1250 OPTIONAL, -- Cond RSRQ2
   freqBandIndicatorPriority-r12 [2] ENUMERATED { true(0) } OPTIONAL, -- Cond mFBI
   nonCriticalExtension [3] SystemInformationBlockType1-v1310-IEs OPTIONAL
}

SystemInformationBlockType1-v1130-IEs ::= SEQUENCE {
   tdd-Config-v1130 [0] TDD-Config-v1130 OPTIONAL, -- Cond TDD-OR
   cellSelectionInfo-v1130 [1] CellSelectionInfo-v1130 OPTIONAL, -- Cond WB-RSRQ
   nonCriticalExtension [2] SystemInformationBlockType1-v1250-IEs OPTIONAL
}

-- Regular non critical extensions
SystemInformationBlockType1-v920-IEs ::= SEQUENCE {
   ims-EmergencySupport-r9 [0] ENUMERATED { true(0) } OPTIONAL, -- Need OR
   cellSelectionInfo-v920 [1] CellSelectionInfo-v920 OPTIONAL, -- Cond RSRQ
   nonCriticalExtension [2] SystemInformationBlockType1-v1130-IEs OPTIONAL
}

SystemInformationBlockType1-v890-IEs ::= SEQUENCE {
   lateNonCriticalExtension [0] OCTET STRING (CONTAINING 
      SystemInformationBlockType1-v8h0-IEs) OPTIONAL,
   nonCriticalExtension [1] SystemInformationBlockType1-v920-IEs OPTIONAL
}

SystemInformationBlockType1 ::= SEQUENCE {
   cellAccessRelatedInfo [0] SEQUENCE {
      plmn-IdentityList [0] PLMN-IdentityList,
      trackingAreaCode [1] TrackingAreaCode,
      cellIdentity [2] CellIdentity,
      cellBarred [3] ENUMERATED { barred(0), notBarred(1) },
      intraFreqReselection [4] ENUMERATED { allowed(0), notAllowed(1) },
      csg-Indication [5] BOOLEAN,
      csg-Identity [6] CSG-Identity OPTIONAL -- Need OR
   },
   cellSelectionInfo [1] SEQUENCE {
      q-RxLevMin [0] Q-RxLevMin,
      q-RxLevMinOffset [1] INTEGER (1..8) OPTIONAL -- Need OP
   },
   p-Max [2] P-Max OPTIONAL, -- Need OP
   freqBandIndicator [3] FreqBandIndicator,
   schedulingInfoList [4] SchedulingInfoList,
   tdd-Config [5] TDD-Config OPTIONAL, -- Cond TDD
   si-WindowLength [6] ENUMERATED { ms1(0), ms2(1), ms5(2), ms10(3), ms15(4), 
      ms20(5), ms40(6) },
   systemInfoValueTag [7] INTEGER (0..31),
   nonCriticalExtension [8] SystemInformationBlockType1-v890-IEs OPTIONAL
}

SystemInformationBlockType1-BR-r13 ::= SystemInformationBlockType1

SIB-Type-MBMS-r14 ::= ENUMERATED { sibType10(0), sibType11(1), 
   sibType12-v920(2), sibType13-v920(3), sibType15-v1130(4), sibType16-v1130(5)
   , ... }

BLER-Range-r12 ::= INTEGER (0..31)

NumberOfPreamblesSent-r11 ::= INTEGER (1..200)

TimeSinceFailure-r11 ::= INTEGER (0..172800)

CellGlobalIdEUTRA ::= SEQUENCE {
   plmn-Identity [0] PLMN-Identity,
   cellIdentity [1] CellIdentity
}

VisitedCellInfo-r12 ::= SEQUENCE {
   visitedCellId-r12 [0] EXPLICIT CHOICE {
      cellGlobalId-r12 [0] CellGlobalIdEUTRA,
      pci-arfcn-r12 [1] SEQUENCE {
         physCellId-r12 [0] PhysCellId,
         carrierFreq-r12 [1] ARFCN-ValueEUTRA-r9
      }
   } OPTIONAL,
   timeSpent-r12 [1] INTEGER (0..4095),
   ...
}

VisitedCellInfoList-r12 ::= SEQUENCE (SIZE (1..maxCellHistory-r12)) OF VisitedCellInfo-r12

MobilityHistoryReport-r12 ::= VisitedCellInfoList-r12

CQI-ReportModeAperiodic ::= ENUMERATED { rm12(0), rm20(1), rm22(2), rm30(3), 
   rm31(4), rm32-v1250(5), rm10-v1310(6), rm11-v1310(7) }

CRI-ConfigIndex-r13 ::= INTEGER (0..1023)

CQI-ReportPeriodicProcExtId-r11 ::= INTEGER (1..maxCQI-ProcExt-r11)

CSI-IM-ConfigId-r11 ::= INTEGER (1..maxCSI-IM-r11)

CSI-IM-ConfigId-r12 ::= INTEGER (1..maxCSI-IM-r12)

CSI-IM-ConfigId-v1250 ::= INTEGER (maxCSI-IM-r12)

CSI-IM-ConfigId-v1310 ::= INTEGER (minCSI-IM-r13..maxCSI-IM-r13)

CSI-IM-ConfigId-r13 ::= INTEGER (1..maxCSI-IM-r13)

CSI-ProcessId-r11 ::= INTEGER (1..maxCSI-Proc-r11)

ResourceConfig-r13 ::= INTEGER (0..31)

NZP-TransmissionComb-r14 ::= INTEGER (0..2)

NZP-FrequencyDensity-r14 ::= ENUMERATED { d1(0), d2(1), d3(2) }

CSI-RS-ConfigNZPId-r11 ::= INTEGER (1..maxCSI-RS-NZP-r11)

CSI-RS-ConfigNZPId-v1310 ::= INTEGER (minCSI-RS-NZP-r13..maxCSI-RS-NZP-r13)

CSI-RS-ConfigNZPId-r13 ::= INTEGER (1..maxCSI-RS-NZP-r13)

CSI-RS-ConfigZPId-r11 ::= INTEGER (1..maxCSI-RS-ZP-r11)

DataInactivityTimer-r14 ::= ENUMERATED { s1(0), s2(1), s3(2), s5(3), s7(4), 
   s10(5), s15(6), s20(7), s40(8), s50(9), s60(10), s80(11), s100(12), s120(13)
   , s150(14), s180(15) }

DRB-Identity ::= INTEGER (1..32)

EPDCCH-SetConfigId-r11 ::= INTEGER (0..1)

PeriodicBSR-Timer-r12 ::= ENUMERATED { sf5(0), sf10(1), sf16(2), sf20(3), 
   sf32(4), sf40(5), sf64(6), sf80(7), sf128(8), sf160(9), sf320(10), sf640(11)
   , sf1280(12), sf2560(13), infinity(14), spare1(15) }

RetxBSR-Timer-r12 ::= ENUMERATED { sf320(0), sf640(1), sf1280(2), sf2560(3), 
   sf5120(4), sf10240(5), spare2(6), spare1(7) }

STAG-Id-r11 ::= INTEGER (1..maxSTAG-r11)

PDCCH-CandidateReductionValue-r13 ::= ENUMERATED { n0(0), n33(1), n66(2), 
   n100(3) }

PDCCH-CandidateReductionValue-r14 ::= ENUMERATED { n0(0), n50(1), n100(2), 
   n150(3) }

PDSCH-RE-MappingQCL-ConfigId-r11 ::= INTEGER (1..maxRE-MapQCL-r11)

ShortTTI-Length-r15 ::= ENUMERATED { slot(0), subslot(1) }

P-a ::= ENUMERATED { dB-6(0), dB-4dot77(1), dB-3(2), dB-1dot77(3), dB0(4), 
   dB1(5), dB2(6), dB3(7) }

SN-FieldLength ::= ENUMERATED { size5(0), size10(1) }

SN-FieldLength-r15 ::= ENUMERATED { size5(0), size10(1), size16-r15(2) }

T-PollRetransmit ::= ENUMERATED { ms5(0), ms10(1), ms15(2), ms20(3), ms25(4), 
   ms30(5), ms35(6), ms40(7), ms45(8), ms50(9), ms55(10), ms60(11), ms65(12), 
   ms70(13), ms75(14), ms80(15), ms85(16), ms90(17), ms95(18), ms100(19), 
   ms105(20), ms110(21), ms115(22), ms120(23), ms125(24), ms130(25), ms135(26)
   , ms140(27), ms145(28), ms150(29), ms155(30), ms160(31), ms165(32), 
   ms170(33), ms175(34), ms180(35), ms185(36), ms190(37), ms195(38), ms200(39)
   , ms205(40), ms210(41), ms215(42), ms220(43), ms225(44), ms230(45), 
   ms235(46), ms240(47), ms245(48), ms250(49), ms300(50), ms350(51), ms400(52)
   , ms450(53), ms500(54), ms800-v1310(55), ms1000-v1310(56), ms2000-v1310(57)
   , ms4000-v1310(58), spare5(59), spare4(60), spare3(61), spare2(62), 
   spare1(63) }

PollPDU ::= ENUMERATED { p4(0), p8(1), p16(2), p32(3), p64(4), p128(5), p256(6)
   , pInfinity(7) }

PollPDU-v1310 ::= ENUMERATED { p512(0), p1024(1), p2048(2), p4096(3), p6144(4)
   , p8192(5), p12288(6), p16384(7) }

PollPDU-r15 ::= ENUMERATED { p4(0), p8(1), p16(2), p32(3), p64(4), p128(5), 
   p256(6), p512(7), p1024(8), p2048-r15(9), p4096-r15(10), p6144-r15(11), 
   p8192-r15(12), p12288-r15(13), p16384-r15(14), pInfinity(15) }

PollByte ::= ENUMERATED { kB25(0), kB50(1), kB75(2), kB100(3), kB125(4), 
   kB250(5), kB375(6), kB500(7), kB750(8), kB1000(9), kB1250(10), kB1500(11), 
   kB2000(12), kB3000(13), kBinfinity(14), spare1(15) }

PollByte-r14 ::= ENUMERATED { kB1(0), kB2(1), kB5(2), kB8(3), kB10(4), kB15(5)
   , kB3500(6), kB4000(7), kB4500(8), kB5000(9), kB5500(10), kB6000(11), 
   kB6500(12), kB7000(13), kB7500(14), kB8000(15), kB9000(16), kB10000(17), 
   kB11000(18), kB12000(19), kB13000(20), kB14000(21), kB15000(22), kB16000(23)
   , kB17000(24), kB18000(25), kB19000(26), kB20000(27), kB25000(28), 
   kB30000(29), kB35000(30), kB40000(31) }

T-Reordering ::= ENUMERATED { ms0(0), ms5(1), ms10(2), ms15(3), ms20(4), 
   ms25(5), ms30(6), ms35(7), ms40(8), ms45(9), ms50(10), ms55(11), ms60(12), 
   ms65(13), ms70(14), ms75(15), ms80(16), ms85(17), ms90(18), ms95(19), 
   ms100(20), ms110(21), ms120(22), ms130(23), ms140(24), ms150(25), ms160(26)
   , ms170(27), ms180(28), ms190(29), ms200(30), ms1600-v1310(31) }

T-StatusProhibit ::= ENUMERATED { ms0(0), ms5(1), ms10(2), ms15(3), ms20(4), 
   ms25(5), ms30(6), ms35(7), ms40(8), ms45(9), ms50(10), ms55(11), ms60(12), 
   ms65(13), ms70(14), ms75(15), ms80(16), ms85(17), ms90(18), ms95(19), 
   ms100(20), ms105(21), ms110(22), ms115(23), ms120(24), ms125(25), ms130(26)
   , ms135(27), ms140(28), ms145(29), ms150(30), ms155(31), ms160(32), 
   ms165(33), ms170(34), ms175(35), ms180(36), ms185(37), ms190(38), ms195(39)
   , ms200(40), ms205(41), ms210(42), ms215(43), ms220(44), ms225(45), 
   ms230(46), ms235(47), ms240(48), ms245(49), ms250(50), ms300(51), ms350(52)
   , ms400(53), ms450(54), ms500(55), ms800-v1310(56), ms1000-v1310(57), 
   ms1200-v1310(58), ms1600-v1310(59), ms2000-v1310(60), ms2400-v1310(61), 
   spare2(62), spare1(63) }

SRS-AntennaPort ::= ENUMERATED { an1(0), an2(1), an4(2), spare1(3) }

DCI7-Candidates-r15 ::= INTEGER (0..6)

SPS-ConfigIndex-r14 ::= INTEGER (1..maxConfigSPS-r14)

SPS-ConfigIndex-r15 ::= INTEGER (1..maxConfigSPS-r15)

SubframeAssignment-r15 ::= ENUMERATED { sa0(0), sa1(1), sa2(2), sa3(3), sa4(4)
   , sa5(5), sa6(6) }

NextHopChainingCount ::= INTEGER (0..7)

CipheringAlgorithm-r12 ::= ENUMERATED { eea0(0), eea1(1), eea2(2), 
   eea3-v1130(3), spare4(4), spare3(5), spare2(6), spare1(7), ... }

ShortMAC-I ::= BIT STRING  (SIZE (16))

CDMA2000-Type ::= ENUMERATED { type1XRTT(0), typeHRPD(1) }

CellIndex ::= INTEGER (1..maxCellMeas)

MobilityParametersCDMA2000 ::= OCTET STRING

PhysCellIdNR-r15 ::= INTEGER (0..1007)

PhysCellIdUTRA-FDD ::= INTEGER (0..511)

PhysCellIdUTRA-TDD ::= INTEGER (0..127)

Q-OffsetRangeInterRAT ::= INTEGER (-15..15)

SCellIndex-r10 ::= INTEGER (1..7)

SCellIndex-r13 ::= INTEGER (1..31)

ServCellIndex-r10 ::= INTEGER (0..7)

ServCellIndex-r13 ::= INTEGER (0..31)

BT-Name-r15 ::= OCTET STRING (SIZE (1..248))

CSI-RSRP-Range-r12 ::= INTEGER (0..97)

Hysteresis ::= INTEGER (0..30)

MBSFN-RSRQ-Range-r12 ::= INTEGER (0..31)

MeasCSI-RS-Id-r12 ::= INTEGER (1..maxCSI-RS-Meas-r12)

MeasId ::= INTEGER (1..maxMeasId)

MeasId-v1250 ::= INTEGER (maxMeasId-Plus1..maxMeasId-r12)

MeasCycleSCell-r10 ::= ENUMERATED { sf160(0), sf256(1), sf320(2), sf512(3), 
   sf640(4), sf1024(5), sf1280(6), spare1(7) }

MeasObjectId ::= INTEGER (1..maxObjectId)

MeasObjectId-v1310 ::= INTEGER (maxObjectId-Plus1-r13..maxObjectId-r13)

MeasObjectId-r13 ::= INTEGER (1..maxObjectId-r13)

WLAN-BandIndicator-r13 ::= ENUMERATED { band2dot4(0), band5(1), band60-v1430(2)
   , spare5(3), spare4(4), spare3(5), spare2(6), spare1(7), ... }

CellIdentityNR-r15 ::= BIT STRING  (SIZE (36))

TrackingAreaCodeNR-r15 ::= BIT STRING  (SIZE (24))

MeasScaleFactor-r12 ::= ENUMERATED { sf-EUTRA-cf1(0), sf-EUTRA-cf2(1) }

ThresholdEUTRA-v1250 ::= CSI-RSRP-Range-r12

ReportConfigId ::= INTEGER (1..maxReportConfigId)

ThresholdGERAN ::= INTEGER (0..63)

ThresholdCDMA2000 ::= INTEGER (0..63)

ReportInterval ::= ENUMERATED { ms120(0), ms240(1), ms480(2), ms640(3), 
   ms1024(4), ms2048(5), ms5120(6), ms10240(7), min1(8), min6(9), min12(10), 
   min30(11), min60(12), spare3(13), spare2(14), spare1(15) }

RS-IndexNR-r15 ::= INTEGER (0..maxRS-Index-1-r15)

RSRP-Range-v1360 ::= INTEGER (-17..-1)

RSRP-RangeSL3-r12 ::= INTEGER (0..11)

RSRQ-Range-v1250 ::= INTEGER (-30..46)

RS-SINR-Range-r13 ::= INTEGER (0..127)

RSSI-Range-r13 ::= INTEGER (0..76)

TimeToTrigger ::= ENUMERATED { ms0(0), ms40(1), ms64(2), ms80(3), ms100(4), 
   ms128(5), ms160(6), ms256(7), ms320(8), ms480(9), ms512(10), ms640(11), 
   ms1024(12), ms1280(13), ms2560(14), ms5120(15) }

WLAN-Channel-r13 ::= INTEGER (0..255)

WLAN-Name-r15 ::= OCTET STRING (SIZE (1..32))

WLAN-RSSI-Range-r13 ::= INTEGER (0..141)

WLAN-Status-r13 ::= ENUMERATED { successfulAssociation(0), 
   failureWlanRadioLink(1), failureWlanUnavailable(2), failureTimeout(3) }

WLAN-Status-v1430 ::= ENUMERATED { suspended(0), resumed(1) }

AbsoluteTimeInfo-r10 ::= BIT STRING  (SIZE (48))

AMF-Identifier-r15 ::= BIT STRING  (SIZE (24))

C-RNTI ::= BIT STRING  (SIZE (16))

DedicatedInfoCDMA2000 ::= OCTET STRING

DedicatedInfoNAS ::= OCTET STRING

I-RNTI-r15 ::= BIT STRING  (SIZE (40))

LoggingDuration-r10 ::= ENUMERATED { min10(0), min20(1), min40(2), min60(3), 
   min90(4), min120(5), spare2(6), spare1(7) }

LoggingInterval-r10 ::= ENUMERATED { ms1280(0), ms2560(1), ms5120(2), 
   ms10240(3), ms20480(4), ms30720(5), ms40960(6), ms61440(7) }

MMEC ::= BIT STRING  (SIZE (8))

NG-5G-S-TMSI-r15 ::= BIT STRING  (SIZE (48))

RAND-CDMA2000 ::= BIT STRING  (SIZE (32))

RAT-Type ::= ENUMERATED { eutra(0), utra(1), geran-cs(2), geran-ps(3), 
   cdma2000-1XRTT(4), nr(5), eutra-nr(6), spare1(7), ... }

ResumeIdentity-r13 ::= BIT STRING  (SIZE (40))

RRC-TransactionIdentifier ::= INTEGER (0..3)

ShortI-RNTI-r15 ::= BIT STRING  (SIZE (24))

AccessStratumRelease ::= ENUMERATED { rel8(0), rel9(1), rel10(2), rel11(3), 
   rel12(4), rel13(5), rel14(6), rel15(7), ... }

ProcessingTimelineSet-r15 ::= ENUMERATED { set1(0), set2(1) }

-- If an additional band combination parameter is defined, which is supported for MR-DC,
--  it shall be defined in the IE CA-ParametersEUTRA in TS 38.331 [82].
SupportedBandwidthCombinationSet-r10 ::= BIT STRING  (SIZE (1..maxBandwidthCombSet-r10))

FeatureSetDL-PerCC-Id-r15 ::= INTEGER (0..maxPerCC-FeatureSets-r15)

FeatureSetUL-PerCC-Id-r15 ::= INTEGER (0..maxPerCC-FeatureSets-r15)

CA-BandwidthClass-r10 ::= ENUMERATED { a(0), b(1), c(2), d(3), e(4), f(5), ...
    }

MIMO-CapabilityUL-r10 ::= ENUMERATED { twoLayers(0), fourLayers(1) }

CA-MIMO-ParametersUL-r10 ::= SEQUENCE {
   ca-BandwidthClassUL-r10 [0] CA-BandwidthClass-r10,
   supportedMIMO-CapabilityUL-r10 [1] MIMO-CapabilityUL-r10 OPTIONAL
}

BandParametersUL-r13 ::= CA-MIMO-ParametersUL-r10

MIMO-CapabilityDL-r10 ::= ENUMERATED { twoLayers(0), fourLayers(1), 
   eightLayers(2) }

IntraBandContiguousCC-Info-r12 ::= SEQUENCE {
   fourLayerTM3-TM4-perCC-r12 [0] ENUMERATED { supported(0) } OPTIONAL,
   supportedMIMO-CapabilityDL-r12 [1] MIMO-CapabilityDL-r10 OPTIONAL,
   supportedCSI-Proc-r12 [2] ENUMERATED { n1(0), n3(1), n4(2) } OPTIONAL
}

CA-MIMO-ParametersDL-r13 ::= SEQUENCE {
   ca-BandwidthClassDL-r13 [0] CA-BandwidthClass-r10,
   supportedMIMO-CapabilityDL-r13 [1] MIMO-CapabilityDL-r10 OPTIONAL,
   fourLayerTM3-TM4-r13 [2] ENUMERATED { supported(0) } OPTIONAL,
   intraBandContiguousCC-InfoList-r13 [3] SEQUENCE (SIZE (1..maxServCell-r13)) OF 
      IntraBandContiguousCC-Info-r12
}

BandParametersDL-r13 ::= CA-MIMO-ParametersDL-r13

V2X-BandwidthClass-r14 ::= ENUMERATED { a(0), b(1), c(2), d(3), e(4), f(5), ...
   , c1-v1530(6) }

SupportedBandUTRA-FDD ::= ENUMERATED { bandI(0), bandII(1), bandIII(2), 
   bandIV(3), bandV(4), bandVI(5), bandVII(6), bandVIII(7), bandIX(8), bandX(9)
   , bandXI(10), bandXII(11), bandXIII(12), bandXIV(13), bandXV(14), 
   bandXVI(15), ..., bandXVII-8a0(16), bandXVIII-8a0(17), bandXIX-8a0(18), 
   bandXX-8a0(19), bandXXI-8a0(20), bandXXII-8a0(21), bandXXIII-8a0(22), 
   bandXXIV-8a0(23), bandXXV-8a0(24), bandXXVI-8a0(25), bandXXVII-8a0(26), 
   bandXXVIII-8a0(27), bandXXIX-8a0(28), bandXXX-8a0(29), bandXXXI-8a0(30), 
   bandXXXII-8a0(31) }

SupportedBandUTRA-TDD128 ::= ENUMERATED { a(0), b(1), c(2), d(3), e(4), f(5), 
   g(6), h(7), i(8), j(9), k(10), l(11), m(12), n(13), o(14), p(15), ... }

SupportedBandUTRA-TDD384 ::= ENUMERATED { a(0), b(1), c(2), d(3), e(4), f(5), 
   g(6), h(7), i(8), j(9), k(10), l(11), m(12), n(13), o(14), p(15), ... }

SupportedBandUTRA-TDD768 ::= ENUMERATED { a(0), b(1), c(2), d(3), e(4), f(5), 
   g(6), h(7), i(8), j(9), k(10), l(11), m(12), n(13), o(14), p(15), ... }

SupportedBandGERAN ::= ENUMERATED { gsm450(0), gsm480(1), gsm710(2), gsm750(3)
   , gsm810(4), gsm850(5), gsm900P(6), gsm900E(7), gsm900R(8), gsm1800(9), 
   gsm1900(10), spare5(11), spare4(12), spare3(13), spare2(14), spare1(15), ...
    }

SL-TxPoolIdentity-r12 ::= INTEGER (1..maxSL-TxPool-r12)

SL-TxPoolIdentity-v1310 ::= INTEGER (maxSL-TxPool-r12Plus1-r13..maxSL-TxPool-r13)

SL-V2X-TxPoolIdentity-r14 ::= INTEGER (1..maxSL-V2X-TxPool-r14)

BCCH-BCH-Message ::= SEQUENCE {
   message [0] BCCH-BCH-MessageType
}

BCCH-BCH-Message-MBMS ::= SEQUENCE {
   message [0] BCCH-BCH-MessageType-MBMS-r14
}

BCCH-DL-SCH-MessageType ::= CHOICE {
   c1 [0] EXPLICIT CHOICE {
      systemInformation [0] SystemInformation,
      systemInformationBlockType1 [1] SystemInformationBlockType1
   },
   messageClassExtension [1] SEQUENCE {

   }
}

BCCH-DL-SCH-Message ::= SEQUENCE {
   message [0] EXPLICIT BCCH-DL-SCH-MessageType
}

BCCH-DL-SCH-MessageType-BR-r13 ::= CHOICE {
   c1 [0] EXPLICIT CHOICE {
      systemInformation-BR-r13 [0] SystemInformation-BR-r13,
      systemInformationBlockType1-BR-r13 [1] SystemInformationBlockType1-BR-r13
   },
   messageClassExtension [1] SEQUENCE {

   }
}

BCCH-DL-SCH-Message-BR ::= SEQUENCE {
   message [0] EXPLICIT BCCH-DL-SCH-MessageType-BR-r13
}

PLMN-IdentityList-MBMS-r14 ::= SEQUENCE (SIZE (1..maxPLMN-r11)) OF PLMN-Identity

SIB-MappingInfo-MBMS-r14 ::= SEQUENCE (SIZE (0..maxSIB-1)) OF SIB-Type-MBMS-r14

SchedulingInfo-MBMS-r14 ::= SEQUENCE {
   si-Periodicity-r14 [0] ENUMERATED { rf16(0), rf32(1), rf64(2), rf128(3), 
      rf256(4), rf512(5) },
   sib-MappingInfo-r14 [1] SIB-MappingInfo-MBMS-r14
}

SchedulingInfoList-MBMS-r14 ::= SEQUENCE (SIZE (1..maxSI-Message)) OF SchedulingInfo-MBMS-r14
   

NonMBSFN-SubframeConfig-r14 ::= SEQUENCE {
   radioFrameAllocationPeriod-r14 [0] ENUMERATED { rf4(0), rf8(1), rf16(2), 
      rf32(3), rf64(4), rf128(5), rf512(6) },
   radioFrameAllocationOffset-r14 [1] INTEGER (0..7),
   subframeAllocation-r14 [2] BIT STRING  (SIZE (9))
}

SystemInformationBlockType1-MBMS-r14 ::= SEQUENCE {
   cellAccessRelatedInfo-r14 [0] SEQUENCE {
      plmn-IdentityList-r14 [0] PLMN-IdentityList-MBMS-r14,
      trackingAreaCode-r14 [1] TrackingAreaCode,
      cellIdentity-r14 [2] CellIdentity
   },
   freqBandIndicator-r14 [1] FreqBandIndicator-r11,
   multiBandInfoList-r14 [2] MultiBandInfoList-r11 OPTIONAL, -- Need OR
   schedulingInfoList-MBMS-r14 [3] SchedulingInfoList-MBMS-r14,
   si-WindowLength-r14 [4] ENUMERATED { ms1(0), ms2(1), ms5(2), ms10(3), 
      ms15(4), ms20(5), ms40(6), ms80(7) },
   systemInfoValueTag-r14 [5] INTEGER (0..31),
   nonMBSFN-SubframeConfig-r14 [6] NonMBSFN-SubframeConfig-r14 OPTIONAL, --Need OR
   pdsch-ConfigCommon-r14 [7] PDSCH-ConfigCommon,
   systemInformationBlockType13-r14 [8] SystemInformationBlockType13-r9
       OPTIONAL, --Need OR
   cellAccessRelatedInfoList-r14 [9] SEQUENCE (SIZE (1..maxPLMN-1-r14)) OF 
      CellAccessRelatedInfo-r14 OPTIONAL, -- Need OR
   nonCriticalExtension [10] SEQUENCE {

   } OPTIONAL
}

BCCH-DL-SCH-MessageType-MBMS-r14 ::= CHOICE {
   c1 [0] EXPLICIT CHOICE {
      systemInformation-MBMS-r14 [0] SystemInformation-MBMS-r14,
      systemInformationBlockType1-MBMS-r14 [1] 
         SystemInformationBlockType1-MBMS-r14
   },
   messageClassExtension [1] SEQUENCE {

   }
}

BCCH-DL-SCH-Message-MBMS ::= SEQUENCE {
   message [0] EXPLICIT BCCH-DL-SCH-MessageType-MBMS-r14
}

CommonSF-AllocPatternList-r9 ::= SEQUENCE (SIZE (1..maxMBSFN-Allocations)) OF MBSFN-SubframeConfig

PMCH-Config-r9 ::= SEQUENCE {
   sf-AllocEnd-r9 [0] INTEGER (0..1535),
   dataMCS-r9 [1] INTEGER (0..28),
   mch-SchedulingPeriod-r9 [2] ENUMERATED { rf8(0), rf16(1), rf32(2), rf64(3), 
      rf128(4), rf256(5), rf512(6), rf1024(7) },
   ...
}

TMGI-r9 ::= SEQUENCE {
   plmn-Id-r9 [0] EXPLICIT CHOICE {
      plmn-Index-r9 [0] INTEGER (1..maxPLMN-r11),
      explicitValue-r9 [1] PLMN-Identity
   },
   serviceId-r9 [1] OCTET STRING (SIZE (3))
}

MBMS-SessionInfo-r9 ::= SEQUENCE {
   tmgi-r9 [0] TMGI-r9,
   sessionId-r9 [1] OCTET STRING (SIZE (1)) OPTIONAL, -- Need OR
   logicalChannelIdentity-r9 [2] INTEGER (0..maxSessionPerPMCH-1),
   ...
}

MBMS-SessionInfoList-r9 ::= SEQUENCE (SIZE (0..maxSessionPerPMCH)) OF MBMS-SessionInfo-r9

PMCH-Info-r9 ::= SEQUENCE {
   pmch-Config-r9 [0] PMCH-Config-r9,
   mbms-SessionInfoList-r9 [1] MBMS-SessionInfoList-r9,
   ...
}

PMCH-InfoList-r9 ::= SEQUENCE (SIZE (0..maxPMCH-PerMBSFN)) OF PMCH-Info-r9

PMCH-Config-r12 ::= SEQUENCE {
   sf-AllocEnd-r12 [0] INTEGER (0..1535),
   dataMCS-r12 [1] EXPLICIT CHOICE {
      normal-r12 [0] INTEGER (0..28),
      higerOrder-r12 [1] INTEGER (0..27)
   },
   mch-SchedulingPeriod-r12 [2] ENUMERATED { rf4(0), rf8(1), rf16(2), rf32(3), 
      rf64(4), rf128(5), rf256(6), rf512(7), rf1024(8) },
   ...,
   [[
      mch-SchedulingPeriod-v1430 [3] ENUMERATED { rf1(0), rf2(1) } OPTIONAL
   ]]
}

PMCH-InfoExt-r12 ::= SEQUENCE {
   pmch-Config-r12 [0] PMCH-Config-r12,
   mbms-SessionInfoList-r12 [1] MBMS-SessionInfoList-r9,
   ...
}

PMCH-InfoListExt-r12 ::= SEQUENCE (SIZE (0..maxPMCH-PerMBSFN)) OF PMCH-InfoExt-r12

CommonSF-AllocPatternList-r14 ::= SEQUENCE (SIZE (1..maxMBSFN-Allocations)) OF 
   MBSFN-SubframeConfig-v1430

MBSFNAreaConfiguration-v1430-IEs ::= SEQUENCE {
   commonSF-Alloc-r14 [0] CommonSF-AllocPatternList-r14,
   nonCriticalExtension [1] SEQUENCE {

   } OPTIONAL
}

MBSFNAreaConfiguration-v1250-IEs ::= SEQUENCE {
   pmch-InfoListExt-r12 [0] PMCH-InfoListExt-r12 OPTIONAL, -- Need OR
   nonCriticalExtension [1] MBSFNAreaConfiguration-v1430-IEs OPTIONAL
}

MBSFNAreaConfiguration-v930-IEs ::= SEQUENCE {
   lateNonCriticalExtension [0] OCTET STRING OPTIONAL,
   nonCriticalExtension [1] MBSFNAreaConfiguration-v1250-IEs OPTIONAL
}

MBSFNAreaConfiguration-r9 ::= SEQUENCE {
   commonSF-Alloc-r9 [0] CommonSF-AllocPatternList-r9,
   commonSF-AllocPeriod-r9 [1] ENUMERATED { rf4(0), rf8(1), rf16(2), rf32(3), 
      rf64(4), rf128(5), rf256(6) },
   pmch-InfoList-r9 [2] PMCH-InfoList-r9,
   nonCriticalExtension [3] MBSFNAreaConfiguration-v930-IEs OPTIONAL
}

CountingRequestInfo-r10 ::= SEQUENCE {
   tmgi-r10 [0] TMGI-r9,
   ...
}

CountingRequestList-r10 ::= SEQUENCE (SIZE (1..maxServiceCount)) OF CountingRequestInfo-r10

MBMSCountingRequest-r10 ::= SEQUENCE {
   countingRequestList-r10 [0] CountingRequestList-r10,
   lateNonCriticalExtension [1] OCTET STRING OPTIONAL,
   nonCriticalExtension [2] SEQUENCE {

   } OPTIONAL
}

MCCH-MessageType ::= CHOICE {
   c1 [0] EXPLICIT CHOICE {
      mbsfnAreaConfiguration-r9 [0] MBSFNAreaConfiguration-r9
   },
   later [1] EXPLICIT CHOICE {
      c2 [0] EXPLICIT CHOICE {
         mbmsCountingRequest-r10 [0] MBMSCountingRequest-r10
      },
      messageClassExtension [1] SEQUENCE {

      }
   }
}

MCCH-Message ::= SEQUENCE {
   message [0] EXPLICIT MCCH-MessageType
}

S-TMSI ::= SEQUENCE {
   mmec [0] MMEC,
   m-TMSI [1] BIT STRING  (SIZE (32))
}

IMSI ::= SEQUENCE (SIZE (6..21)) OF IMSI-Digit

PagingUE-Identity ::= CHOICE {
   s-TMSI [0] S-TMSI,
   imsi [1] IMSI,
   ...,
   ng-5G-S-TMSI-r15 [2] NG-5G-S-TMSI-r15,
   fullI-RNTI-r15 [3] I-RNTI-r15
}

PagingRecord ::= SEQUENCE {
   ue-Identity [0] EXPLICIT PagingUE-Identity,
   cn-Domain [1] ENUMERATED { ps(0), cs(1) },
   ...
}

PagingRecordList ::= SEQUENCE (SIZE (1..maxPageRec)) OF PagingRecord

Paging-v1530-IEs ::= SEQUENCE {
   accessType [0] ENUMERATED { non3GPP(0) } OPTIONAL, -- Need ON
   nonCriticalExtension [1] SEQUENCE {

   } OPTIONAL
}

Paging-v1310-IEs ::= SEQUENCE {
   redistributionIndication-r13 [0] ENUMERATED { true(0) } OPTIONAL, -- Need ON
   systemInfoModification-eDRX-r13 [1] ENUMERATED { true(0) } OPTIONAL, -- Need ON
   nonCriticalExtension [2] Paging-v1530-IEs OPTIONAL
}

Paging-v1130-IEs ::= SEQUENCE {
   eab-ParamModification-r11 [0] ENUMERATED { true(0) } OPTIONAL, -- Need ON
   nonCriticalExtension [1] Paging-v1310-IEs OPTIONAL
}

Paging-v920-IEs ::= SEQUENCE {
   cmas-Indication-r9 [0] ENUMERATED { true(0) } OPTIONAL, -- Need ON
   nonCriticalExtension [1] Paging-v1130-IEs OPTIONAL
}

Paging-v890-IEs ::= SEQUENCE {
   lateNonCriticalExtension [0] OCTET STRING OPTIONAL,
   nonCriticalExtension [1] Paging-v920-IEs OPTIONAL
}

Paging ::= SEQUENCE {
   pagingRecordList [0] PagingRecordList OPTIONAL, -- Need ON
   systemInfoModification [1] ENUMERATED { true(0) } OPTIONAL, -- Need ON
   etws-Indication [2] ENUMERATED { true(0) } OPTIONAL, -- Need ON
   nonCriticalExtension [3] Paging-v890-IEs OPTIONAL
}

PCCH-MessageType ::= CHOICE {
   c1 [0] EXPLICIT CHOICE {
      paging [0] Paging
   },
   messageClassExtension [1] SEQUENCE {

   }
}

PCCH-Message ::= SEQUENCE {
   message [0] EXPLICIT PCCH-MessageType
}

UL-AM-RLC ::= SEQUENCE {
   t-PollRetransmit [0] T-PollRetransmit,
   pollPDU [1] PollPDU,
   pollByte [2] PollByte,
   maxRetxThreshold [3] ENUMERATED { t1(0), t2(1), t3(2), t4(3), t6(4), t8(5), 
      t16(6), t32(7) }
}

DL-AM-RLC ::= SEQUENCE {
   t-Reordering [0] T-Reordering,
   t-StatusProhibit [1] T-StatusProhibit
}

UL-UM-RLC ::= SEQUENCE {
   sn-FieldLength [0] SN-FieldLength
}

DL-UM-RLC ::= SEQUENCE {
   sn-FieldLength [0] SN-FieldLength,
   t-Reordering [1] T-Reordering
}

RLC-Config ::= CHOICE {
   am [0] SEQUENCE {
      ul-AM-RLC [0] UL-AM-RLC,
      dl-AM-RLC [1] DL-AM-RLC
   },
   um-Bi-Directional [1] SEQUENCE {
      ul-UM-RLC [0] UL-UM-RLC,
      dl-UM-RLC [1] DL-UM-RLC
   },
   um-Uni-Directional-UL [2] SEQUENCE {
      ul-UM-RLC [0] UL-UM-RLC
   },
   um-Uni-Directional-DL [3] SEQUENCE {
      dl-UM-RLC [0] DL-UM-RLC
   },
   ...
}

LogicalChannelConfig ::= SEQUENCE {
   ul-SpecificParameters [0] SEQUENCE {
      priority [0] INTEGER (1..16),
      prioritisedBitRate [1] ENUMERATED { kBps0(0), kBps8(1), kBps16(2), 
         kBps32(3), kBps64(4), kBps128(5), kBps256(6), infinity(7), 
         kBps512-v1020(8), kBps1024-v1020(9), kBps2048-v1020(10), spare5(11), 
         spare4(12), spare3(13), spare2(14), spare1(15) },
      bucketSizeDuration [2] ENUMERATED { ms50(0), ms100(1), ms150(2), ms300(3)
         , ms500(4), ms1000(5), spare2(6), spare1(7) },
      logicalChannelGroup [3] INTEGER (0..3) OPTIONAL -- Need OR
   } OPTIONAL,
   ...,
   [[
      logicalChannelSR-Mask-r9 [1] ENUMERATED { setup(0) } OPTIONAL
   ]],
   [[
      logicalChannelSR-Prohibit-r12 [2] BOOLEAN OPTIONAL
   ]],
   [[
      laa-UL-Allowed-r14 [3] BOOLEAN OPTIONAL,
      bitRateQueryProhibitTimer-r14 [4] ENUMERATED { s0(0), s0dot4(1), 
         s0dot8(2), s1dot6(3), s3(4), s6(5), s12(6), s30(7) } OPTIONAL
   ]],
   [[
      allowedTTI-Lengths-r15 [5] EXPLICIT CHOICE {
         release [0] NULL,
         setup [1] SEQUENCE {
            shortTTI-r15 [0] BOOLEAN,
            subframeTTI-r15 [1] BOOLEAN
         }
      } OPTIONAL,
      logicalChannelSR-Restriction-r15 [6] EXPLICIT CHOICE {
         release [0] NULL,
         setup [1] ENUMERATED { spucch(0), pucch(1) }
      } OPTIONAL,
      channellAccessPriority-r15 [7] EXPLICIT CHOICE {
         release [0] NULL,
         setup [1] INTEGER (1..4)
      } OPTIONAL,
      lch-CellRestriction-r15 [8] BIT STRING  (SIZE (maxServCell-r13)) OPTIONAL
   ]]
}

RLC-Config-v1530 ::= CHOICE {
   release [0] NULL,
   setup [1] SEQUENCE {
      rlc-OutOfOrderDelivery-r15 [0] ENUMERATED { true(0) }
   }
}

UL-AM-RLC-r15 ::= SEQUENCE {
   t-PollRetransmit-r15 [0] T-PollRetransmit,
   pollPDU-r15 [1] PollPDU-r15,
   pollByte-r15 [2] PollByte-r14,
   maxRetxThreshold-r15 [3] ENUMERATED { t1(0), t2(1), t3(2), t4(3), t6(4), 
      t8(5), t16(6), t32(7) },
   extended-RLC-LI-Field-r15 [4] BOOLEAN
}

DL-AM-RLC-r15 ::= SEQUENCE {
   t-Reordering-r15 [0] T-Reordering,
   t-StatusProhibit-r15 [1] T-StatusProhibit,
   extended-RLC-LI-Field-r15 [2] BOOLEAN
}

DL-UM-RLC-r15 ::= SEQUENCE {
   sn-FieldLength-r15 [0] SN-FieldLength-r15,
   t-Reordering-r15 [1] T-Reordering
}

RLC-Config-r15 ::= SEQUENCE {
   mode-r15 [0] EXPLICIT CHOICE {
      am-r15 [0] SEQUENCE {
         ul-AM-RLC-r15 [0] UL-AM-RLC-r15,
         dl-AM-RLC-r15 [1] DL-AM-RLC-r15
      },
      um-Bi-Directional-r15 [1] SEQUENCE {
         ul-UM-RLC-r15 [0] UL-UM-RLC,
         dl-UM-RLC-r15 [1] DL-UM-RLC-r15
      },
      um-Uni-Directional-UL-r15 [2] SEQUENCE {
         ul-UM-RLC-r15 [0] UL-UM-RLC
      },
      um-Uni-Directional-DL-r15 [3] SEQUENCE {
         dl-UM-RLC-r15 [0] DL-UM-RLC-r15
      }
   },
   reestablishRLC-r15 [1] ENUMERATED { true(0) } OPTIONAL, -- Need ON
   rlc-OutOfOrderDelivery-r15 [2] ENUMERATED { true(0) } OPTIONAL,
   ...
}

RLC-BearerConfig-r15 ::= CHOICE {
   release [0] NULL,
   setup [1] SEQUENCE {
      rlc-Config-r15 [0] RLC-Config-r15 OPTIONAL, -- Need ON
      logicalChannelIdentityConfig-r15 [1] EXPLICIT CHOICE {
         logicalChannelIdentity-r15 [0] INTEGER (1..10),
         logicalChannelIdentityExt-r15 [1] INTEGER (32..38)
      },
      logicalChannelConfig-r15 [2] LogicalChannelConfig OPTIONAL -- Need ON
   }
}

RLC-Config-v1510 ::= SEQUENCE {
   reestablishRLC-r15 [0] ENUMERATED { true(0) }
}

SRB-ToAddMod ::= SEQUENCE {
   srb-Identity [0] INTEGER (1..2),
   rlc-Config [1] EXPLICIT CHOICE {
      explicitValue [0] EXPLICIT RLC-Config,
      defaultValue [1] NULL
   } OPTIONAL, -- Cond Setup
   logicalChannelConfig [2] EXPLICIT CHOICE {
      explicitValue [0] LogicalChannelConfig,
      defaultValue [1] NULL
   } OPTIONAL,
   ...,
   [[
      pdcp-verChange-r15 [3] ENUMERATED { true(0) } OPTIONAL,
      rlc-Config-v1530 [4] EXPLICIT RLC-Config-v1530 OPTIONAL,
      rlc-BearerConfigSecondary-r15 [5] EXPLICIT RLC-BearerConfig-r15 OPTIONAL
         ,
      srb-Identity-v1530 [6] INTEGER (4) OPTIONAL
   ]],
   [[
      rlc-Config-v1560 [7] RLC-Config-v1510 OPTIONAL
   ]]
}

SRB-ToAddModList ::= SEQUENCE (SIZE (1..2)) OF SRB-ToAddMod

PDCP-Config ::= SEQUENCE {
   discardTimer [0] ENUMERATED { ms50(0), ms100(1), ms150(2), ms300(3), 
      ms500(4), ms750(5), ms1500(6), infinity(7) } OPTIONAL, -- Cond Setup
   rlc-AM [1] SEQUENCE {
      statusReportRequired [0] BOOLEAN
   } OPTIONAL, -- Cond Rlc-AM
   rlc-UM [2] SEQUENCE {
      pdcp-SN-Size [0] ENUMERATED { len7bits(0), len12bits(1) }
   } OPTIONAL, -- Cond Rlc-UM
   headerCompression [3] EXPLICIT CHOICE {
      notUsed [0] NULL,
      rohc [1] SEQUENCE {
         maxCID [0] INTEGER (1..16383) DEFAULT 15,
         profiles [1] SEQUENCE {
            profile0x0001 [0] BOOLEAN,
            profile0x0002 [1] BOOLEAN,
            profile0x0003 [2] BOOLEAN,
            profile0x0004 [3] BOOLEAN,
            profile0x0006 [4] BOOLEAN,
            profile0x0101 [5] BOOLEAN,
            profile0x0102 [6] BOOLEAN,
            profile0x0103 [7] BOOLEAN,
            profile0x0104 [8] BOOLEAN
         },
         ...
      }
   },
   ...,
   [[
      rn-IntegrityProtection-r10 [4] ENUMERATED { enabled(0) } OPTIONAL
   ]],
   [[
      pdcp-SN-Size-v1130 [5] ENUMERATED { len15bits(0) } OPTIONAL
   ]],
   [[
      ul-DataSplitDRB-ViaSCG-r12 [6] BOOLEAN OPTIONAL,
      t-Reordering-r12 [7] ENUMERATED { ms0(0), ms20(1), ms40(2), ms60(3), 
         ms80(4), ms100(5), ms120(6), ms140(7), ms160(8), ms180(9), ms200(10), 
         ms220(11), ms240(12), ms260(13), ms280(14), ms300(15), ms500(16), 
         ms750(17), spare14(18), spare13(19), spare12(20), spare11(21), 
         spare10(22), spare9(23), spare8(24), spare7(25), spare6(26), 
         spare5(27), spare4(28), spare3(29), spare2(30), spare1(31) } OPTIONAL
   ]],
   [[
      ul-DataSplitThreshold-r13 [8] EXPLICIT CHOICE {
         release [0] NULL,
         setup [1] ENUMERATED { b0(0), b100(1), b200(2), b400(3), b800(4), 
            b1600(5), b3200(6), b6400(7), b12800(8), b25600(9), b51200(10), 
            b102400(11), b204800(12), b409600(13), b819200(14), spare1(15) }
      } OPTIONAL,
      pdcp-SN-Size-v1310 [9] ENUMERATED { len18bits(0) } OPTIONAL,
      statusFeedback-r13 [10] EXPLICIT CHOICE {
         release [0] NULL,
         setup [1] SEQUENCE {
            statusPDU-TypeForPolling-r13 [0] ENUMERATED { type1(0), type2(1) }
                OPTIONAL, -- Need ON
            statusPDU-Periodicity-Type1-r13 [1] ENUMERATED { ms5(0), ms10(1), 
               ms20(2), ms30(3), ms40(4), ms50(5), ms60(6), ms70(7), ms80(8), 
               ms90(9), ms100(10), ms150(11), ms200(12), ms300(13), ms500(14), 
               ms1000(15), ms2000(16), ms5000(17), ms10000(18), ms20000(19), 
               ms50000(20) } OPTIONAL, -- Need ON
            statusPDU-Periodicity-Type2-r13 [2] ENUMERATED { ms5(0), ms10(1), 
               ms20(2), ms30(3), ms40(4), ms50(5), ms60(6), ms70(7), ms80(8), 
               ms90(9), ms100(10), ms150(11), ms200(12), ms300(13), ms500(14), 
               ms1000(15), ms2000(16), ms5000(17), ms10000(18), ms20000(19), 
               ms50000(20) } OPTIONAL, -- Need ON
            statusPDU-Periodicity-Offset-r13 [3] ENUMERATED { ms1(0), ms2(1), 
               ms5(2), ms10(3), ms25(4), ms50(5), ms100(6), ms250(7), ms500(8)
               , ms2500(9), ms5000(10), ms25000(11) } OPTIONAL -- Need ON
         }
      } OPTIONAL
   ]],
   [[
      ul-LWA-Config-r14 [11] EXPLICIT CHOICE {
         release [0] NULL,
         setup [1] SEQUENCE {
            ul-LWA-DRB-ViaWLAN-r14 [0] BOOLEAN,
            ul-LWA-DataSplitThreshold-r14 [1] ENUMERATED { b0(0), b100(1), 
               b200(2), b400(3), b800(4), b1600(5), b3200(6), b6400(7), 
               b12800(8), b25600(9), b51200(10), b102400(11), b204800(12), 
               b409600(13), b819200(14) } OPTIONAL -- Need OR
         }
      } OPTIONAL,
      uplinkOnlyHeaderCompression-r14 [12] EXPLICIT CHOICE {
         notUsed-r14 [0] NULL,
         rohc-r14 [1] SEQUENCE {
            maxCID-r14 [0] INTEGER (1..16383) DEFAULT 15,
            profiles-r14 [1] SEQUENCE {
               profile0x0006-r14 [0] BOOLEAN
            },
            ...
         }
      } OPTIONAL
   ]],
   [[
      uplinkDataCompression-r15 [13] SEQUENCE {
         bufferSize-r15 [0] ENUMERATED { kbyte2(0), kbyte4(1), kbyte8(2), 
            spare1(3) },
         dictionary-r15 [1] ENUMERATED { sip-SDP(0), operator(1) } OPTIONAL,
         ...
      } OPTIONAL,
      pdcp-DuplicationConfig-r15 [14] EXPLICIT CHOICE {
         release [0] NULL,
         setup [1] SEQUENCE {
            pdcp-Duplication-r15 [0] ENUMERATED { configured(0), activated(1) }
         }
      } OPTIONAL
   ]]
}

RLC-Config-v1250 ::= SEQUENCE {
   ul-extended-RLC-LI-Field-r12 [0] BOOLEAN,
   dl-extended-RLC-LI-Field-r12 [1] BOOLEAN
}

RLC-Config-v1310 ::= SEQUENCE {
   ul-extended-RLC-AM-SN-r13 [0] BOOLEAN,
   dl-extended-RLC-AM-SN-r13 [1] BOOLEAN,
   pollPDU-v1310 [2] PollPDU-v1310 OPTIONAL -- Need OR
}

RLC-Config-v1430 ::= CHOICE {
   release [0] NULL,
   setup [1] SEQUENCE {
      pollByte-r14 [0] PollByte-r14
   }
}

DRB-ToAddMod ::= SEQUENCE {
   eps-BearerIdentity [0] INTEGER (0..15) OPTIONAL, -- Cond DRB-Setup
   drb-Identity [1] DRB-Identity,
   pdcp-Config [2] PDCP-Config OPTIONAL, -- Cond PDCP
   rlc-Config [3] EXPLICIT RLC-Config OPTIONAL, -- Cond SetupM
   logicalChannelIdentity [4] INTEGER (3..10) OPTIONAL, -- Cond DRB-SetupM
   logicalChannelConfig [5] LogicalChannelConfig OPTIONAL,
   ...,
   [[
      drb-TypeChange-r12 [6] ENUMERATED { toMCG(0) } OPTIONAL,
      rlc-Config-v1250 [7] RLC-Config-v1250 OPTIONAL
   ]],
   [[
      rlc-Config-v1310 [8] RLC-Config-v1310 OPTIONAL,
      drb-TypeLWA-r13 [9] BOOLEAN OPTIONAL,
      drb-TypeLWIP-r13 [10] ENUMERATED { lwip(0), lwip-DL-only(1), 
         lwip-UL-only(2), eutran(3) } OPTIONAL
   ]],
   [[
      rlc-Config-v1430 [11] EXPLICIT RLC-Config-v1430 OPTIONAL,
      lwip-UL-Aggregation-r14 [12] BOOLEAN OPTIONAL,
      lwip-DL-Aggregation-r14 [13] BOOLEAN OPTIONAL,
      lwa-WLAN-AC-r14 [14] ENUMERATED { ac-bk(0), ac-be(1), ac-vi(2), ac-vo(3)
          } OPTIONAL
   ]],
   [[
      rlc-Config-v1510 [15] RLC-Config-v1510 OPTIONAL
   ]],
   [[
      rlc-Config-v1530 [16] EXPLICIT RLC-Config-v1530 OPTIONAL,
      rlc-BearerConfigSecondary-r15 [17] EXPLICIT RLC-BearerConfig-r15 OPTIONAL
         ,
      logicalChannelIdentity-r15 [18] INTEGER (32..38) OPTIONAL
   ]]
}

DRB-ToAddModList ::= SEQUENCE (SIZE (1..maxDRB)) OF DRB-ToAddMod

DRB-ToReleaseList ::= SEQUENCE (SIZE (1..maxDRB)) OF DRB-Identity

DRX-Config ::= CHOICE {
   release [0] NULL,
   setup [1] SEQUENCE {
      onDurationTimer [0] ENUMERATED { psf1(0), psf2(1), psf3(2), psf4(3), 
         psf5(4), psf6(5), psf8(6), psf10(7), psf20(8), psf30(9), psf40(10), 
         psf50(11), psf60(12), psf80(13), psf100(14), psf200(15) },
      drx-InactivityTimer [1] ENUMERATED { psf1(0), psf2(1), psf3(2), psf4(3), 
         psf5(4), psf6(5), psf8(6), psf10(7), psf20(8), psf30(9), psf40(10), 
         psf50(11), psf60(12), psf80(13), psf100(14), psf200(15), psf300(16), 
         psf500(17), psf750(18), psf1280(19), psf1920(20), psf2560(21), 
         psf0-v1020(22), spare9(23), spare8(24), spare7(25), spare6(26), 
         spare5(27), spare4(28), spare3(29), spare2(30), spare1(31) },
      drx-RetransmissionTimer [2] ENUMERATED { psf1(0), psf2(1), psf4(2), 
         psf6(3), psf8(4), psf16(5), psf24(6), psf33(7) },
      longDRX-CycleStartOffset [3] EXPLICIT CHOICE {
         sf10 [0] INTEGER (0..9),
         sf20 [1] INTEGER (0..19),
         sf32 [2] INTEGER (0..31),
         sf40 [3] INTEGER (0..39),
         sf64 [4] INTEGER (0..63),
         sf80 [5] INTEGER (0..79),
         sf128 [6] INTEGER (0..127),
         sf160 [7] INTEGER (0..159),
         sf256 [8] INTEGER (0..255),
         sf320 [9] INTEGER (0..319),
         sf512 [10] INTEGER (0..511),
         sf640 [11] INTEGER (0..639),
         sf1024 [12] INTEGER (0..1023),
         sf1280 [13] INTEGER (0..1279),
         sf2048 [14] INTEGER (0..2047),
         sf2560 [15] INTEGER (0..2559)
      },
      shortDRX [4] SEQUENCE {
         shortDRX-Cycle [0] ENUMERATED { sf2(0), sf5(1), sf8(2), sf10(3), 
            sf16(4), sf20(5), sf32(6), sf40(7), sf64(8), sf80(9), sf128(10), 
            sf160(11), sf256(12), sf320(13), sf512(14), sf640(15) },
         drxShortCycleTimer [1] INTEGER (1..16)
      } OPTIONAL -- Need OR
   }
}

STAG-ToReleaseList-r11 ::= SEQUENCE (SIZE (1..maxSTAG-r11)) OF STAG-Id-r11

STAG-ToAddMod-r11 ::= SEQUENCE {
   stag-Id-r11 [0] STAG-Id-r11,
   timeAlignmentTimerSTAG-r11 [1] TimeAlignmentTimer,
   ...
}

STAG-ToAddModList-r11 ::= SEQUENCE (SIZE (1..maxSTAG-r11)) OF STAG-ToAddMod-r11

DRX-Config-v1130 ::= SEQUENCE {
   drx-RetransmissionTimer-v1130 [0] ENUMERATED { psf0-v1130(0) } OPTIONAL, --Need OR
   longDRX-CycleStartOffset-v1130 [1] EXPLICIT CHOICE {
      sf60-v1130 [0] INTEGER (0..59),
      sf70-v1130 [1] INTEGER (0..69)
   } OPTIONAL, --Need OR
   shortDRX-Cycle-v1130 [2] ENUMERATED { sf4-v1130(0) } OPTIONAL --Need OR
}

DRX-Config-v1310 ::= SEQUENCE {
   longDRX-CycleStartOffset-v1310 [0] SEQUENCE {
      sf60-v1310 [0] INTEGER (0..59)
   } OPTIONAL --Need OR	
}

DRX-Config-r13 ::= SEQUENCE {
   onDurationTimer-v1310 [0] ENUMERATED { psf300(0), psf400(1), psf500(2), 
      psf600(3), psf800(4), psf1000(5), psf1200(6), psf1600(7) } OPTIONAL,
                     --Need OR
   drx-RetransmissionTimer-v1310 [1] ENUMERATED { psf40(0), psf64(1), psf80(2)
      , psf96(3), psf112(4), psf128(5), psf160(6), psf320(7) } OPTIONAL,
                      --Need OR
   drx-ULRetransmissionTimer-r13 [2] ENUMERATED { psf0(0), psf1(1), psf2(2), 
      psf4(3), psf6(4), psf8(5), psf16(6), psf24(7), psf33(8), psf40(9), 
      psf64(10), psf80(11), psf96(12), psf112(13), psf128(14), psf160(15), 
      psf320(16) } OPTIONAL
                     --Need OR
}

DRX-Config-r15 ::= SEQUENCE {
   drx-RetransmissionTimerShortTTI-r15 [0] ENUMERATED { tti10(0), tti20(1), 
      tti40(2), tti64(3), tti80(4), tti96(5), tti112(6), tti128(7), tti160(8), 
      tti320(9) } OPTIONAL, --Need OR
   drx-UL-RetransmissionTimerShortTTI-r15 [1] ENUMERATED { tti0(0), tti1(1), 
      tti2(2), tti4(3), tti6(4), tti8(5), tti16(6), tti24(7), tti33(8), 
      tti40(9), tti64(10), tti80(11), tti96(12), tti112(13), tti128(14), 
      tti160(15), tti320(16) } OPTIONAL --Need OR
}

MAC-MainConfig ::= SEQUENCE {
   ul-SCH-Config [0] SEQUENCE {
      maxHARQ-Tx [0] ENUMERATED { n1(0), n2(1), n3(2), n4(3), n5(4), n6(5), 
         n7(6), n8(7), n10(8), n12(9), n16(10), n20(11), n24(12), n28(13), 
         spare2(14), spare1(15) } OPTIONAL, -- Need ON
      periodicBSR-Timer [1] PeriodicBSR-Timer-r12 OPTIONAL, -- Need ON
      retxBSR-Timer [2] RetxBSR-Timer-r12,
      ttiBundling [3] BOOLEAN
   } OPTIONAL, -- Need ON
   drx-Config [1] EXPLICIT DRX-Config OPTIONAL, -- Need ON
   timeAlignmentTimerDedicated [2] TimeAlignmentTimer,
   phr-Config [3] EXPLICIT CHOICE {
      release [0] NULL,
      setup [1] SEQUENCE {
         periodicPHR-Timer [0] ENUMERATED { sf10(0), sf20(1), sf50(2), sf100(3)
            , sf200(4), sf500(5), sf1000(6), infinity(7) },
         prohibitPHR-Timer [1] ENUMERATED { sf0(0), sf10(1), sf20(2), sf50(3), 
            sf100(4), sf200(5), sf500(6), sf1000(7) },
         dl-PathlossChange [2] ENUMERATED { dB1(0), dB3(1), dB6(2), infinity(3)
             }
      }
   } OPTIONAL,
   ...,
   [[
      sr-ProhibitTimer-r9 [4] INTEGER (0..7) OPTIONAL
   ]],
   [[
      mac-MainConfig-v1020 [5] SEQUENCE {
         sCellDeactivationTimer-r10 [0] ENUMERATED { rf2(0), rf4(1), rf8(2), 
            rf16(3), rf32(4), rf64(5), rf128(6), spare(7) } OPTIONAL, -- Need OP
         extendedBSR-Sizes-r10 [1] ENUMERATED { setup(0) } OPTIONAL, -- Need OR
         extendedPHR-r10 [2] ENUMERATED { setup(0) } OPTIONAL -- Need OR
      } OPTIONAL
   ]],
   [[
      stag-ToReleaseList-r11 [6] STAG-ToReleaseList-r11 OPTIONAL,
      stag-ToAddModList-r11 [7] STAG-ToAddModList-r11 OPTIONAL,
      drx-Config-v1130 [8] DRX-Config-v1130 OPTIONAL
   ]],
   [[
      e-HARQ-Pattern-r12 [9] BOOLEAN OPTIONAL,
      dualConnectivityPHR [10] EXPLICIT CHOICE {
         release [0] NULL,
         setup [1] SEQUENCE {
            phr-ModeOtherCG-r12 [0] ENUMERATED { real(0), virtual(1) }
         }
      } OPTIONAL,
      logicalChannelSR-Config-r12 [11] EXPLICIT CHOICE {
         release [0] NULL,
         setup [1] SEQUENCE {
            logicalChannelSR-ProhibitTimer-r12 [0] ENUMERATED { sf20(0), 
               sf40(1), sf64(2), sf128(3), sf512(4), sf1024(5), sf2560(6), 
               spare1(7) }
         }
      } OPTIONAL
   ]],
   [[
      drx-Config-v1310 [12] DRX-Config-v1310 OPTIONAL,
      extendedPHR2-r13 [13] BOOLEAN OPTIONAL,
      eDRX-Config-CycleStartOffset-r13 [14] EXPLICIT CHOICE {
         release [0] NULL,
         setup [1] EXPLICIT CHOICE {
            sf5120 [0] INTEGER (0..1),
            sf10240 [1] INTEGER (0..3)
         }
      } OPTIONAL
   ]],
   [[
      drx-Config-r13 [15] EXPLICIT CHOICE {
         release [0] NULL,
         setup [1] DRX-Config-r13
      } OPTIONAL
   ]],
   [[
      skipUplinkTx-r14 [16] EXPLICIT CHOICE {
         release [0] NULL,
         setup [1] SEQUENCE {
            skipUplinkTxSPS-r14 [0] ENUMERATED { true(0) } OPTIONAL, -- Need OR
            skipUplinkTxDynamic-r14 [1] ENUMERATED { true(0) } OPTIONAL -- Need OR
         }
      } OPTIONAL,
      dataInactivityTimerConfig-r14 [17] EXPLICIT CHOICE {
         release [0] NULL,
         setup [1] SEQUENCE {
            dataInactivityTimer-r14 [0] DataInactivityTimer-r14
         }
      } OPTIONAL
   ]],
   [[
      rai-Activation-r14 [18] ENUMERATED { true(0) } OPTIONAL
   ]],
   [[
      shortTTI-AndSPT-r15 [19] EXPLICIT CHOICE {
         release [0] NULL,
         setup [1] SEQUENCE {
            drx-Config-r15 [0] DRX-Config-r15 OPTIONAL, -- Need ON
            periodicBSR-Timer-r15 [1] ENUMERATED { sf1(0), sf5(1), sf10(2), 
               sf16(3), sf20(4), sf32(5), sf40(6), sf64(7), sf80(8), sf128(9), 
               sf160(10), sf320(11), sf640(12), sf1280(13), sf2560(14), 
               infinity(15) } OPTIONAL,
                     -- Need ON
            proc-Timeline-r15 [2] ENUMERATED { nplus4set1(0), nplus6set1(1), 
               nplus6set2(2), nplus8set2(3) } OPTIONAL, -- Need ON
            ssr-ProhibitTimer-r15 [3] INTEGER (0..7) OPTIONAL -- Need ON
         }
      } OPTIONAL,
      mpdcch-UL-HARQ-ACK-FeedbackConfig-r15 [20] BOOLEAN OPTIONAL,
      dormantStateTimers-r15 [21] EXPLICIT CHOICE {
         release [0] NULL,
         setup [1] SEQUENCE {
            sCellHibernationTimer-r15 [0] ENUMERATED { rf2(0), rf4(1), rf8(2), 
               rf16(3), rf32(4), rf64(5), rf128(6), spare(7) } OPTIONAL, -- Need OR
            dormantSCellDeactivationTimer-r15 [1] ENUMERATED { rf2(0), rf4(1), 
               rf8(2), rf16(3), rf32(4), rf64(5), rf128(6), rf320(7), rf640(8)
               , rf1280(9), rf2560(10), rf5120(11), rf10240(12), spare3(13), 
               spare2(14), spare1(15) } OPTIONAL -- Need OR
         }
      } OPTIONAL
   ]]
}

N1PUCCH-AN-PersistentList ::= SEQUENCE (SIZE (1..4)) OF INTEGER (0..2047)

SPS-ConfigDL ::= CHOICE {
   release [0] NULL,
   setup [1] SEQUENCE {
      semiPersistSchedIntervalDL [0] ENUMERATED { sf10(0), sf20(1), sf32(2), 
         sf40(3), sf64(4), sf80(5), sf128(6), sf160(7), sf320(8), sf640(9), 
         spare6(10), spare5(11), spare4(12), spare3(13), spare2(14), spare1(15)
          },
      numberOfConfSPS-Processes [1] INTEGER (1..8),
      n1PUCCH-AN-PersistentList [2] N1PUCCH-AN-PersistentList,
      ...,
      [[
         twoAntennaPortActivated-r10 [3] EXPLICIT CHOICE {
            release [0] NULL,
            setup [1] SEQUENCE {
               n1PUCCH-AN-PersistentListP1-r10 [0] N1PUCCH-AN-PersistentList
            }
         } OPTIONAL
      ]]
   }
}

TPC-Index ::= CHOICE {
   indexOfFormat3 [0] INTEGER (1..15),
   indexOfFormat3A [1] INTEGER (1..31)
}

TPC-PDCCH-Config ::= CHOICE {
   release [0] NULL,
   setup [1] SEQUENCE {
      tpc-RNTI [0] BIT STRING  (SIZE (16)),
      tpc-Index [1] EXPLICIT TPC-Index
   }
}

SPS-ConfigUL ::= CHOICE {
   release [0] NULL,
   setup [1] SEQUENCE {
      semiPersistSchedIntervalUL [0] ENUMERATED { sf10(0), sf20(1), sf32(2), 
         sf40(3), sf64(4), sf80(5), sf128(6), sf160(7), sf320(8), sf640(9), 
         sf1-v1430(10), sf2-v1430(11), sf3-v1430(12), sf4-v1430(13), 
         sf5-v1430(14), spare1(15) },
      implicitReleaseAfter [1] ENUMERATED { e2(0), e3(1), e4(2), e8(3) },
      p0-Persistent [2] SEQUENCE {
         p0-NominalPUSCH-Persistent [0] INTEGER (-126..24),
         p0-UE-PUSCH-Persistent [1] INTEGER (-8..7)
      } OPTIONAL, -- Need OP
      twoIntervalsConfig [3] ENUMERATED { true(0) } OPTIONAL,
      ...,
      [[
         p0-PersistentSubframeSet2-r12 [4] EXPLICIT CHOICE {
            release [0] NULL,
            setup [1] SEQUENCE {
               p0-NominalPUSCH-PersistentSubframeSet2-r12 [0] INTEGER (-126..24),
               p0-UE-PUSCH-PersistentSubframeSet2-r12 [1] INTEGER (-8..7)
            }
         } OPTIONAL
      ]],
      [[
         numberOfConfUlSPS-Processes-r13 [5] INTEGER (1..8) OPTIONAL
      ]],
      [[
         fixedRV-NonAdaptive-r14 [6] ENUMERATED { true(0) } OPTIONAL,
         sps-ConfigIndex-r14 [7] SPS-ConfigIndex-r14 OPTIONAL,
         semiPersistSchedIntervalUL-v1430 [8] ENUMERATED { sf50(0), sf100(1), 
            sf200(2), sf300(3), sf400(4), sf500(5), sf600(6), sf700(7), 
            sf800(8), sf900(9), sf1000(10), spare5(11), spare4(12), spare3(13)
            , spare2(14), spare1(15) } OPTIONAL
      ]],
      [[
         cyclicShiftSPS-r15 [9] ENUMERATED { cs0(0), cs1(1), cs2(2), cs3(3), 
            cs4(4), cs5(5), cs6(6), cs7(7) } OPTIONAL,
         harq-ProcID-Offset-r15 [10] INTEGER (0..7) OPTIONAL,
         rv-SPS-UL-Repetitions-r15 [11] ENUMERATED { ulrvseq1(0), ulrvseq2(1), 
            ulrvseq3(2) } OPTIONAL,
         tpc-PDCCH-ConfigPUSCH-SPS-r15 [12] EXPLICIT TPC-PDCCH-Config OPTIONAL
            ,
         totalNumberPUSCH-SPS-UL-Repetitions-r15 [13] ENUMERATED { n2(0), n3(1)
            , n4(2), n6(3) } OPTIONAL,
         sps-ConfigIndex-r15 [14] SPS-ConfigIndex-r15 OPTIONAL
      ]]
   }
}

SPS-Config ::= SEQUENCE {
   semiPersistSchedC-RNTI [0] C-RNTI OPTIONAL, -- Need OR
   sps-ConfigDL [1] EXPLICIT SPS-ConfigDL OPTIONAL, -- Need ON
   sps-ConfigUL [2] EXPLICIT SPS-ConfigUL OPTIONAL -- Need ON
}

PDSCH-ConfigDedicated ::= SEQUENCE {
   p-a [0] ENUMERATED { dB-6(0), dB-4dot77(1), dB-3(2), dB-1dot77(3), dB0(4), 
      dB1(5), dB2(6), dB3(7) }
}

PUCCH-ConfigDedicated ::= SEQUENCE {
   ackNackRepetition [0] EXPLICIT CHOICE {
      release [0] NULL,
      setup [1] SEQUENCE {
         repetitionFactor [0] ENUMERATED { n2(0), n4(1), n6(2), spare1(3) },
         n1PUCCH-AN-Rep [1] INTEGER (0..2047)
      }
   },
   tdd-AckNackFeedbackMode [1] ENUMERATED { bundling(0), multiplexing(1) }
       OPTIONAL -- Cond TDD
}

PUSCH-ConfigDedicated ::= SEQUENCE {
   betaOffset-ACK-Index [0] INTEGER (0..15),
   betaOffset-RI-Index [1] INTEGER (0..15),
   betaOffset-CQI-Index [2] INTEGER (0..15)
}

UplinkPowerControlDedicated ::= SEQUENCE {
   p0-UE-PUSCH [0] INTEGER (-8..7),
   deltaMCS-Enabled [1] ENUMERATED { en0(0), en1(1) },
   accumulationEnabled [2] BOOLEAN,
   p0-UE-PUCCH [3] INTEGER (-8..7),
   pSRS-Offset [4] INTEGER (0..15),
   filterCoefficient [5] FilterCoefficient DEFAULT fc4
}

CQI-ReportPeriodic ::= CHOICE {
   release [0] NULL,
   setup [1] SEQUENCE {
      cqi-PUCCH-ResourceIndex [0] INTEGER (0..1185),
      cqi-pmi-ConfigIndex [1] INTEGER (0..1023),
      cqi-FormatIndicatorPeriodic [2] EXPLICIT CHOICE {
         widebandCQI [0] NULL,
         subbandCQI [1] SEQUENCE {
            k [0] INTEGER (1..4)
         }
      },
      ri-ConfigIndex [3] INTEGER (0..1023) OPTIONAL, -- Need OR
      simultaneousAckNackAndCQI [4] BOOLEAN
   }
}

CQI-ReportConfig ::= SEQUENCE {
   cqi-ReportModeAperiodic [0] CQI-ReportModeAperiodic OPTIONAL, -- Need OR
   nomPDSCH-RS-EPRE-Offset [1] INTEGER (-1..6),
   cqi-ReportPeriodic [2] EXPLICIT CQI-ReportPeriodic OPTIONAL -- Need ON
}

SoundingRS-UL-ConfigDedicated ::= CHOICE {
   release [0] NULL,
   setup [1] SEQUENCE {
      srs-Bandwidth [0] ENUMERATED { bw0(0), bw1(1), bw2(2), bw3(3) },
      srs-HoppingBandwidth [1] ENUMERATED { hbw0(0), hbw1(1), hbw2(2), hbw3(3)
          },
      freqDomainPosition [2] INTEGER (0..23),
      duration [3] BOOLEAN,
      srs-ConfigIndex [4] INTEGER (0..1023),
      transmissionComb [5] INTEGER (0..1),
      cyclicShift [6] ENUMERATED { cs0(0), cs1(1), cs2(2), cs3(3), cs4(4), 
         cs5(5), cs6(6), cs7(7) }
   }
}

AntennaInfoDedicated ::= SEQUENCE {
   transmissionMode [0] ENUMERATED { tm1(0), tm2(1), tm3(2), tm4(3), tm5(4), 
      tm6(5), tm7(6), tm8-v920(7) },
   codebookSubsetRestriction [1] EXPLICIT CHOICE {
      n2TxAntenna-tm3 [0] BIT STRING  (SIZE (2)),
      n4TxAntenna-tm3 [1] BIT STRING  (SIZE (4)),
      n2TxAntenna-tm4 [2] BIT STRING  (SIZE (6)),
      n4TxAntenna-tm4 [3] BIT STRING  (SIZE (64)),
      n2TxAntenna-tm5 [4] BIT STRING  (SIZE (4)),
      n4TxAntenna-tm5 [5] BIT STRING  (SIZE (16)),
      n2TxAntenna-tm6 [6] BIT STRING  (SIZE (4)),
      n4TxAntenna-tm6 [7] BIT STRING  (SIZE (16))
   } OPTIONAL, -- Cond TM
   ue-TransmitAntennaSelection [2] EXPLICIT CHOICE {
      release [0] NULL,
      setup [1] ENUMERATED { closedLoop(0), openLoop(1) }
   }
}

SchedulingRequestConfig ::= CHOICE {
   release [0] NULL,
   setup [1] SEQUENCE {
      sr-PUCCH-ResourceIndex [0] INTEGER (0..2047),
      sr-ConfigIndex [1] INTEGER (0..157),
      dsr-TransMax [2] ENUMERATED { n4(0), n8(1), n16(2), n32(3), n64(4), 
         spare3(5), spare2(6), spare1(7) }
   }
}

CQI-ReportConfig-v920 ::= SEQUENCE {
   cqi-Mask-r9 [0] ENUMERATED { setup(0) } OPTIONAL, -- Cond cqi-Setup
   pmi-RI-Report-r9 [1] ENUMERATED { setup(0) } OPTIONAL -- Cond PMIRI
}

AntennaInfoDedicated-v920 ::= SEQUENCE {
   codebookSubsetRestriction-v920 [0] EXPLICIT CHOICE {
      n2TxAntenna-tm8-r9 [0] BIT STRING  (SIZE (6)),
      n4TxAntenna-tm8-r9 [1] BIT STRING  (SIZE (32))
   } OPTIONAL -- Cond TM8
}

AntennaInfoDedicated-r10 ::= SEQUENCE {
   transmissionMode-r10 [0] ENUMERATED { tm1(0), tm2(1), tm3(2), tm4(3), tm5(4)
      , tm6(5), tm7(6), tm8-v920(7), tm9-v1020(8), tm10-v1130(9), spare6(10), 
      spare5(11), spare4(12), spare3(13), spare2(14), spare1(15) },
   codebookSubsetRestriction-r10 [1] BIT STRING  OPTIONAL, -- Cond TMX
   ue-TransmitAntennaSelection [2] EXPLICIT CHOICE {
      release [0] NULL,
      setup [1] ENUMERATED { closedLoop(0), openLoop(1) }
   }
}

AntennaInfoUL-r10 ::= SEQUENCE {
   transmissionModeUL-r10 [0] ENUMERATED { tm1(0), tm2(1), spare6(2), spare5(3)
      , spare4(4), spare3(5), spare2(6), spare1(7) } OPTIONAL, -- Need OR
   fourAntennaPortActivated-r10 [1] ENUMERATED { setup(0) } OPTIONAL -- Need OR
}

CQI-ReportAperiodic-r10 ::= CHOICE {
   release [0] NULL,
   setup [1] SEQUENCE {
      cqi-ReportModeAperiodic-r10 [0] CQI-ReportModeAperiodic,
      aperiodicCSI-Trigger-r10 [1] SEQUENCE {
         trigger1-r10 [0] BIT STRING  (SIZE (8)),
         trigger2-r10 [1] BIT STRING  (SIZE (8))
      } OPTIONAL -- Need OR
   }
}

CQI-ReportPeriodic-r10 ::= CHOICE {
   release [0] NULL,
   setup [1] SEQUENCE {
      cqi-PUCCH-ResourceIndex-r10 [0] INTEGER (0..1184),
      cqi-PUCCH-ResourceIndexP1-r10 [1] INTEGER (0..1184) OPTIONAL, -- Need OR
      cqi-pmi-ConfigIndex [2] INTEGER (0..1023),
      cqi-FormatIndicatorPeriodic-r10 [3] EXPLICIT CHOICE {
         widebandCQI-r10 [0] SEQUENCE {
            csi-ReportMode-r10 [0] ENUMERATED { submode1(0), submode2(1) }
                OPTIONAL -- Need OR
         },
         subbandCQI-r10 [1] SEQUENCE {
            k [0] INTEGER (1..4),
            periodicityFactor-r10 [1] ENUMERATED { n2(0), n4(1) }
         }
      },
      ri-ConfigIndex [4] INTEGER (0..1023) OPTIONAL, -- Need OR
      simultaneousAckNackAndCQI [5] BOOLEAN,
      cqi-Mask-r9 [6] ENUMERATED { setup(0) } OPTIONAL, -- Need OR
      csi-ConfigIndex-r10 [7] EXPLICIT CHOICE {
         release [0] NULL,
         setup [1] SEQUENCE {
            cqi-pmi-ConfigIndex2-r10 [0] INTEGER (0..1023),
            ri-ConfigIndex2-r10 [1] INTEGER (0..1023) OPTIONAL -- Need OR
         }
      } OPTIONAL -- Need ON
   }
}

MeasSubframePattern-r10 ::= CHOICE {
   subframePatternFDD-r10 [0] BIT STRING  (SIZE (40)),
   subframePatternTDD-r10 [1] EXPLICIT CHOICE {
      subframeConfig1-5-r10 [0] BIT STRING  (SIZE (20)),
      subframeConfig0-r10 [1] BIT STRING  (SIZE (70)),
      subframeConfig6-r10 [2] BIT STRING  (SIZE (60)),
      ...
   },
   ...
}

CQI-ReportConfig-r10 ::= SEQUENCE {
   cqi-ReportAperiodic-r10 [0] EXPLICIT CQI-ReportAperiodic-r10 OPTIONAL, -- Need ON
   nomPDSCH-RS-EPRE-Offset [1] INTEGER (-1..6),
   cqi-ReportPeriodic-r10 [2] EXPLICIT CQI-ReportPeriodic-r10 OPTIONAL, -- Need ON
   pmi-RI-Report-r9 [3] ENUMERATED { setup(0) } OPTIONAL, -- Cond PMIRIPCell
   csi-SubframePatternConfig-r10 [4] EXPLICIT CHOICE {
      release [0] NULL,
      setup [1] SEQUENCE {
         csi-MeasSubframeSet1-r10 [0] EXPLICIT MeasSubframePattern-r10,
         csi-MeasSubframeSet2-r10 [1] EXPLICIT MeasSubframePattern-r10
      }
   } OPTIONAL -- Need ON
}

ZeroTxPowerCSI-RS-r12 ::= SEQUENCE {
   zeroTxPowerResourceConfigList-r12 [0] BIT STRING  (SIZE (16)),
   zeroTxPowerSubframeConfig-r12 [1] INTEGER (0..154)
}

ZeroTxPowerCSI-RS-Conf-r12 ::= CHOICE {
   release [0] NULL,
   setup [1] ZeroTxPowerCSI-RS-r12
}

CSI-RS-Config-r10 ::= SEQUENCE {
   csi-RS-r10 [0] EXPLICIT CHOICE {
      release [0] NULL,
      setup [1] SEQUENCE {
         antennaPortsCount-r10 [0] ENUMERATED { an1(0), an2(1), an4(2), an8(3)
             },
         resourceConfig-r10 [1] INTEGER (0..31),
         subframeConfig-r10 [2] INTEGER (0..154),
         p-C-r10 [3] INTEGER (-8..15)
      }
   } OPTIONAL, -- Need ON
   zeroTxPowerCSI-RS-r10 [1] EXPLICIT ZeroTxPowerCSI-RS-Conf-r12 OPTIONAL -- Need ON
}

PUCCH-Format3-Conf-r13 ::= SEQUENCE {
   n3PUCCH-AN-List-r13 [0] SEQUENCE (SIZE (1..4)) OF INTEGER (0..549) OPTIONAL, -- Need ON
   twoAntennaPortActivatedPUCCH-Format3-r13 [1] EXPLICIT CHOICE {
      release [0] NULL,
      setup [1] SEQUENCE {
         n3PUCCH-AN-ListP1-r13 [0] SEQUENCE (SIZE (1..4)) OF INTEGER (0..549)
      }
   } OPTIONAL -- Need ON
}

N1PUCCH-AN-CS-r10 ::= SEQUENCE (SIZE (1..4)) OF INTEGER (0..2047)

PUCCH-ConfigDedicated-v1020 ::= SEQUENCE {
   pucch-Format-r10 [0] EXPLICIT CHOICE {
      format3-r10 [0] PUCCH-Format3-Conf-r13,
      channelSelection-r10 [1] SEQUENCE {
         n1PUCCH-AN-CS-r10 [0] EXPLICIT CHOICE {
            release [0] NULL,
            setup [1] SEQUENCE {
               n1PUCCH-AN-CS-List-r10 [0] SEQUENCE (SIZE (1..2)) OF 
                  N1PUCCH-AN-CS-r10
            }
         } OPTIONAL -- Need ON
      }
   } OPTIONAL, -- Need OR
   twoAntennaPortActivatedPUCCH-Format1a1b-r10 [1] ENUMERATED { true(0) }
       OPTIONAL, -- Need OR
   simultaneousPUCCH-PUSCH-r10 [2] ENUMERATED { true(0) } OPTIONAL, -- Need OR
   n1PUCCH-AN-RepP1-r10 [3] INTEGER (0..2047) OPTIONAL -- Need OR
}

PUSCH-ConfigDedicated-v1020 ::= SEQUENCE {
   betaOffsetMC-r10 [0] SEQUENCE {
      betaOffset-ACK-Index-MC-r10 [0] INTEGER (0..15),
      betaOffset-RI-Index-MC-r10 [1] INTEGER (0..15),
      betaOffset-CQI-Index-MC-r10 [2] INTEGER (0..15)
   } OPTIONAL, -- Need OR
   groupHoppingDisabled-r10 [1] ENUMERATED { true(0) } OPTIONAL, -- Need OR
   dmrs-WithOCC-Activated-r10 [2] ENUMERATED { true(0) } OPTIONAL -- Need OR
}

SchedulingRequestConfig-v1020 ::= SEQUENCE {
   sr-PUCCH-ResourceIndexP1-r10 [0] INTEGER (0..2047) OPTIONAL -- Need OR
}

SoundingRS-UL-ConfigDedicated-v1020 ::= SEQUENCE {
   srs-AntennaPort-r10 [0] SRS-AntennaPort
}

SRS-ConfigAp-r10 ::= SEQUENCE {
   srs-AntennaPortAp-r10 [0] SRS-AntennaPort,
   srs-BandwidthAp-r10 [1] ENUMERATED { bw0(0), bw1(1), bw2(2), bw3(3) },
   freqDomainPositionAp-r10 [2] INTEGER (0..23),
   transmissionCombAp-r10 [3] INTEGER (0..1),
   cyclicShiftAp-r10 [4] ENUMERATED { cs0(0), cs1(1), cs2(2), cs3(3), cs4(4), 
      cs5(5), cs6(6), cs7(7) }
}

SoundingRS-UL-ConfigDedicatedAperiodic-r10 ::= CHOICE {
   release [0] NULL,
   setup [1] SEQUENCE {
      srs-ConfigIndexAp-r10 [0] INTEGER (0..31),
      srs-ConfigApDCI-Format4-r10 [1] SEQUENCE (SIZE (1..3)) OF SRS-ConfigAp-r10
          OPTIONAL, --Need ON
      srs-ActivateAp-r10 [2] EXPLICIT CHOICE {
         release [0] NULL,
         setup [1] SEQUENCE {
            srs-ConfigApDCI-Format0-r10 [0] SRS-ConfigAp-r10,
            srs-ConfigApDCI-Format1a2b2c-r10 [1] SRS-ConfigAp-r10,
            ...
         }
      } OPTIONAL -- Need ON
   }
}

DeltaTxD-OffsetListPUCCH-r10 ::= SEQUENCE {
   deltaTxD-OffsetPUCCH-Format1-r10 [0] ENUMERATED { dB0(0), dB-2(1) },
   deltaTxD-OffsetPUCCH-Format1a1b-r10 [1] ENUMERATED { dB0(0), dB-2(1) },
   deltaTxD-OffsetPUCCH-Format22a2b-r10 [2] ENUMERATED { dB0(0), dB-2(1) },
   deltaTxD-OffsetPUCCH-Format3-r10 [3] ENUMERATED { dB0(0), dB-2(1) },
   ...
}

UplinkPowerControlDedicated-v1020 ::= SEQUENCE {
   deltaTxD-OffsetListPUCCH-r10 [0] DeltaTxD-OffsetListPUCCH-r10 OPTIONAL, -- Need OR
   pSRS-OffsetAp-r10 [1] INTEGER (0..15) OPTIONAL -- Need OR
}

CSI-RS-ConfigNZPToReleaseList-r11 ::= SEQUENCE (SIZE (1..maxCSI-RS-NZP-r11)) OF 
   CSI-RS-ConfigNZPId-r11

CSI-RS-ConfigNZP-r11 ::= SEQUENCE {
   csi-RS-ConfigNZPId-r11 [0] CSI-RS-ConfigNZPId-r11,
   antennaPortsCount-r11 [1] ENUMERATED { an1(0), an2(1), an4(2), an8(3) },
   resourceConfig-r11 [2] INTEGER (0..31),
   subframeConfig-r11 [3] INTEGER (0..154),
   scramblingIdentity-r11 [4] INTEGER (0..503),
   qcl-CRS-Info-r11 [5] SEQUENCE {
      qcl-ScramblingIdentity-r11 [0] INTEGER (0..503),
      crs-PortsCount-r11 [1] ENUMERATED { n1(0), n2(1), n4(2), spare1(3) },
      mbsfn-SubframeConfigList-r11 [2] EXPLICIT CHOICE {
         release [0] NULL,
         setup [1] SEQUENCE {
            subframeConfigList [0] MBSFN-SubframeConfigList
         }
      } OPTIONAL -- Need ON
   } OPTIONAL,
   ...,
   [[
      csi-RS-ConfigNZPId-v1310 [6] CSI-RS-ConfigNZPId-v1310 OPTIONAL
   ]],
   [[
      transmissionComb-r14 [7] NZP-TransmissionComb-r14 OPTIONAL,
      frequencyDensity-r14 [8] NZP-FrequencyDensity-r14 OPTIONAL
   ]],
   [[
      mbsfn-SubframeConfigList-v1430 [9] EXPLICIT CHOICE {
         release [0] NULL,
         setup [1] SEQUENCE {
            subframeConfigList-v1430 [0] MBSFN-SubframeConfigList-v1430
         }
      } OPTIONAL
   ]]
}

CSI-RS-ConfigNZPToAddModList-r11 ::= SEQUENCE (SIZE (1..maxCSI-RS-NZP-r11)) OF 
   CSI-RS-ConfigNZP-r11

CSI-RS-ConfigZPToReleaseList-r11 ::= SEQUENCE (SIZE (1..maxCSI-RS-ZP-r11)) OF 
   CSI-RS-ConfigZPId-r11

CSI-RS-ConfigZP-r11 ::= SEQUENCE {
   csi-RS-ConfigZPId-r11 [0] CSI-RS-ConfigZPId-r11,
   resourceConfigList-r11 [1] BIT STRING  (SIZE (16)),
   subframeConfig-r11 [2] INTEGER (0..154),
   ...
}

CSI-RS-ConfigZPToAddModList-r11 ::= SEQUENCE (SIZE (1..maxCSI-RS-ZP-r11)) OF CSI-RS-ConfigZP-r11
   

EPDCCH-SetConfigToReleaseList-r11 ::= SEQUENCE (SIZE (1..maxEPDCCH-Set-r11)) OF 
   EPDCCH-SetConfigId-r11

EPDCCH-SetConfig-r11 ::= SEQUENCE {
   setConfigId-r11 [0] EPDCCH-SetConfigId-r11,
   transmissionType-r11 [1] ENUMERATED { localised(0), distributed(1) },
   resourceBlockAssignment-r11 [2] SEQUENCE {
      numberPRB-Pairs-r11 [0] ENUMERATED { n2(0), n4(1), n8(2) },
      resourceBlockAssignment-r11 [1] BIT STRING  (SIZE (4..38))
   },
   dmrs-ScramblingSequenceInt-r11 [3] INTEGER (0..503),
   pucch-ResourceStartOffset-r11 [4] INTEGER (0..2047),
   re-MappingQCL-ConfigId-r11 [5] PDSCH-RE-MappingQCL-ConfigId-r11 OPTIONAL,
   ...,
   [[
      csi-RS-ConfigZPId2-r12 [6] EXPLICIT CHOICE {
         release [0] NULL,
         setup [1] CSI-RS-ConfigZPId-r11
      } OPTIONAL
   ]],
   [[
      numberPRB-Pairs-v1310 [7] EXPLICIT CHOICE {
         release [0] NULL,
         setup [1] ENUMERATED { n6(0) }
      } OPTIONAL,
      mpdcch-config-r13 [8] EXPLICIT CHOICE {
         release [0] NULL,
         setup [1] SEQUENCE {
            csi-NumRepetitionCE-r13 [0] ENUMERATED { sf1(0), sf2(1), sf4(2), 
               sf8(3), sf16(4), sf32(5) },
            mpdcch-pdsch-HoppingConfig-r13 [1] ENUMERATED { on(0), off(1) },
            mpdcch-StartSF-UESS-r13 [2] EXPLICIT CHOICE {
               fdd-r13 [0] ENUMERATED { v1(0), v1dot5(1), v2(2), v2dot5(3), 
                  v4(4), v5(5), v8(6), v10(7) },
               tdd-r13 [1] ENUMERATED { v1(0), v2(1), v4(2), v5(3), v8(4), 
                  v10(5), v20(6), spare1(7) }
            },
            mpdcch-NumRepetition-r13 [3] ENUMERATED { r1(0), r2(1), r4(2), 
               r8(3), r16(4), r32(5), r64(6), r128(7), r256(8) },
            mpdcch-Narrowband-r13 [4] INTEGER (1..maxAvailNarrowBands-r13)
         }
      } OPTIONAL
   ]]
}

EPDCCH-SetConfigToAddModList-r11 ::= SEQUENCE (SIZE (1..maxEPDCCH-Set-r11)) OF 
   EPDCCH-SetConfig-r11

EPDCCH-Config-r11 ::= SEQUENCE {
   config-r11 [0] EXPLICIT CHOICE {
      release [0] NULL,
      setup [1] SEQUENCE {
         subframePatternConfig-r11 [0] EXPLICIT CHOICE {
            release [0] NULL,
            setup [1] SEQUENCE {
               subframePattern-r11 [0] EXPLICIT MeasSubframePattern-r10
            }
         } OPTIONAL, -- Need ON
         startSymbol-r11 [1] INTEGER (1..4) OPTIONAL, -- Need OP
         setConfigToReleaseList-r11 [2] EPDCCH-SetConfigToReleaseList-r11
             OPTIONAL, -- Need ON
         setConfigToAddModList-r11 [3] EPDCCH-SetConfigToAddModList-r11
             OPTIONAL -- Need ON
      }
   }
}

DMRS-Config-r11 ::= CHOICE {
   release [0] NULL,
   setup [1] SEQUENCE {
      scramblingIdentity-r11 [0] INTEGER (0..503),
      scramblingIdentity2-r11 [1] INTEGER (0..503)
   }
}

RE-MappingQCLConfigToReleaseList-r11 ::= SEQUENCE (SIZE (1..maxRE-MapQCL-r11)) OF 
   PDSCH-RE-MappingQCL-ConfigId-r11

PDSCH-RE-MappingQCL-Config-r11 ::= SEQUENCE {
   pdsch-RE-MappingQCL-ConfigId-r11 [0] PDSCH-RE-MappingQCL-ConfigId-r11,
   optionalSetOfFields-r11 [1] SEQUENCE {
      crs-PortsCount-r11 [0] ENUMERATED { n1(0), n2(1), n4(2), spare1(3) },
      crs-FreqShift-r11 [1] INTEGER (0..5),
      mbsfn-SubframeConfigList-r11 [2] EXPLICIT CHOICE {
         release [0] NULL,
         setup [1] SEQUENCE {
            subframeConfigList [0] MBSFN-SubframeConfigList
         }
      } OPTIONAL, -- Need ON
      pdsch-Start-r11 [3] ENUMERATED { reserved(0), n1(1), n2(2), n3(3), n4(4)
         , assigned(5) }
   } OPTIONAL, -- Need OP
   csi-RS-ConfigZPId-r11 [2] CSI-RS-ConfigZPId-r11,
   qcl-CSI-RS-ConfigNZPId-r11 [3] CSI-RS-ConfigNZPId-r11 OPTIONAL,
   ...,
   [[
      mbsfn-SubframeConfigList-v1430 [4] EXPLICIT CHOICE {
         release [0] NULL,
         setup [1] SEQUENCE {
            subframeConfigList-v1430 [0] MBSFN-SubframeConfigList-v1430
         }
      } OPTIONAL
   ]],
   [[
      codewordOneConfig-v1530 [5] EXPLICIT CHOICE {
         release [0] NULL,
         setup [1] SEQUENCE {
            crs-PortsCount-v1530 [0] ENUMERATED { n1(0), n2(1), n4(2), 
               spare1(3) },
            crs-FreqShift-v1530 [1] INTEGER (0..5),
            mbsfn-SubframeConfigList-v1530 [2] MBSFN-SubframeConfigList
                OPTIONAL,
            mbsfn-SubframeConfigListExt-v1530 [3] 
               MBSFN-SubframeConfigList-v1430 OPTIONAL,
            pdsch-Start-v1530 [4] ENUMERATED { reserved(0), n1(1), n2(2), n3(3)
               , n4(4), assigned(5) },
            csi-RS-ConfigZPId-v1530 [5] CSI-RS-ConfigZPId-r11,
            qcl-CSI-RS-ConfigNZPId-v1530 [6] CSI-RS-ConfigNZPId-r11 OPTIONAL
         }
      } OPTIONAL
   ]]
}

RE-MappingQCLConfigToAddModList-r11 ::= SEQUENCE (SIZE (1..maxRE-MapQCL-r11)) OF 
   PDSCH-RE-MappingQCL-Config-r11

PDSCH-ConfigDedicated-v1130 ::= SEQUENCE {
   dmrs-ConfigPDSCH-r11 [0] EXPLICIT DMRS-Config-r11 OPTIONAL, -- Need ON
   qcl-Operation [1] ENUMERATED { typeA(0), typeB(1) } OPTIONAL, -- Need OR
   re-MappingQCLConfigToReleaseList-r11 [2] 
      RE-MappingQCLConfigToReleaseList-r11 OPTIONAL, -- Need ON
   re-MappingQCLConfigToAddModList-r11 [3] RE-MappingQCLConfigToAddModList-r11
       OPTIONAL -- Need ON
}

CQI-ReportPeriodicProcExtToReleaseList-r11 ::= SEQUENCE (SIZE (1..maxCQI-ProcExt-r11)) OF 
   CQI-ReportPeriodicProcExtId-r11

CRI-ReportConfig-r13 ::= CHOICE {
   release [0] NULL,
   setup [1] SEQUENCE {
      cri-ConfigIndex-r13 [0] CRI-ConfigIndex-r13,
      cri-ConfigIndex2-r13 [1] CRI-ConfigIndex-r13 OPTIONAL -- Need OR
   }
}

CQI-ReportPeriodicProcExt-r11 ::= SEQUENCE {
   cqi-ReportPeriodicProcExtId-r11 [0] CQI-ReportPeriodicProcExtId-r11,
   cqi-pmi-ConfigIndex-r11 [1] INTEGER (0..1023),
   cqi-FormatIndicatorPeriodic-r11 [2] EXPLICIT CHOICE {
      widebandCQI-r11 [0] SEQUENCE {
         csi-ReportMode-r11 [0] ENUMERATED { submode1(0), submode2(1) }
             OPTIONAL -- Need OR
      },
      subbandCQI-r11 [1] SEQUENCE {
         k [0] INTEGER (1..4),
         periodicityFactor-r11 [1] ENUMERATED { n2(0), n4(1) }
      }
   },
   ri-ConfigIndex-r11 [3] INTEGER (0..1023) OPTIONAL, -- Need OR
   csi-ConfigIndex-r11 [4] EXPLICIT CHOICE {
      release [0] NULL,
      setup [1] SEQUENCE {
         cqi-pmi-ConfigIndex2-r11 [0] INTEGER (0..1023),
         ri-ConfigIndex2-r11 [1] INTEGER (0..1023) OPTIONAL -- Need OR
      }
   } OPTIONAL,
   ...,
   [[
      cri-ReportConfig-r13 [5] EXPLICIT CRI-ReportConfig-r13 OPTIONAL
   ]],
   [[
      periodicityFactorWB-r13 [6] ENUMERATED { n2(0), n4(1) } OPTIONAL
   ]]
}

CQI-ReportPeriodicProcExtToAddModList-r11 ::= SEQUENCE (SIZE (1..maxCQI-ProcExt-r11)) OF 
   CQI-ReportPeriodicProcExt-r11

CQI-ReportPeriodic-v1130 ::= SEQUENCE {
   simultaneousAckNackAndCQI-Format3-r11 [0] ENUMERATED { setup(0) } OPTIONAL, -- Need OR
   cqi-ReportPeriodicProcExtToReleaseList-r11 [1] 
      CQI-ReportPeriodicProcExtToReleaseList-r11 OPTIONAL, -- Need ON
   cqi-ReportPeriodicProcExtToAddModList-r11 [2] 
      CQI-ReportPeriodicProcExtToAddModList-r11 OPTIONAL -- Need ON
}

CSI-IM-ConfigToReleaseList-r11 ::= SEQUENCE (SIZE (1..maxCSI-IM-r11)) OF CSI-IM-ConfigId-r11

CSI-IM-Config-r11 ::= SEQUENCE {
   csi-IM-ConfigId-r11 [0] CSI-IM-ConfigId-r11,
   resourceConfig-r11 [1] INTEGER (0..31),
   subframeConfig-r11 [2] INTEGER (0..154),
   ...,
   [[
      interferenceMeasRestriction-r13 [3] BOOLEAN OPTIONAL
   ]]
}

CSI-IM-ConfigToAddModList-r11 ::= SEQUENCE (SIZE (1..maxCSI-IM-r11)) OF CSI-IM-Config-r11

CSI-ProcessToReleaseList-r11 ::= SEQUENCE (SIZE (1..maxCSI-Proc-r11)) OF CSI-ProcessId-r11

P-C-AndCBSR-r11 ::= SEQUENCE {
   p-C-r11 [0] INTEGER (-8..15),
   codebookSubsetRestriction-r11 [1] BIT STRING 
}

P-C-AndCBSR-Pair-r13a ::= SEQUENCE (SIZE (1..2)) OF P-C-AndCBSR-r11

CQI-ReportBothProc-r11 ::= SEQUENCE {
   ri-Ref-CSI-ProcessId-r11 [0] CSI-ProcessId-r11 OPTIONAL, -- Need OR
   pmi-RI-Report-r11 [1] ENUMERATED { setup(0) } OPTIONAL -- Need OR
}

CQI-ReportAperiodicProc-r11 ::= SEQUENCE {
   cqi-ReportModeAperiodic-r11 [0] CQI-ReportModeAperiodic,
   trigger01-r11 [1] BOOLEAN,
   trigger10-r11 [2] BOOLEAN,
   trigger11-r11 [3] BOOLEAN
}

CQI-ReportAperiodicProc-v1310 ::= SEQUENCE {
   trigger001-r13 [0] BOOLEAN,
   trigger010-r13 [1] BOOLEAN,
   trigger011-r13 [2] BOOLEAN,
   trigger100-r13 [3] BOOLEAN,
   trigger101-r13 [4] BOOLEAN,
   trigger110-r13 [5] BOOLEAN,
   trigger111-r13 [6] BOOLEAN
}

P-C-AndCBSR-r13 ::= SEQUENCE {
   p-C-r13 [0] INTEGER (-8..15),
   cbsr-Selection-r13 [1] EXPLICIT CHOICE {
      nonPrecoded-r13 [0] SEQUENCE {
         codebookSubsetRestriction1-r13 [0] BIT STRING ,
         codebookSubsetRestriction2-r13 [1] BIT STRING 
      },
      beamformedK1a-r13 [1] SEQUENCE {
         codebookSubsetRestriction3-r13 [0] BIT STRING 
      },
      beamformedKN-r13 [2] SEQUENCE {
         codebookSubsetRestriction-r13 [0] BIT STRING 
      }
   },
   ...
}

P-C-AndCBSR-Pair-r13 ::= SEQUENCE (SIZE (1..2)) OF P-C-AndCBSR-r13

NZP-ResourceConfig-r13 ::= SEQUENCE {
   resourceConfig-r13 [0] ResourceConfig-r13,
   ...,
   [[
      transmissionComb-r14 [1] NZP-TransmissionComb-r14 OPTIONAL,
      frequencyDensity-r14 [2] NZP-FrequencyDensity-r14 OPTIONAL
   ]]
}

CSI-RS-ConfigNZP-EMIMO-r13 ::= CHOICE {
   release [0] NULL,
   setup [1] SEQUENCE {
      nzp-resourceConfigList-r13 [0] SEQUENCE (SIZE (1..2)) OF 
         NZP-ResourceConfig-r13,
      cdmType-r13 [1] ENUMERATED { cdm2(0), cdm4(1) } OPTIONAL -- Need OR
   }
}

CSI-RS-ConfigNonPrecoded-r13 ::= SEQUENCE {
   p-C-AndCBSRList-r13 [0] P-C-AndCBSR-Pair-r13 OPTIONAL, -- Need OR
   codebookConfigN1-r13 [1] ENUMERATED { n1(0), n2(1), n3(2), n4(3), n8(4) },
   codebookConfigN2-r13 [2] ENUMERATED { n1(0), n2(1), n3(2), n4(3), n8(4) },
   codebookOverSamplingRateConfig-O1-r13 [3] ENUMERATED { n4(0), n8(1) }
       OPTIONAL, -- Need OR
   codebookOverSamplingRateConfig-O2-r13 [4] ENUMERATED { n4(0), n8(1) }
       OPTIONAL, -- Need OR
   codebookConfig-r13 [5] INTEGER (1..4),
   csi-IM-ConfigIdList-r13 [6] SEQUENCE (SIZE (1..2)) OF CSI-IM-ConfigId-r13
       OPTIONAL, -- Need OR
   csi-RS-ConfigNZP-EMIMO-r13 [7] EXPLICIT CSI-RS-ConfigNZP-EMIMO-r13 OPTIONAL -- Need ON
}

CSI-RS-ConfigBeamformed-r13 ::= SEQUENCE {
   csi-RS-ConfigNZPIdListExt-r13 [0] SEQUENCE (SIZE (1..7)) OF 
      CSI-RS-ConfigNZPId-r13 OPTIONAL, -- Need OR
   csi-IM-ConfigIdList-r13 [1] SEQUENCE (SIZE (1..8)) OF CSI-IM-ConfigId-r13
       OPTIONAL, -- Need OR
   p-C-AndCBSR-PerResourceConfigList-r13 [2] SEQUENCE (SIZE (1..8)) OF 
      P-C-AndCBSR-Pair-r13 OPTIONAL, -- Need OR
   ace-For4Tx-PerResourceConfigList-r13 [3] SEQUENCE (SIZE (1..7)) OF BOOLEAN
       OPTIONAL, -- Need OR
   alternativeCodebookEnabledBeamformed-r13 [4] ENUMERATED { true(0) } OPTIONAL
      , -- Need OR
   channelMeasRestriction-r13 [5] ENUMERATED { on(0) } OPTIONAL -- Need OR
}

CSI-RS-ConfigEMIMO-r13 ::= CHOICE {
   release [0] NULL,
   setup [1] EXPLICIT CHOICE {
      nonPrecoded-r13 [0] CSI-RS-ConfigNonPrecoded-r13,
      beamformed-r13 [1] CSI-RS-ConfigBeamformed-r13
   }
}

CSI-RS-ConfigNZP-EMIMO-v1430 ::= SEQUENCE {
--All extensions are for Non-Precoded so could be grouped by setup/ release choice
   nzp-resourceConfigListExt-r14 [0] SEQUENCE (SIZE (0..4)) OF 
      NZP-ResourceConfig-r13,
   cdmType-v1430 [1] ENUMERATED { cdm8(0) } OPTIONAL -- Need OR
}

CSI-RS-Config-NZP-v1430 ::= SEQUENCE {
   transmissionComb-r14 [0] NZP-TransmissionComb-r14 OPTIONAL, -- Need OR
   frequencyDensity-r14 [1] NZP-FrequencyDensity-r14 OPTIONAL -- Need OR
}

CSI-RS-ConfigNonPrecoded-v1430 ::= SEQUENCE {
   csi-RS-ConfigNZP-EMIMO-v1430 [0] CSI-RS-ConfigNZP-EMIMO-v1430 OPTIONAL, -- Need ON
   codebookConfigN1-v1430 [1] ENUMERATED { n5(0), n6(1), n7(2), n10(3), n12(4)
      , n14(5), n16(6) },
   codebookConfigN2-v1430 [2] ENUMERATED { n5(0), n6(1), n7(2) },
   nzp-ResourceConfigTM9-Original-v1430 [3] CSI-RS-Config-NZP-v1430
}

CSI-RS-ConfigNZP-Activation-r14 ::= SEQUENCE {
   csi-RS-NZP-mode-r14 [0] ENUMERATED { semiPersistent(0), aperiodic(1) },
   activatedResources-r14 [1] INTEGER (0..4)
}

CSI-RS-ConfigBeamformed-v1430 ::= SEQUENCE {
   csi-RS-ConfigNZP-ApList-r14 [0] SEQUENCE (SIZE (1..8)) OF CSI-RS-ConfigNZP-r11
       OPTIONAL,
                           -- Need OR
   nzp-ResourceConfigOriginal-v1430 [1] CSI-RS-Config-NZP-v1430 OPTIONAL, -- Need OR
   csi-RS-NZP-Activation-r14 [2] CSI-RS-ConfigNZP-Activation-r14 OPTIONAL -- Need OR
}

CSI-RS-ConfigEMIMO-v1430 ::= CHOICE {
   release [0] NULL,
   setup [1] EXPLICIT CHOICE {
      nonPrecoded-v1430 [0] CSI-RS-ConfigNonPrecoded-v1430,
      beamformed-v1430 [1] CSI-RS-ConfigBeamformed-v1430
   }
}

CSI-RS-ConfigBeamformed-r14 ::= SEQUENCE {
   csi-RS-ConfigNZPIdListExt-r14 [0] SEQUENCE (SIZE (1..7)) OF 
      CSI-RS-ConfigNZPId-r13 OPTIONAL, -- Need OR
   csi-IM-ConfigIdList-r14 [1] SEQUENCE (SIZE (1..8)) OF CSI-IM-ConfigId-r13
       OPTIONAL, -- Need OR
   p-C-AndCBSR-PerResourceConfigList-r14 [2] SEQUENCE (SIZE (1..8)) OF 
      P-C-AndCBSR-Pair-r13 OPTIONAL, -- Need OR
   ace-For4Tx-PerResourceConfigList-r14 [3] SEQUENCE (SIZE (1..7)) OF BOOLEAN
       OPTIONAL, -- Need OR
   alternativeCodebookEnabledBeamformed-r14 [4] ENUMERATED { true(0) } OPTIONAL
      , -- Need OR
   channelMeasRestriction-r14 [5] ENUMERATED { on(0) } OPTIONAL, -- Need OR
   csi-RS-ConfigNZP-ApList-r14 [6] SEQUENCE (SIZE (1..8)) OF CSI-RS-ConfigNZP-r11
       OPTIONAL,
                           -- Need OR
   nzp-ResourceConfigOriginal-v1430 [7] CSI-RS-Config-NZP-v1430 OPTIONAL, -- Need OR
   csi-RS-NZP-Activation-r14 [8] CSI-RS-ConfigNZP-Activation-r14 OPTIONAL -- Need OR
}

CSI-RS-ConfigEMIMO2-r14 ::= CHOICE {
   release [0] NULL,
   setup [1] CSI-RS-ConfigBeamformed-r14
}

CSI-RS-ConfigEMIMO-Hybrid-r14 ::= CHOICE {
   release [0] NULL,
   setup [1] SEQUENCE {
      periodicityOffsetIndex-r14 [0] INTEGER (0..1023) OPTIONAL, -- Need OR
      eMIMO-Type2-r14 [1] EXPLICIT CSI-RS-ConfigEMIMO2-r14 OPTIONAL -- Need ON
   }
}

CSI-RS-ConfigNonPrecoded-v1480 ::= SEQUENCE {
   csi-RS-ConfigNZP-EMIMO-v1480 [0] CSI-RS-ConfigNZP-EMIMO-v1430 OPTIONAL, -- Need ON
   codebookConfigN1-v1480 [1] ENUMERATED { n5(0), n6(1), n7(2), n10(3), n12(4)
      , n14(5), n16(6) } OPTIONAL, -- Need OR
   codebookConfigN2-r1480 [2] ENUMERATED { n5(0), n6(1), n7(2) } OPTIONAL, -- Need OR
   nzp-ResourceConfigTM9-Original-v1480 [3] CSI-RS-Config-NZP-v1430
}

CSI-RS-ConfigEMIMO-v1480 ::= CHOICE {
   release [0] NULL,
   setup [1] EXPLICIT CHOICE {
      nonPrecoded-v1480 [0] CSI-RS-ConfigNonPrecoded-v1480,
      beamformed-v1480 [1] CSI-RS-ConfigBeamformed-v1430
   }
}

P-C-AndCBSR-r15 ::= SEQUENCE {
   p-C-r15 [0] INTEGER (-8..15),
   codebookSubsetRestriction4-r15 [1] BIT STRING 
}

P-C-AndCBSR-Pair-r15 ::= SEQUENCE (SIZE (1..2)) OF P-C-AndCBSR-r15

CSI-RS-ConfigNonPrecoded-v1530 ::= SEQUENCE {
   p-C-AndCBSRList-r15 [0] P-C-AndCBSR-Pair-r15 OPTIONAL -- Need OR
}

CSI-RS-ConfigEMIMO-v1530 ::= CHOICE {
   release [0] NULL,
   setup [1] EXPLICIT CHOICE {
      nonPrecoded-v1530 [0] CSI-RS-ConfigNonPrecoded-v1530
   }
}

CSI-Process-r11 ::= SEQUENCE {
   csi-ProcessId-r11 [0] CSI-ProcessId-r11,
   csi-RS-ConfigNZPId-r11 [1] CSI-RS-ConfigNZPId-r11,
   csi-IM-ConfigId-r11 [2] CSI-IM-ConfigId-r11,
   p-C-AndCBSRList-r11 [3] P-C-AndCBSR-Pair-r13a,
   cqi-ReportBothProc-r11 [4] CQI-ReportBothProc-r11 OPTIONAL, -- Need OR
   cqi-ReportPeriodicProcId-r11 [5] INTEGER (0..maxCQI-ProcExt-r11) OPTIONAL, -- Need OR
   cqi-ReportAperiodicProc-r11 [6] CQI-ReportAperiodicProc-r11 OPTIONAL,
   ...,
   [[
      alternativeCodebookEnabledFor4TXProc-r12 [7] ENUMERATED { true(0) }
          OPTIONAL,
      csi-IM-ConfigIdList-r12 [8] EXPLICIT CHOICE {
         release [0] NULL,
         setup [1] SEQUENCE (SIZE (1..2)) OF CSI-IM-ConfigId-r12
      } OPTIONAL,
      cqi-ReportAperiodicProc2-r12 [9] EXPLICIT CHOICE {
         release [0] NULL,
         setup [1] CQI-ReportAperiodicProc-r11
      } OPTIONAL
   ]],
   [[
      cqi-ReportAperiodicProc-v1310 [10] EXPLICIT CHOICE {
         release [0] NULL,
         setup [1] CQI-ReportAperiodicProc-v1310
      } OPTIONAL,
      cqi-ReportAperiodicProc2-v1310 [11] EXPLICIT CHOICE {
         release [0] NULL,
         setup [1] CQI-ReportAperiodicProc-v1310
      } OPTIONAL,
      eMIMO-Type-r13 [12] EXPLICIT CSI-RS-ConfigEMIMO-r13 OPTIONAL
   ]],
   [[
      dummy [13] EXPLICIT CSI-RS-ConfigEMIMO-v1430 OPTIONAL,
      eMIMO-Hybrid-r14 [14] EXPLICIT CSI-RS-ConfigEMIMO-Hybrid-r14 OPTIONAL,
      advancedCodebookEnabled-r14 [15] BOOLEAN OPTIONAL
   ]],
   [[
      eMIMO-Type-v1480 [16] EXPLICIT CSI-RS-ConfigEMIMO-v1480 OPTIONAL
   ]],
   [[
      feCOMP-CSI-Enabled-v1530 [17] BOOLEAN OPTIONAL,
      eMIMO-Type-v1530 [18] EXPLICIT CSI-RS-ConfigEMIMO-v1530 OPTIONAL
   ]]
}

CSI-ProcessToAddModList-r11 ::= SEQUENCE (SIZE (1..maxCSI-Proc-r11)) OF CSI-Process-r11

CQI-ReportBoth-r11 ::= SEQUENCE {
   csi-IM-ConfigToReleaseList-r11 [0] CSI-IM-ConfigToReleaseList-r11 OPTIONAL, -- Need ON
   csi-IM-ConfigToAddModList-r11 [1] CSI-IM-ConfigToAddModList-r11 OPTIONAL, -- Need ON
   csi-ProcessToReleaseList-r11 [2] CSI-ProcessToReleaseList-r11 OPTIONAL, -- Need ON
   csi-ProcessToAddModList-r11 [3] CSI-ProcessToAddModList-r11 OPTIONAL -- Need ON
}

CQI-ReportConfig-v1130 ::= SEQUENCE {
   cqi-ReportPeriodic-v1130 [0] CQI-ReportPeriodic-v1130,
   cqi-ReportBoth-r11 [1] CQI-ReportBoth-r11
}

PUCCH-ConfigDedicated-v1130 ::= SEQUENCE {
   n1PUCCH-AN-CS-v1130 [0] EXPLICIT CHOICE {
      release [0] NULL,
      setup [1] SEQUENCE {
         n1PUCCH-AN-CS-ListP1-r11 [0] SEQUENCE (SIZE (2..4)) OF INTEGER (0..2047)
      }
   } OPTIONAL, -- Need ON
   nPUCCH-Param-r11 [1] EXPLICIT CHOICE {
      release [0] NULL,
      setup [1] SEQUENCE {
         nPUCCH-Identity-r11 [0] INTEGER (0..503),
         n1PUCCH-AN-r11 [1] INTEGER (0..2047)
      }
   } OPTIONAL -- Need ON
}

PUSCH-ConfigDedicated-v1130 ::= SEQUENCE {
   pusch-DMRS-r11 [0] EXPLICIT CHOICE {
      release [0] NULL,
      setup [1] SEQUENCE {
         nPUSCH-Identity-r11 [0] INTEGER (0..509),
         nDMRS-CSH-Identity-r11 [1] INTEGER (0..509)
      }
   }
}

DeltaTxD-OffsetListPUCCH-v1130 ::= SEQUENCE {
   deltaTxD-OffsetPUCCH-Format1bCS-r11 [0] ENUMERATED { dB0(0), dB-1(1) }
}

UplinkPowerControlDedicated-v1130 ::= SEQUENCE {
   pSRS-Offset-v1130 [0] INTEGER (16..31) OPTIONAL, -- Need OR
   pSRS-OffsetAp-v1130 [1] INTEGER (16..31) OPTIONAL, -- Need OR
   deltaTxD-OffsetListPUCCH-v1130 [2] DeltaTxD-OffsetListPUCCH-v1130 OPTIONAL -- Need OR
}

AntennaInfoDedicated-v1250 ::= SEQUENCE {
   alternativeCodebookEnabledFor4TX-r12 [0] BOOLEAN
}

EIMTA-MainConfig-r12 ::= CHOICE {
   release [0] NULL,
   setup [1] SEQUENCE {
      eimta-RNTI-r12 [0] C-RNTI,
      eimta-CommandPeriodicity-r12 [1] ENUMERATED { sf10(0), sf20(1), sf40(2), 
         sf80(3) },
      eimta-CommandSubframeSet-r12 [2] BIT STRING  (SIZE (10))
   }
}

EIMTA-MainConfigServCell-r12 ::= CHOICE {
   release [0] NULL,
   setup [1] SEQUENCE {
      eimta-UL-DL-ConfigIndex-r12 [0] INTEGER (1..5),
      eimta-HARQ-ReferenceConfig-r12 [1] ENUMERATED { sa2(0), sa4(1), sa5(2) },
      mbsfn-SubframeConfigList-v1250 [2] EXPLICIT CHOICE {
         release [0] NULL,
         setup [1] SEQUENCE {
            subframeConfigList-r12 [0] MBSFN-SubframeConfigList
         }
      }
   }
}

PUCCH-ConfigDedicated-v1250 ::= SEQUENCE {
   nkaPUCCH-Param-r12 [0] EXPLICIT CHOICE {
      release [0] NULL,
      setup [1] SEQUENCE {
         nkaPUCCH-AN-r12 [0] INTEGER (0..2047)
      }
   }
}

CSI-IM-ConfigExt-r12 ::= SEQUENCE {
   csi-IM-ConfigId-v1250 [0] CSI-IM-ConfigId-v1250,
   resourceConfig-r12 [1] INTEGER (0..31),
   subframeConfig-r12 [2] INTEGER (0..154),
   ...,
   [[
      interferenceMeasRestriction-r13 [3] BOOLEAN OPTIONAL,
      csi-IM-ConfigId-v1310 [4] CSI-IM-ConfigId-v1310 OPTIONAL
   ]]
}

CQI-ReportBoth-v1250 ::= SEQUENCE {
   csi-IM-ConfigToReleaseListExt-r12 [0] CSI-IM-ConfigId-v1250 OPTIONAL, -- Need ON
   csi-IM-ConfigToAddModListExt-r12 [1] CSI-IM-ConfigExt-r12 OPTIONAL -- Need ON
}

CQI-ReportAperiodic-v1250 ::= CHOICE {
   release [0] NULL,
   setup [1] SEQUENCE {
      aperiodicCSI-Trigger-v1250 [0] SEQUENCE {
         trigger-SubframeSetIndicator-r12 [0] ENUMERATED { s1(0), s2(1) },
         trigger1-SubframeSetIndicator-r12 [1] BIT STRING  (SIZE (8)),
         trigger2-SubframeSetIndicator-r12 [2] BIT STRING  (SIZE (8))
      }
   }
}

CQI-ReportConfig-v1250 ::= SEQUENCE {
   csi-SubframePatternConfig-r12 [0] EXPLICIT CHOICE {
      release [0] NULL,
      setup [1] SEQUENCE {
         csi-MeasSubframeSets-r12 [0] BIT STRING  (SIZE (10))
      }
   } OPTIONAL, -- Need ON
   cqi-ReportBoth-v1250 [1] CQI-ReportBoth-v1250 OPTIONAL, -- Need ON
   cqi-ReportAperiodic-v1250 [2] EXPLICIT CQI-ReportAperiodic-v1250 OPTIONAL, -- Need ON
   altCQI-Table-r12 [3] ENUMERATED { allSubframes(0), csi-SubframeSet1(1), 
      csi-SubframeSet2(2), spare1(3) } OPTIONAL -- Need OP
}

UplinkPowerControlDedicated-v1250 ::= SEQUENCE {
   set2PowerControlParameter [0] EXPLICIT CHOICE {
      release [0] NULL,
      setup [1] SEQUENCE {
         tpc-SubframeSet-r12 [0] BIT STRING  (SIZE (10)),
         p0-NominalPUSCH-SubframeSet2-r12 [1] INTEGER (-126..24),
         alpha-SubframeSet2-r12 [2] Alpha-r12,
         p0-UE-PUSCH-SubframeSet2-r12 [3] INTEGER (-8..7)
      }
   }
}

PUSCH-ConfigDedicated-v1250 ::= SEQUENCE {
   uciOnPUSCH [0] EXPLICIT CHOICE {
      release [0] NULL,
      setup [1] SEQUENCE {
         betaOffset-ACK-Index-SubframeSet2-r12 [0] INTEGER (0..15),
         betaOffset-RI-Index-SubframeSet2-r12 [1] INTEGER (0..15),
         betaOffset-CQI-Index-SubframeSet2-r12 [2] INTEGER (0..15),
         betaOffsetMC-r12 [3] SEQUENCE {
            betaOffset-ACK-Index-MC-SubframeSet2-r12 [0] INTEGER (0..15),
            betaOffset-RI-Index-MC-SubframeSet2-r12 [1] INTEGER (0..15),
            betaOffset-CQI-Index-MC-SubframeSet2-r12 [2] INTEGER (0..15)
         } OPTIONAL -- Need OR
      }
   }
}

CSI-RS-Config-v1250 ::= SEQUENCE {
   zeroTxPowerCSI-RS2-r12 [0] EXPLICIT ZeroTxPowerCSI-RS-Conf-r12 OPTIONAL, -- Need ON
   ds-ZeroTxPowerCSI-RS-r12 [1] EXPLICIT CHOICE {
      release [0] NULL,
      setup [1] SEQUENCE {
         zeroTxPowerCSI-RS-List-r12 [0] SEQUENCE (SIZE (1..maxDS-ZTP-CSI-RS-r12)) OF 
            ZeroTxPowerCSI-RS-r12
      }
   } OPTIONAL -- Need ON
}

PDSCH-ConfigDedicated-v1280 ::= SEQUENCE {
   tbsIndexAlt-r12 [0] ENUMERATED { a26(0), a33(1) } OPTIONAL -- Need OR
}

DMRS-Config-v1310 ::= SEQUENCE {
   dmrs-tableAlt-r13 [0] ENUMERATED { true(0) } OPTIONAL -- Need OR
}

PDSCH-ConfigDedicated-v1310 ::= SEQUENCE {
   dmrs-ConfigPDSCH-v1310 [0] DMRS-Config-v1310 OPTIONAL -- Need ON
}

Format4-resource-r13 ::= SEQUENCE {
   startingPRB-format4-r13 [0] INTEGER (0..109),
   numberOfPRB-format4-r13 [1] INTEGER (0..7)
}

Format5-resource-r13 ::= SEQUENCE {
   startingPRB-format5-r13 [0] INTEGER (0..109),
   cdm-index-format5-r13 [1] INTEGER (0..1)
}

PUCCH-ConfigDedicated-r13 ::= SEQUENCE {
--Release 8
   ackNackRepetition-r13 [0] EXPLICIT CHOICE {
      release [0] NULL,
      setup [1] SEQUENCE {
         repetitionFactor-r13 [0] ENUMERATED { n2(0), n4(1), n6(2), spare1(3) }
            ,
         n1PUCCH-AN-Rep-r13 [1] INTEGER (0..2047)
      }
   },
   tdd-AckNackFeedbackMode-r13 [1] ENUMERATED { bundling(0), multiplexing(1) }
       OPTIONAL, -- Cond TDD
--Release 10
   pucch-Format-r13 [2] EXPLICIT CHOICE {
      format3-r13 [0] SEQUENCE {
         n3PUCCH-AN-List-r13 [0] SEQUENCE (SIZE (1..4)) OF INTEGER (0..549) OPTIONAL,
             -- Need ON
         twoAntennaPortActivatedPUCCH-Format3-r13 [1] EXPLICIT CHOICE {
            release [0] NULL,
            setup [1] SEQUENCE {
               n3PUCCH-AN-ListP1-r13 [0] SEQUENCE (SIZE (1..4)) OF INTEGER (0..549)
            }
         } OPTIONAL -- Need ON
      },
      channelSelection-r13 [1] SEQUENCE {
         n1PUCCH-AN-CS-r13 [0] EXPLICIT CHOICE {
            release [0] NULL,
            setup [1] SEQUENCE {
               n1PUCCH-AN-CS-List-r13 [0] SEQUENCE (SIZE (1..2)) OF 
                  N1PUCCH-AN-CS-r10,
               dummy1 [1] SEQUENCE (SIZE (2..4)) OF INTEGER (0..2047)
            }
         } OPTIONAL -- Need ON
      },
      format4-r13 [2] SEQUENCE {
         format4-resourceConfiguration-r13 [0] SEQUENCE (SIZE (4)) OF 
            Format4-resource-r13,
         format4-MultiCSI-resourceConfiguration-r13 [1] SEQUENCE (SIZE (1..2)
            ) OF Format4-resource-r13 OPTIONAL -- Need OR
      },
      format5-r13 [3] SEQUENCE {
         format5-resourceConfiguration-r13 [0] SEQUENCE (SIZE (4)) OF 
            Format5-resource-r13,
         format5-MultiCSI-resourceConfiguration-r13 [1] Format5-resource-r13
             OPTIONAL -- Need OR
      }
   } OPTIONAL, -- Need OR
   twoAntennaPortActivatedPUCCH-Format1a1b-r13 [3] ENUMERATED { true(0) }
       OPTIONAL, -- Need OR
   simultaneousPUCCH-PUSCH-r13 [4] ENUMERATED { true(0) } OPTIONAL, -- Need OR
   n1PUCCH-AN-RepP1-r13 [5] INTEGER (0..2047) OPTIONAL, -- Need OR
--Release 11
   nPUCCH-Param-r13 [6] EXPLICIT CHOICE {
      release [0] NULL,
      setup [1] SEQUENCE {
         nPUCCH-Identity-r13 [0] INTEGER (0..503),
         n1PUCCH-AN-r13 [1] INTEGER (0..2047)
      }
   } OPTIONAL, -- Need ON
--Release 12
   nkaPUCCH-Param-r13 [7] EXPLICIT CHOICE {
      release [0] NULL,
      setup [1] SEQUENCE {
         nkaPUCCH-AN-r13 [0] INTEGER (0..2047)
      }
   } OPTIONAL, -- Need ON
--Release 13
   spatialBundlingPUCCH-r13 [8] BOOLEAN,
   spatialBundlingPUSCH-r13 [9] BOOLEAN,
   harq-TimingTDD-r13 [10] BOOLEAN,
   codebooksizeDetermination-r13 [11] ENUMERATED { dai(0), cc(1) } OPTIONAL, -- Need OR
   maximumPayloadCoderate-r13 [12] INTEGER (0..7) OPTIONAL, -- Need OR
   pucch-NumRepetitionCE-r13 [13] EXPLICIT CHOICE {
      release [0] NULL,
      setup [1] EXPLICIT CHOICE {
         modeA [0] SEQUENCE {
            pucch-NumRepetitionCE-format1-r13 [0] ENUMERATED { r1(0), r2(1), 
               r4(2), r8(3) },
            pucch-NumRepetitionCE-format2-r13 [1] ENUMERATED { r1(0), r2(1), 
               r4(2), r8(3) }
         },
         modeB [1] SEQUENCE {
            pucch-NumRepetitionCE-format1-r13 [0] ENUMERATED { r4(0), r8(1), 
               r16(2), r32(3) },
            pucch-NumRepetitionCE-format2-r13 [1] ENUMERATED { r4(0), r8(1), 
               r16(2), r32(3) }
         }
      }
   } OPTIONAL --Need ON
}

PUSCH-ConfigDedicated-r13 ::= SEQUENCE {
   betaOffset-ACK-Index-r13 [0] INTEGER (0..15),
   betaOffset2-ACK-Index-r13 [1] INTEGER (0..15) OPTIONAL, -- Need OR
   betaOffset-RI-Index-r13 [2] INTEGER (0..15),
   betaOffset-CQI-Index-r13 [3] INTEGER (0..15),
   betaOffsetMC-r13 [4] SEQUENCE {
      betaOffset-ACK-Index-MC-r13 [0] INTEGER (0..15),
      betaOffset2-ACK-Index-MC-r13 [1] INTEGER (0..15) OPTIONAL, -- Need OR
      betaOffset-RI-Index-MC-r13 [2] INTEGER (0..15),
      betaOffset-CQI-Index-MC-r13 [3] INTEGER (0..15)
   } OPTIONAL, -- Need OR
   groupHoppingDisabled-r13 [5] ENUMERATED { true(0) } OPTIONAL, -- Need OR
   dmrs-WithOCC-Activated-r13 [6] ENUMERATED { true(0) } OPTIONAL, -- Need OR
   pusch-DMRS-r11 [7] EXPLICIT CHOICE {
      release [0] NULL,
      setup [1] SEQUENCE {
         nPUSCH-Identity-r13 [0] INTEGER (0..509),
         nDMRS-CSH-Identity-r13 [1] INTEGER (0..509)
      }
   } OPTIONAL, -- Need ON
   uciOnPUSCH [8] EXPLICIT CHOICE {
      release [0] NULL,
      setup [1] SEQUENCE {
         betaOffset-ACK-Index-SubframeSet2-r13 [0] INTEGER (0..15),
         betaOffset2-ACK-Index-SubframeSet2-r13 [1] INTEGER (0..15) OPTIONAL, -- Need OR
         betaOffset-RI-Index-SubframeSet2-r13 [2] INTEGER (0..15),
         betaOffset-CQI-Index-SubframeSet2-r13 [3] INTEGER (0..15),
         betaOffsetMC-r12 [4] SEQUENCE {
            betaOffset-ACK-Index-MC-SubframeSet2-r13 [0] INTEGER (0..15),
            betaOffset2-ACK-Index-MC-SubframeSet2-r13 [1] INTEGER (0..15) OPTIONAL
               , -- Need OR
            betaOffset-RI-Index-MC-SubframeSet2-r13 [2] INTEGER (0..15),
            betaOffset-CQI-Index-MC-SubframeSet2-r13 [3] INTEGER (0..15)
         } OPTIONAL -- Need OR
      }
   } OPTIONAL, -- Need ON
   pusch-HoppingConfig-r13 [9] ENUMERATED { on(0) } OPTIONAL -- Need OR
}

PDCCH-CandidateReductions-r13 ::= CHOICE {
   release [0] NULL,
   setup [1] SEQUENCE {
      pdcch-candidateReductionAL1-r13 [0] PDCCH-CandidateReductionValue-r13,
      pdcch-candidateReductionAL2-r13 [1] PDCCH-CandidateReductionValue-r13,
      pdcch-candidateReductionAL3-r13 [2] PDCCH-CandidateReductionValue-r13,
      pdcch-candidateReductionAL4-r13 [3] PDCCH-CandidateReductionValue-r13,
      pdcch-candidateReductionAL5-r13 [4] PDCCH-CandidateReductionValue-r13
   }
}

CSI-IM-ConfigToReleaseListExt-r13 ::= SEQUENCE (SIZE (1..maxCSI-IM-v1310)) OF 
   CSI-IM-ConfigId-v1310

CSI-IM-ConfigToAddModListExt-r13 ::= SEQUENCE (SIZE (1..maxCSI-IM-v1310)) OF 
   CSI-IM-ConfigExt-r12

CQI-ReportBoth-v1310 ::= SEQUENCE {
   csi-IM-ConfigToReleaseListExt-r13 [0] CSI-IM-ConfigToReleaseListExt-r13
       OPTIONAL, -- Need ON
   csi-IM-ConfigToAddModListExt-r13 [1] CSI-IM-ConfigToAddModListExt-r13
       OPTIONAL -- Need ON
}

CQI-ReportAperiodic-v1310 ::= CHOICE {
   release [0] NULL,
   setup [1] SEQUENCE {
      aperiodicCSI-Trigger-v1310 [0] SEQUENCE {
         trigger1-r13 [0] BIT STRING  (SIZE (32)),
         trigger2-r13 [1] BIT STRING  (SIZE (32)),
         trigger3-r13 [2] BIT STRING  (SIZE (32)),
         trigger4-r13 [3] BIT STRING  (SIZE (32)),
         trigger5-r13 [4] BIT STRING  (SIZE (32)),
         trigger6-r13 [5] BIT STRING  (SIZE (32))
      } OPTIONAL, -- Need ON
      aperiodicCSI-Trigger2-r13 [1] EXPLICIT CHOICE {
         release [0] NULL,
         setup [1] SEQUENCE {
            trigger1-SubframeSetIndicator-r13 [0] BIT STRING  (SIZE (32)),
            trigger2-SubframeSetIndicator-r13 [1] BIT STRING  (SIZE (32)),
            trigger3-SubframeSetIndicator-r13 [2] BIT STRING  (SIZE (32)),
            trigger4-SubframeSetIndicator-r13 [3] BIT STRING  (SIZE (32)),
            trigger5-SubframeSetIndicator-r13 [4] BIT STRING  (SIZE (32)),
            trigger6-SubframeSetIndicator-r13 [5] BIT STRING  (SIZE (32))
         }
      } OPTIONAL -- Need ON
   }
}

CQI-ReportPeriodic-v1310 ::= SEQUENCE {
   cri-ReportConfig-r13 [0] EXPLICIT CRI-ReportConfig-r13 OPTIONAL, -- Need OR
   simultaneousAckNackAndCQI-Format4-Format5-r13 [1] ENUMERATED { setup(0) }
       OPTIONAL -- Need OR
}

CQI-ReportConfig-v1310 ::= SEQUENCE {
   cqi-ReportBoth-v1310 [0] CQI-ReportBoth-v1310 OPTIONAL, -- Need ON
   cqi-ReportAperiodic-v1310 [1] EXPLICIT CQI-ReportAperiodic-v1310 OPTIONAL, -- Need ON
   cqi-ReportPeriodic-v1310 [2] CQI-ReportPeriodic-v1310 OPTIONAL -- Need ON
}

SoundingRS-UL-ConfigDedicated-v1310 ::= CHOICE {
   release [0] NULL,
   setup [1] SEQUENCE {
      transmissionComb-v1310 [0] INTEGER (2..3) OPTIONAL, -- Need OR
      cyclicShift-v1310 [1] ENUMERATED { cs8(0), cs9(1), cs10(2), cs11(3) }
          OPTIONAL, -- Need OR
      transmissionCombNum-r13 [2] ENUMERATED { n2(0), n4(1) } OPTIONAL -- Need OR
   }
}

SoundingRS-UL-ConfigDedicatedUpPTsExt-r13 ::= CHOICE {
   release [0] NULL,
   setup [1] SEQUENCE {
      srs-UpPtsAdd-r13 [0] ENUMERATED { sym2(0), sym4(1) },
      srs-Bandwidth-r13 [1] ENUMERATED { bw0(0), bw1(1), bw2(2), bw3(3) },
      srs-HoppingBandwidth-r13 [2] ENUMERATED { hbw0(0), hbw1(1), hbw2(2), 
         hbw3(3) },
      freqDomainPosition-r13 [3] INTEGER (0..23),
      duration-r13 [4] BOOLEAN,
      srs-ConfigIndex-r13 [5] INTEGER (0..1023),
      transmissionComb-r13 [6] INTEGER (0..3),
      cyclicShift-r13 [7] ENUMERATED { cs0(0), cs1(1), cs2(2), cs3(3), cs4(4), 
         cs5(5), cs6(6), cs7(7), cs8(8), cs9(9), cs10(10), cs11(11) },
      srs-AntennaPort-r13 [8] SRS-AntennaPort,
      transmissionCombNum-r13 [9] ENUMERATED { n2(0), n4(1) }
   }
}

SRS-ConfigAp-v1310 ::= SEQUENCE {
   transmissionCombAp-v1310 [0] INTEGER (2..3) OPTIONAL, -- Need OR
   cyclicShiftAp-v1310 [1] ENUMERATED { cs8(0), cs9(1), cs10(2), cs11(3) }
       OPTIONAL, -- Need OR
   transmissionCombNum-r13 [2] ENUMERATED { n2(0), n4(1) } OPTIONAL -- Need OR
}

SoundingRS-UL-ConfigDedicatedAperiodic-v1310 ::= CHOICE {
   release [0] NULL,
   setup [1] SEQUENCE {
      srs-ConfigApDCI-Format4-v1310 [0] SEQUENCE (SIZE (1..3)) OF 
         SRS-ConfigAp-v1310 OPTIONAL, --Need ON
      srs-ActivateAp-v1310 [1] EXPLICIT CHOICE {
         release [0] NULL,
         setup [1] SEQUENCE {
            srs-ConfigApDCI-Format0-v1310 [0] SRS-ConfigAp-v1310 OPTIONAL, -- Need ON
            srs-ConfigApDCI-Format1a2b2c-v1310 [1] SRS-ConfigAp-v1310 OPTIONAL -- Need ON
         }
      } OPTIONAL -- Need ON
   }
}

SRS-ConfigAp-r13 ::= SEQUENCE {
   srs-AntennaPortAp-r13 [0] SRS-AntennaPort,
   srs-BandwidthAp-r13 [1] ENUMERATED { bw0(0), bw1(1), bw2(2), bw3(3) },
   freqDomainPositionAp-r13 [2] INTEGER (0..23),
   transmissionCombAp-r13 [3] INTEGER (0..3),
   cyclicShiftAp-r13 [4] ENUMERATED { cs0(0), cs1(1), cs2(2), cs3(3), cs4(4), 
      cs5(5), cs6(6), cs7(7), cs8(8), cs9(9), cs10(10), cs11(11) },
   transmissionCombNum-r13 [5] ENUMERATED { n2(0), n4(1) }
}

SoundingRS-UL-ConfigDedicatedAperiodicUpPTsExt-r13 ::= CHOICE {
   release [0] NULL,
   setup [1] SEQUENCE {
      srs-UpPtsAdd-r13 [0] ENUMERATED { sym2(0), sym4(1) },
      srs-ConfigIndexAp-r13 [1] INTEGER (0..31),
      srs-ConfigApDCI-Format4-r13 [2] SEQUENCE (SIZE (1..3)) OF SRS-ConfigAp-r13
          OPTIONAL, --Need ON
      srs-ActivateAp-r13 [3] EXPLICIT CHOICE {
         release [0] NULL,
         setup [1] SEQUENCE {
            srs-ConfigApDCI-Format0-r13 [0] SRS-ConfigAp-r13,
            srs-ConfigApDCI-Format1a2b2c-r13 [1] SRS-ConfigAp-r13
         }
      } OPTIONAL -- Need ON
   }
}

CSI-RS-Config-v1310 ::= SEQUENCE {
   eMIMO-Type-r13 [0] EXPLICIT CSI-RS-ConfigEMIMO-r13 OPTIONAL -- Need ON
}

CSI-RS-ConfigNZPToAddModListExt-r13 ::= SEQUENCE (SIZE (1..maxCSI-RS-NZP-v1310)) OF 
   CSI-RS-ConfigNZP-r11

CSI-RS-ConfigNZPToReleaseListExt-r13 ::= SEQUENCE (SIZE (1..maxCSI-RS-NZP-v1310)) OF 
   CSI-RS-ConfigNZPId-v1310

CQI-ReportPeriodic-v1320 ::= SEQUENCE {
   periodicityFactorWB-r13 [0] ENUMERATED { n2(0), n4(1) } OPTIONAL -- Need OR
}

CQI-ReportConfig-v1320 ::= SEQUENCE {
   cqi-ReportPeriodic-v1320 [0] CQI-ReportPeriodic-v1320 OPTIONAL -- Need ON
}

SRS-CC-SetIndex-r14 ::= SEQUENCE {
   cc-SetIndex-r14 [0] INTEGER (0..3),
   cc-IndexInOneCC-Set-r14 [1] INTEGER (0..7)
}

SRS-TPC-PDCCH-Config-r14 ::= CHOICE {
   release [0] NULL,
   setup [1] SEQUENCE {
      srs-TPC-RNTI-r14 [0] BIT STRING  (SIZE (16)),
      startingBitOfFormat3B-r14 [1] INTEGER (0..31),
      fieldTypeFormat3B-r14 [2] INTEGER (1..4),
      srs-CC-SetIndexlist-r14 [3] SEQUENCE (SIZE (1..4)) OF SRS-CC-SetIndex-r14
          OPTIONAL -- Cond SRS-Trigger-TypeA
   }
}

PUSCH-EnhancementsConfig-r14 ::= CHOICE {
   release [0] NULL,
   setup [1] SEQUENCE {
      pusch-HoppingOffsetPUSCH-Enh-r14 [0] INTEGER (1..100) OPTIONAL, -- Need ON
      interval-ULHoppingPUSCH-Enh-r14 [1] EXPLICIT CHOICE {
         interval-FDD-PUSCH-Enh-r14 [0] ENUMERATED { int1(0), int2(1), int4(2)
            , int8(3) },
         interval-TDD-PUSCH-Enh-r14 [1] ENUMERATED { int1(0), int5(1), int10(2)
            , int20(3) }
      } OPTIONAL -- Need ON
   }
}

AntennaInfoDedicated-v1430 ::= SEQUENCE {
   ce-UE-TxAntennaSelection-config-r14 [0] ENUMERATED { on(0) } OPTIONAL -- Need OR
}

PUCCH-ConfigDedicated-v1430 ::= SEQUENCE {
   pucch-NumRepetitionCE-format1-r14 [0] ENUMERATED { r64(0), r128(1) }
       OPTIONAL -- Need OR
}

PDSCH-ConfigDedicated-v1430 ::= SEQUENCE {
   ce-PDSCH-MaxBandwidth-r14 [0] ENUMERATED { bw5(0), bw20(1) } OPTIONAL, -- Need OP
   ce-PDSCH-TenProcesses-r14 [1] ENUMERATED { on(0) } OPTIONAL, -- Need OR
   ce-HARQ-AckBundling-r14 [2] ENUMERATED { on(0) } OPTIONAL, -- Need OR
   ce-SchedulingEnhancement-r14 [3] ENUMERATED { range1(0), range2(1) }
       OPTIONAL, -- Need OR
   tbsIndexAlt2-r14 [4] ENUMERATED { b33(0) } OPTIONAL -- Need OR
}

TDD-PUSCH-UpPTS-r14 ::= CHOICE {
   release [0] NULL,
   setup [1] SEQUENCE {
      symPUSCH-UpPTS-r14 [0] ENUMERATED { sym1(0), sym2(1), sym3(2), sym4(3), 
         sym5(4), sym6(5) } OPTIONAL, -- Need ON
      dmrs-LessUpPTS-Config-r14 [1] ENUMERATED { true(0) } OPTIONAL -- Need OR
   }
}

Enable256QAM-r14 ::= CHOICE {
   release [0] NULL,
   setup [1] EXPLICIT CHOICE {
      tpc-SubframeSet-Configured-r14 [0] SEQUENCE {
         subframeSet1-DCI-Format0-r14 [0] BOOLEAN,
         subframeSet1-DCI-Format4-r14 [1] BOOLEAN,
         subframeSet2-DCI-Format0-r14 [2] BOOLEAN,
         subframeSet2-DCI-Format4-r14 [3] BOOLEAN
      },
      tpc-SubframeSet-NotConfigured-r14 [1] SEQUENCE {
         dci-Format0-r14 [0] BOOLEAN,
         dci-Format4-r14 [1] BOOLEAN
      }
   }
}

PUSCH-ConfigDedicated-v1430 ::= SEQUENCE {
   ce-PUSCH-NB-MaxTBS-r14 [0] ENUMERATED { on(0) } OPTIONAL, -- Need OR
   ce-PUSCH-MaxBandwidth-r14 [1] ENUMERATED { bw5(0) } OPTIONAL, -- Need OR
   tdd-PUSCH-UpPTS-r14 [2] EXPLICIT TDD-PUSCH-UpPTS-r14 OPTIONAL, -- Need ON
   ul-DMRS-IFDMA-r14 [3] BOOLEAN,
   enable256QAM-r14 [4] EXPLICIT Enable256QAM-r14 OPTIONAL -- Need ON
}

CSI-RS-Config-v1430 ::= SEQUENCE {
   dummy [0] EXPLICIT CSI-RS-ConfigEMIMO-v1430 OPTIONAL, -- Need ON
   eMIMO-Hybrid-r14 [1] EXPLICIT CSI-RS-ConfigEMIMO-Hybrid-r14 OPTIONAL, -- Need ON
   advancedCodebookEnabled-r14 [2] BOOLEAN OPTIONAL -- Need ON
}

CSI-RS-ConfigZP-ApList-r14 ::= CHOICE {
   release [0] NULL,
   setup [1] SEQUENCE (SIZE (1..maxCSI-RS-ZP-r11)) OF CSI-RS-ConfigZP-r11
}

CQI-ReportAperiodicHybrid-r14 ::= SEQUENCE {
   triggers-r14 [0] EXPLICIT CHOICE {
      oneBit-r14 [0] SEQUENCE {
         trigger1-Indicator-r14 [0] BIT STRING  (SIZE (8))
      },
      twoBit-r14 [1] SEQUENCE {
         trigger01-Indicator-r14 [0] BIT STRING  (SIZE (8)),
         trigger10-Indicator-r14 [1] BIT STRING  (SIZE (8)),
         trigger11-Indicator-r14 [2] BIT STRING  (SIZE (8))
      },
      threeBit-r14 [2] SEQUENCE {
         trigger001-Indicator-r14 [0] BIT STRING  (SIZE (32)),
         trigger010-Indicator-r14 [1] BIT STRING  (SIZE (32)),
         trigger011-Indicator-r14 [2] BIT STRING  (SIZE (32)),
         trigger100-Indicator-r14 [3] BIT STRING  (SIZE (32)),
         trigger101-Indicator-r14 [4] BIT STRING  (SIZE (32)),
         trigger110-Indicator-r14 [5] BIT STRING  (SIZE (32)),
         trigger111-Indicator-r14 [6] BIT STRING  (SIZE (32))
      }
   } OPTIONAL -- Need OR
}

CQI-ReportConfig-v1430 ::= SEQUENCE {
   cqi-ReportAperiodicHybrid-r14 [0] CQI-ReportAperiodicHybrid-r14 OPTIONAL -- Need ON
}

CSI-RS-Config-v1480 ::= SEQUENCE {
   eMIMO-Type-v1480 [0] EXPLICIT CSI-RS-ConfigEMIMO-v1480 OPTIONAL -- Need ON
}

AntennaInfoDedicatedSTTI-r15 ::= CHOICE {
   release [0] NULL,
   setup [1] SEQUENCE {
      transmissionModeDL-MBSFN-r15 [0] ENUMERATED { tm9(0), tm10(1) } OPTIONAL,
          -- Need OR
      transmissionModeDL-nonMBSFN-r15 [1] ENUMERATED { tm1(0), tm2(1), tm3(2), 
         tm4(3), tm6(4), tm8(5), tm9(6), tm10(7) } OPTIONAL, --_Need OR
      codebookSubsetRestriction [2] EXPLICIT CHOICE {
         n2TxAntenna-tm3-r15 [0] BIT STRING  (SIZE (2)),
         n4TxAntenna-tm3-r15 [1] BIT STRING  (SIZE (4)),
         n2TxAntenna-tm4-r15 [2] BIT STRING  (SIZE (6)),
         n4TxAntenna-tm4-r15 [3] BIT STRING  (SIZE (64)),
         n2TxAntenna-tm5-r15 [4] BIT STRING  (SIZE (4)),
         n4TxAntenna-tm5-r15 [5] BIT STRING  (SIZE (16)),
         n2TxAntenna-tm6-r15 [6] BIT STRING  (SIZE (4)),
         n4TxAntenna-tm6-r15 [7] BIT STRING  (SIZE (16)),
         n2TxAntenna-tm8-r15 [8] BIT STRING  (SIZE (6)),
         n4TxAntenna-tm8-r15 [9] BIT STRING  (SIZE (64)),
         n2TxAntenna-tm9and10-r15 [10] BIT STRING  (SIZE (6)),
         n4TxAntenna-tm9and10-r15 [11] BIT STRING  (SIZE (96)),
         n8TxAntenna-tm9and10-r15 [12] BIT STRING  (SIZE (109))
      } OPTIONAL, -- Cond TM
      maxLayersMIMO-STTI-r15 [3] ENUMERATED { twoLayers(0), fourLayers(1) }
          OPTIONAL, -- Need OR
      slotSubslotPDSCH-TxDiv-2Layer-r15 [4] BOOLEAN,
      slotSubslotPDSCH-TxDiv-4Layer-r15 [5] BOOLEAN
   }
}

AntennaInfoUL-STTI-r15 ::= SEQUENCE {
   transmissionModeUL-STTI-r15 [0] ENUMERATED { tm1(0), tm2(1) } OPTIONAL -- Need OR
}

PUCCH-ConfigDedicated-v1530 ::= SEQUENCE {
   n1PUCCH-AN-SPT-r15 [0] INTEGER (0..2047) OPTIONAL, -- Need OR
   codebooksizeDeterminationSTTI-r15 [1] ENUMERATED { dai(0), cc(1) } OPTIONAL -- Need OR
}

SR-SubslotSPUCCH-ResourceList-r15 ::= SEQUENCE (SIZE (1..4)) OF INTEGER (0..1319)

SchedulingRequestConfig-v1530 ::= CHOICE {
   release [0] NULL,
   setup [1] SEQUENCE {
      sr-SlotSPUCCH-IndexFH-r15 [0] INTEGER (0..1319) OPTIONAL, -- Need OR
      sr-SlotSPUCCH-IndexNoFH-r15 [1] INTEGER (0..3959) OPTIONAL, -- Need OR
      sr-SubslotSPUCCH-ResourceList-r15 [2] SR-SubslotSPUCCH-ResourceList-r15
          OPTIONAL, -- Need OR
      sr-ConfigIndexSlot-r15 [3] INTEGER (0..36) OPTIONAL, -- Need OR
      sr-ConfigIndexSubslot-r15 [4] INTEGER (0..122) OPTIONAL, -- Need OR
      dssr-TransMax-r15 [5] ENUMERATED { n4(0), n8(1), n16(2), n32(3), n64(4), 
         spare3(5), spare2(6), spare1(7) }
   }
}

DeltaTxD-OffsetListSPUCCH-r15 ::= SEQUENCE {
   deltaTxD-OffsetSPUCCH-Format1-r15 [0] ENUMERATED { dB0(0), dB-2(1) },
   deltaTxD-OffsetSPUCCH-Format1a-r15 [1] ENUMERATED { dB0(0), dB-2(1) },
   deltaTxD-OffsetSPUCCH-Format1b-r15 [2] ENUMERATED { dB0(0), dB-2(1) },
   deltaTxD-OffsetSPUCCH-Format3-r15 [3] ENUMERATED { dB0(0), dB-2(1) },
   ...
}

UplinkPowerControlDedicatedSTTI-r15 ::= SEQUENCE {
   accumulationEnabledSTTI-r15 [0] BOOLEAN,
   deltaTxD-OffsetListSPUCCH-r15 [1] DeltaTxD-OffsetListSPUCCH-r15 OPTIONAL, -- Need OR
   uplinkPower-CSIPayload [2] BOOLEAN
}

CQI-ReportConfig-r15 ::= CHOICE {
   release [0] NULL,
   setup [1] SEQUENCE {
      cqi-ReportConfig-r10 [0] CQI-ReportConfig-r10 OPTIONAL, -- Need ON
      cqi-ReportConfig-v1130 [1] CQI-ReportConfig-v1130 OPTIONAL, -- Need ON
      cqi-ReportConfigPCell-v1250 [2] CQI-ReportConfig-v1250 OPTIONAL, -- Need ON
      cqi-ReportConfig-v1310 [3] CQI-ReportConfig-v1310 OPTIONAL, -- Need ON
      cqi-ReportConfig-v1320 [4] CQI-ReportConfig-v1320 OPTIONAL, -- Need ON
      cqi-ReportConfig-v1430 [5] CQI-ReportConfig-v1430 OPTIONAL, -- Need ON
      altCQI-Table-1024QAM-r15 [6] ENUMERATED { allSubframes(0), 
         csi-SubframeSet1(1), csi-SubframeSet2(2), spare1(3) } OPTIONAL -- Need OP
   }
}

CSI-RS-Config-r15 ::= CHOICE {
   release [0] NULL,
   setup [1] SEQUENCE {
      csi-RS-Config-r10 [0] CSI-RS-Config-r10 OPTIONAL, -- Need ON
      csi-RS-Config-v1250 [1] CSI-RS-Config-v1250 OPTIONAL, -- Need ON
      csi-RS-Config-v1310 [2] CSI-RS-Config-v1310 OPTIONAL, -- Need ON
      csi-RS-Config-v1430 [3] CSI-RS-Config-v1430 OPTIONAL -- Need ON
   }
}

CSI-RS-ConfigNZPToReleaseList-r15 ::= SEQUENCE (SIZE (1..maxCSI-RS-NZP-r13)) OF 
   CSI-RS-ConfigNZPId-r13

CSI-RS-ConfigNZPToAddModList-r15 ::= SEQUENCE (SIZE (1..maxCSI-RS-NZP-r13)) OF 
   CSI-RS-ConfigNZP-r11

SlotOrSubslotPDSCH-Config-r15 ::= CHOICE {
   release [0] NULL,
   setup [1] SEQUENCE {
      altCQI-TableSTTI-r15 [0] ENUMERATED { allSubframes(0), 
         csi-SubframeSet1(1), csi-SubframeSet2(2), spare1(3) } OPTIONAL, -- Need OR
      altCQI-Table1024QAM-STTI-r15 [1] ENUMERATED { allSubframes(0), 
         csi-SubframeSet1(1), csi-SubframeSet2(2), spare1(3) } OPTIONAL, -- Need OR
      resourceAllocation-r15 [2] ENUMERATED { resourceAllocationType0(0), 
         resourceAllocationType2(1) } OPTIONAL, -- Need OR
      tbsIndexAlt-STTI-r15 [3] ENUMERATED { a33(0) } OPTIONAL, -- Need OR
      tbsIndexAlt2-STTI-r15 [4] ENUMERATED { b33(0) } OPTIONAL, -- Need OR
      tbsIndexAlt3-STTI-r15 [5] ENUMERATED { a37(0) } OPTIONAL,
      ...
   }
}

SlotOrSubslotPUSCH-Config-r15 ::= CHOICE {
   release [0] NULL,
   setup [1] SEQUENCE {
      betaOffsetSlot-ACK-Index-r15 [0] INTEGER (0..15) OPTIONAL, -- Need OR
      betaOffset2Slot-ACK-Index-r15 [1] INTEGER (0..15) OPTIONAL, -- Need OR
      betaOffsetSubslot-ACK-Index-r15 [2] SEQUENCE (SIZE (1..2)) OF INTEGER (0..15)
          OPTIONAL, -- Need OR
      betaOffset2Subslot-ACK-Index-r15 [3] SEQUENCE (SIZE (1..2)) OF INTEGER (0..15)
          OPTIONAL, -- Need OR
      betaOffsetSlot-RI-Index-r15 [4] INTEGER (0..15) OPTIONAL, -- Need OR
      betaOffsetSubslot-RI-Index-r15 [5] SEQUENCE (SIZE (1..2)) OF INTEGER (0..15)
          OPTIONAL, -- Need OR
      betaOffsetSlot-CQI-Index-r15 [6] INTEGER (0..15) OPTIONAL, -- Need OR
      betaOffsetSubslot-CQI-Index-r15 [7] INTEGER (0..15) OPTIONAL, -- Need OR
      enable256QAM-SlotOrSubslot-r15 [8] EXPLICIT Enable256QAM-r14 OPTIONAL, -- Need ON
      resourceAllocationOffset-r15 [9] INTEGER (1..2) OPTIONAL, -- Need OR
      ul-DMRS-IFDMA-SlotOrSubslot-r15 [10] BOOLEAN,
      ...
   }
}

DCI7-CandidatesPerAL-SPDCCH-r15 ::= SEQUENCE (SIZE (1..4)) OF DCI7-Candidates-r15
   

SPDCCH-Elements-r15 ::= CHOICE {
   release [0] NULL,
   setup [1] SEQUENCE {
      spdcch-SetConfigId-r15 [0] INTEGER (0..3) OPTIONAL, -- Need OR
      spdcch-SetReferenceSig-r15 [1] ENUMERATED { crs(0), dmrs(1) } OPTIONAL, -- Need OR
      transmissionType-r15 [2] ENUMERATED { localised(0), distributed(1) }
          OPTIONAL, -- Need OR
      spdcch-NoOfSymbols-r15 [3] INTEGER (1..2) OPTIONAL, -- Need OR
      dmrs-ScramblingSequenceInt-r15 [4] INTEGER (0..503) OPTIONAL, -- Need OR
      dci7-CandidatesPerAL-PDCCH-r15 [5] SEQUENCE (SIZE (1..4)) OF 
         DCI7-Candidates-r15 OPTIONAL, -- Need OR
      dci7-CandidateSetsPerAL-SPDCCH-r15 [6] SEQUENCE (SIZE (1..2)) OF 
         DCI7-CandidatesPerAL-SPDCCH-r15 OPTIONAL, -- Need OR
      resourceBlockAssignment-r15 [7] SEQUENCE {
         numberRB-InFreq-domain-r15 [0] INTEGER (2..100),
         resourceBlockAssignment-r15 [1] BIT STRING  (SIZE (98))
      } OPTIONAL, -- Need OR
      subslotApplicability-r15 [8] BIT STRING  (SIZE (5)) OPTIONAL, -- Need OR
      al-StartingPointSPDCCH-r15 [9] SEQUENCE (SIZE (1..4)) OF INTEGER (0..49)
          OPTIONAL, -- Need OR
      subframeType-r15 [10] ENUMERATED { mbsfn(0), nonmbsfn(1), all(2) }
          OPTIONAL, -- Need OR
      rateMatchingMode-r15 [11] ENUMERATED { m1(0), m2(1), m3(2), m4(3) }
          OPTIONAL,
      ...
   }
}

SPDCCH-Set-r15 ::= SEQUENCE (SIZE (1..4)) OF SPDCCH-Elements-r15

SPDCCH-Config-r15 ::= CHOICE {
   release [0] NULL,
   setup [1] SEQUENCE {
      spdcch-L1-ReuseIndication-r15 [0] ENUMERATED { n0(0), n1(1), n2(2) }
          OPTIONAL, -- Need OR
      spdcch-SetConfig-r15 [1] SPDCCH-Set-r15 OPTIONAL -- Need OR
   }
}

N4SPUCCH-Resource-r15 ::= SEQUENCE {
   n4startingPRB-r15 [0] INTEGER (0..109),
   n4numberOfPRB-r15 [1] INTEGER (0..7)
}

SPUCCH-Elements-r15 ::= CHOICE {
   release [0] NULL,
   setup [1] SEQUENCE {
      n1SubslotSPUCCH-AN-List-r15 [0] SEQUENCE (SIZE (1..4)) OF INTEGER (0..1319)
          OPTIONAL, -- Need OR
      n1SlotSPUCCH-FH-AN-List-r15 [1] INTEGER (0..1319) OPTIONAL, -- Need OR
      n1SlotSPUCCH-NoFH-AN-List-r15 [2] INTEGER (0..3959) OPTIONAL, -- Need OR
      n3SPUCCH-AN-List-r15 [3] INTEGER (0..549) OPTIONAL, -- Need OR
      n4SPUCCHSlot-Resource-r15 [4] SEQUENCE (SIZE (1..2)) OF 
         N4SPUCCH-Resource-r15 OPTIONAL, -- Need OR
      n4SPUCCHSubslot-Resource-r15 [5] SEQUENCE (SIZE (1..2)) OF 
         N4SPUCCH-Resource-r15 OPTIONAL, -- Need OR
      n4maxCoderateSlotPUCCH-r15 [6] INTEGER (0..7) OPTIONAL, -- Need OR
      n4maxCoderateSubslotPUCCH-r15 [7] INTEGER (0..7) OPTIONAL, -- Need OR
      n4maxCoderateMultiResourceSlotPUCCH-r15 [8] INTEGER (0..7) OPTIONAL, -- Need OR
      n4maxCoderateMultiResourceSubslotPUCCH-r15 [9] INTEGER (0..7) OPTIONAL -- Need OR
   }
}

SPUCCH-Set-r15 ::= SEQUENCE (SIZE (1..4)) OF SPUCCH-Elements-r15

SPUCCH-Config-r15 ::= CHOICE {
   release [0] NULL,
   setup [1] SEQUENCE {
      spucch-Set-r15 [0] SPUCCH-Set-r15 OPTIONAL, -- Need ON
      twoAntennaPortActivatedSPUCCH-Format1a1b-r15 [1] ENUMERATED { true(0) }
          OPTIONAL, -- Need OR
      dummy [2] SEQUENCE {
         n3SPUCCH-AN-List-r15 [0] SEQUENCE (SIZE (1..4)) OF INTEGER (0..549)
      }
   }
}

ShortTTI-r15 ::= SEQUENCE {
   dl-STTI-Length-r15 [0] ShortTTI-Length-r15 OPTIONAL, -- Need OR
   ul-STTI-Length-r15 [1] ShortTTI-Length-r15 OPTIONAL -- Need OR
}

PhysicalConfigDedicatedSTTI-r15 ::= CHOICE {
   release [0] NULL,
   setup [1] SEQUENCE {
      antennaInfoDedicatedSTTI-r15 [0] EXPLICIT AntennaInfoDedicatedSTTI-r15
          OPTIONAL, -- Need ON
      antennaInfoUL-STTI-r15 [1] AntennaInfoUL-STTI-r15 OPTIONAL, -- Need ON
      pucch-ConfigDedicated-v1530 [2] PUCCH-ConfigDedicated-v1530 OPTIONAL, -- Need ON
      schedulingRequestConfig-v1530 [3] EXPLICIT SchedulingRequestConfig-v1530
          OPTIONAL, -- Need ON
      uplinkPowerControlDedicatedSTTI-r15 [4] 
         UplinkPowerControlDedicatedSTTI-r15 OPTIONAL, --Need ON
      cqi-ReportConfig-r15 [5] EXPLICIT CQI-ReportConfig-r15 OPTIONAL, -- Need ON
      csi-RS-Config-r15 [6] EXPLICIT CSI-RS-Config-r15 OPTIONAL, -- Need ON
      csi-RS-ConfigNZPToReleaseList-r15 [7] CSI-RS-ConfigNZPToReleaseList-r15
          OPTIONAL, -- Need ON
      csi-RS-ConfigNZPToAddModList-r15 [8] CSI-RS-ConfigNZPToAddModList-r15
          OPTIONAL, -- Need ON
      csi-RS-ConfigZPToReleaseList-r15 [9] CSI-RS-ConfigZPToReleaseList-r11
          OPTIONAL, -- Need ON
      csi-RS-ConfigZPToAddModList-r11 [10] CSI-RS-ConfigZPToAddModList-r11
          OPTIONAL, -- Need ON
      csi-RS-ConfigZP-ApList-r15 [11] EXPLICIT CSI-RS-ConfigZP-ApList-r14
          OPTIONAL, -- Need ON
      eimta-MainConfig-r12 [12] EXPLICIT EIMTA-MainConfig-r12 OPTIONAL, -- Need ON
      eimta-MainConfigServCell-r15 [13] EXPLICIT EIMTA-MainConfigServCell-r12
          OPTIONAL, -- Need ON
      semiOpenLoopSTTI-r15 [14] BOOLEAN,
      slotOrSubslotPDSCH-Config-r15 [15] EXPLICIT SlotOrSubslotPDSCH-Config-r15
          OPTIONAL, -- Need ON
      slotOrSubslotPUSCH-Config-r15 [16] EXPLICIT SlotOrSubslotPUSCH-Config-r15
          OPTIONAL, -- Need ON
      spdcch-Config-r15 [17] EXPLICIT SPDCCH-Config-r15 OPTIONAL, -- Need ON
      spucch-Config-r15 [18] EXPLICIT SPUCCH-Config-r15 OPTIONAL, -- Need ON
      srs-DCI7-TriggeringConfig-r15 [19] BOOLEAN,
      shortProcessingTime-r15 [20] BOOLEAN,
      shortTTI-r15 [21] ShortTTI-r15 OPTIONAL -- Need ON
   }
}

PDSCH-ConfigDedicated-v1530 ::= SEQUENCE {
   qcl-Operation-v1530 [0] ENUMERATED { typeC(0) } OPTIONAL, -- Need OR
   tbs-IndexAlt3-r15 [1] ENUMERATED { a37(0) } OPTIONAL, -- Need OR
--eNote (ToDo): Clarify that eMTC fields (i.e. fields starting with ce-) do not apply
--for SCell (merging issue)
   ce-CQI-AlternativeTableConfig-r15 [2] ENUMERATED { on(0) } OPTIONAL, -- Need OR
   ce-PDSCH-64QAM-Config-r15 [3] ENUMERATED { on(0) } OPTIONAL, -- Need OR
   ce-PDSCH-FlexibleStartPRB-AllocConfig-r15 [4] ENUMERATED { on(0) } OPTIONAL,
       -- Need OR
   altMCS-TableScalingConfig-r15 [5] ENUMERATED { oDot5(0), oDot625(1), 
      oDot75(2), oDot875(3) } OPTIONAL -- Need OR
}

PUSCH-ConfigDedicated-v1530 ::= SEQUENCE {
   ce-PUSCH-FlexibleStartPRB-AllocConfig-r15 [0] EXPLICIT CHOICE {
      release [0] NULL,
      setup [1] SEQUENCE {
         offsetCE-ModeB-r15 [0] INTEGER (-1..3) OPTIONAL -- Cond CE-ModeB
      }
   },
   ce-PUSCH-SubPRB-Config-r15 [1] EXPLICIT CHOICE {
      release [0] NULL,
      setup [1] SEQUENCE {
         locationCE-ModeB-r15 [0] INTEGER (0..5) OPTIONAL, -- Cond CE-ModeB
         sixToneCyclicShift-r15 [1] INTEGER (0..3),
         threeToneCyclicShift-r15 [2] INTEGER (0..2)
      }
   } OPTIONAL -- Need ON
}

CQI-ReportConfig-v1530 ::= SEQUENCE {
   altCQI-Table-1024QAM-r15 [0] ENUMERATED { allSubframes(0), 
      csi-SubframeSet1(1), csi-SubframeSet2(2), spare1(3) } OPTIONAL -- Need OP
}

AntennaInfoDedicated-v1530 ::= CHOICE {
   release [0] NULL,
   setup [1] EXPLICIT CHOICE {
      ue-TxAntennaSelection-SRS-1T4R-Config-r15 [0] NULL,
      ue-TxAntennaSelection-SRS-2T4R-NrOfPairs-r15 [1] ENUMERATED { two(0), 
         three(1) }
   }
}

CSI-RS-Config-v1530 ::= SEQUENCE {
   eMIMO-Type-v1530 [0] EXPLICIT CSI-RS-ConfigEMIMO-v1530 OPTIONAL -- Need ON
}

UplinkPowerControlDedicated-v1530 ::= SEQUENCE {
   alpha-UE-r15 [0] Alpha-r12 OPTIONAL, -- Need OR
   p0-UE-PUSCH-r15 [1] INTEGER (-16..15) OPTIONAL -- Need OR
}

CFI-Config-r15 ::= SEQUENCE {
   cfi-SubframeNonMBSFN-r15 [0] INTEGER (1..4) OPTIONAL, -- Need ON
   cfi-SlotSubslotNonMBSFN-r15 [1] INTEGER (1..3) OPTIONAL, -- Need ON
   cfi-SubframeMBSFN-r15 [2] INTEGER (1..2) OPTIONAL, -- Need ON
   cfi-SlotSubslotMBSFN-r15 [3] INTEGER (1..2) OPTIONAL -- Need ON
}

CFI-PatternConfig-r15 ::= SEQUENCE {
   cfi-PatternSubframe-r15 [0] SEQUENCE (SIZE (10)) OF INTEGER (1..4) OPTIONAL, -- Need ON
   cfi-PatternSlotSubslot-r15 [1] SEQUENCE (SIZE (10)) OF INTEGER (1..3) OPTIONAL -- Need ON
}

SPUCCH-Config-v1550 ::= CHOICE {
   release [0] NULL,
   setup [1] SEQUENCE {
      twoAntennaPortActivatedSPUCCH-Format3-v1550 [0] SEQUENCE {
         n3SPUCCH-AN-List-v1550 [0] SEQUENCE (SIZE (1..4)) OF INTEGER (0..549)
      }
   }
}

PhysicalConfigDedicated ::= SEQUENCE {
   pdsch-ConfigDedicated [0] PDSCH-ConfigDedicated OPTIONAL, -- Need ON
   pucch-ConfigDedicated [1] PUCCH-ConfigDedicated OPTIONAL, -- Need ON
   pusch-ConfigDedicated [2] PUSCH-ConfigDedicated OPTIONAL, -- Need ON
   uplinkPowerControlDedicated [3] UplinkPowerControlDedicated OPTIONAL, -- Need ON
   tpc-PDCCH-ConfigPUCCH [4] EXPLICIT TPC-PDCCH-Config OPTIONAL, -- Need ON
   tpc-PDCCH-ConfigPUSCH [5] EXPLICIT TPC-PDCCH-Config OPTIONAL, -- Need ON
   cqi-ReportConfig [6] CQI-ReportConfig OPTIONAL, -- Cond CQI-r8
   soundingRS-UL-ConfigDedicated [7] EXPLICIT SoundingRS-UL-ConfigDedicated
       OPTIONAL, -- Need ON
   antennaInfo [8] EXPLICIT CHOICE {
      explicitValue [0] AntennaInfoDedicated,
      defaultValue [1] NULL
   } OPTIONAL, -- Cond AI-r8
   schedulingRequestConfig [9] EXPLICIT SchedulingRequestConfig OPTIONAL,
   ...,
   [[
      cqi-ReportConfig-v920 [10] CQI-ReportConfig-v920 OPTIONAL,
      antennaInfo-v920 [11] AntennaInfoDedicated-v920 OPTIONAL
   ]],
   [[
      antennaInfo-r10 [12] EXPLICIT CHOICE {
         explicitValue-r10 [0] AntennaInfoDedicated-r10,
         defaultValue [1] NULL
      } OPTIONAL,
      antennaInfoUL-r10 [13] AntennaInfoUL-r10 OPTIONAL,
      cif-Presence-r10 [14] BOOLEAN OPTIONAL,
      cqi-ReportConfig-r10 [15] CQI-ReportConfig-r10 OPTIONAL,
      csi-RS-Config-r10 [16] CSI-RS-Config-r10 OPTIONAL,
      pucch-ConfigDedicated-v1020 [17] PUCCH-ConfigDedicated-v1020 OPTIONAL,
      pusch-ConfigDedicated-v1020 [18] PUSCH-ConfigDedicated-v1020 OPTIONAL,
      schedulingRequestConfig-v1020 [19] SchedulingRequestConfig-v1020 OPTIONAL
         ,
      soundingRS-UL-ConfigDedicated-v1020 [20] 
         SoundingRS-UL-ConfigDedicated-v1020 OPTIONAL,
      soundingRS-UL-ConfigDedicatedAperiodic-r10 [21] EXPLICIT 
         SoundingRS-UL-ConfigDedicatedAperiodic-r10 OPTIONAL,
      uplinkPowerControlDedicated-v1020 [22] UplinkPowerControlDedicated-v1020
          OPTIONAL
   ]],
   [[
      additionalSpectrumEmissionCA-r10 [23] EXPLICIT CHOICE {
         release [0] NULL,
         setup [1] SEQUENCE {
            additionalSpectrumEmissionPCell-r10 [0] AdditionalSpectrumEmission
         }
      } OPTIONAL
   ]],
   [[
      csi-RS-ConfigNZPToReleaseList-r11 [24] CSI-RS-ConfigNZPToReleaseList-r11
          OPTIONAL,
      csi-RS-ConfigNZPToAddModList-r11 [25] CSI-RS-ConfigNZPToAddModList-r11
          OPTIONAL,
      csi-RS-ConfigZPToReleaseList-r11 [26] CSI-RS-ConfigZPToReleaseList-r11
          OPTIONAL,
      csi-RS-ConfigZPToAddModList-r11 [27] CSI-RS-ConfigZPToAddModList-r11
          OPTIONAL,
      epdcch-Config-r11 [28] EPDCCH-Config-r11 OPTIONAL,
      pdsch-ConfigDedicated-v1130 [29] PDSCH-ConfigDedicated-v1130 OPTIONAL,
      cqi-ReportConfig-v1130 [30] CQI-ReportConfig-v1130 OPTIONAL,
      pucch-ConfigDedicated-v1130 [31] PUCCH-ConfigDedicated-v1130 OPTIONAL,
      pusch-ConfigDedicated-v1130 [32] PUSCH-ConfigDedicated-v1130 OPTIONAL,
      uplinkPowerControlDedicated-v1130 [33] UplinkPowerControlDedicated-v1130
          OPTIONAL
   ]],
   [[
      antennaInfo-v1250 [34] AntennaInfoDedicated-v1250 OPTIONAL,
      eimta-MainConfig-r12 [35] EXPLICIT EIMTA-MainConfig-r12 OPTIONAL,
      eimta-MainConfigPCell-r12 [36] EXPLICIT EIMTA-MainConfigServCell-r12
          OPTIONAL,
      pucch-ConfigDedicated-v1250 [37] PUCCH-ConfigDedicated-v1250 OPTIONAL,
      cqi-ReportConfigPCell-v1250 [38] CQI-ReportConfig-v1250 OPTIONAL,
      uplinkPowerControlDedicated-v1250 [39] UplinkPowerControlDedicated-v1250
          OPTIONAL,
      pusch-ConfigDedicated-v1250 [40] PUSCH-ConfigDedicated-v1250 OPTIONAL,
      csi-RS-Config-v1250 [41] CSI-RS-Config-v1250 OPTIONAL
   ]],
   [[
      pdsch-ConfigDedicated-v1280 [42] PDSCH-ConfigDedicated-v1280 OPTIONAL
   ]],
   [[
      pdsch-ConfigDedicated-v1310 [43] PDSCH-ConfigDedicated-v1310 OPTIONAL,
      pucch-ConfigDedicated-r13 [44] PUCCH-ConfigDedicated-r13 OPTIONAL,
      pusch-ConfigDedicated-r13 [45] PUSCH-ConfigDedicated-r13 OPTIONAL,
      pdcch-CandidateReductions-r13 [46] EXPLICIT PDCCH-CandidateReductions-r13
          OPTIONAL,
      cqi-ReportConfig-v1310 [47] CQI-ReportConfig-v1310 OPTIONAL,
      soundingRS-UL-ConfigDedicated-v1310 [48] EXPLICIT 
         SoundingRS-UL-ConfigDedicated-v1310 OPTIONAL,
      soundingRS-UL-ConfigDedicatedUpPTsExt-r13 [49] EXPLICIT 
         SoundingRS-UL-ConfigDedicatedUpPTsExt-r13 OPTIONAL,
      soundingRS-UL-ConfigDedicatedAperiodic-v1310 [50] EXPLICIT 
         SoundingRS-UL-ConfigDedicatedAperiodic-v1310 OPTIONAL,
      soundingRS-UL-ConfigDedicatedAperiodicUpPTsExt-r13 [51] EXPLICIT 
         SoundingRS-UL-ConfigDedicatedAperiodicUpPTsExt-r13 OPTIONAL,
      csi-RS-Config-v1310 [52] CSI-RS-Config-v1310 OPTIONAL,
      ce-Mode-r13 [53] EXPLICIT CHOICE {
         release [0] NULL,
         setup [1] ENUMERATED { ce-ModeA(0), ce-ModeB(1) }
      } OPTIONAL,
      csi-RS-ConfigNZPToAddModListExt-r13 [54] 
         CSI-RS-ConfigNZPToAddModListExt-r13 OPTIONAL,
      csi-RS-ConfigNZPToReleaseListExt-r13 [55] 
         CSI-RS-ConfigNZPToReleaseListExt-r13 OPTIONAL
   ]],
   [[
      cqi-ReportConfig-v1320 [56] CQI-ReportConfig-v1320 OPTIONAL
   ]],
   [[
      typeA-SRS-TPC-PDCCH-Group-r14 [57] EXPLICIT CHOICE {
         release [0] NULL,
         setup [1] SEQUENCE (SIZE (1..32)) OF SRS-TPC-PDCCH-Config-r14
      } OPTIONAL,
      must-Config-r14 [58] EXPLICIT CHOICE {
         release [0] NULL,
         setup [1] SEQUENCE {
            k-max-r14 [0] ENUMERATED { l1(0), l3(1) },
            p-a-must-r14 [1] ENUMERATED { dB-6(0), dB-4dot77(1), dB-3(2), 
               dB-1dot77(3), dB0(4), dB1(5), dB2(6), dB3(7) } OPTIONAL -- Need ON
         }
      } OPTIONAL,
      pusch-EnhancementsConfig-r14 [59] EXPLICIT PUSCH-EnhancementsConfig-r14
          OPTIONAL,
      ce-pdsch-pusch-EnhancementConfig-r14 [60] ENUMERATED { on(0) } OPTIONAL,
      antennaInfo-v1430 [61] AntennaInfoDedicated-v1430 OPTIONAL,
      pucch-ConfigDedicated-v1430 [62] PUCCH-ConfigDedicated-v1430 OPTIONAL,
      pdsch-ConfigDedicated-v1430 [63] PDSCH-ConfigDedicated-v1430 OPTIONAL,
      pusch-ConfigDedicated-v1430 [64] PUSCH-ConfigDedicated-v1430 OPTIONAL,
      soundingRS-UL-PeriodicConfigDedicatedList-r14 [65] SEQUENCE (SIZE (1..2)
         ) OF SoundingRS-UL-ConfigDedicated OPTIONAL,
      soundingRS-UL-PeriodicConfigDedicatedUpPTsExtList-r14 [66] SEQUENCE (
         SIZE (1..4)) OF SoundingRS-UL-ConfigDedicatedUpPTsExt-r13 OPTIONAL,
      soundingRS-UL-AperiodicConfigDedicatedList-r14 [67] SEQUENCE (SIZE (1..2)
         ) OF SoundingRS-UL-ConfigDedicatedAperiodic-r10 OPTIONAL,
      soundingRS-UL-ConfigDedicatedApUpPTsExtList-r14 [68] SEQUENCE (SIZE (1..4)
         ) OF SoundingRS-UL-ConfigDedicatedAperiodicUpPTsExt-r13 OPTIONAL,
      csi-RS-Config-v1430 [69] CSI-RS-Config-v1430 OPTIONAL,
      csi-RS-ConfigZP-ApList-r14 [70] EXPLICIT CSI-RS-ConfigZP-ApList-r14
          OPTIONAL,
      cqi-ReportConfig-v1430 [71] CQI-ReportConfig-v1430 OPTIONAL,
      semiOpenLoop-r14 [72] BOOLEAN OPTIONAL
   ]],
   [[
      csi-RS-Config-v1480 [73] CSI-RS-Config-v1480 OPTIONAL
   ]],
   [[
      physicalConfigDedicatedSTTI-r15 [74] EXPLICIT 
         PhysicalConfigDedicatedSTTI-r15 OPTIONAL,
      pdsch-ConfigDedicated-v1530 [75] PDSCH-ConfigDedicated-v1530 OPTIONAL,
      pusch-ConfigDedicated-v1530 [76] PUSCH-ConfigDedicated-v1530 OPTIONAL,
      cqi-ReportConfig-v1530 [77] CQI-ReportConfig-v1530 OPTIONAL,
      antennaInfo-v1530 [78] EXPLICIT AntennaInfoDedicated-v1530 OPTIONAL,
      csi-RS-Config-v1530 [79] CSI-RS-Config-v1530 OPTIONAL,
      uplinkPowerControlDedicated-v1530 [80] UplinkPowerControlDedicated-v1530
          OPTIONAL,
      semiStaticCFI-Config-r15 [81] EXPLICIT CHOICE {
         release [0] NULL,
         setup [1] EXPLICIT CHOICE {
            cfi-Config-r15 [0] CFI-Config-r15,
            cfi-PatternConfig-r15 [1] CFI-PatternConfig-r15
         }
      } OPTIONAL,
      blindPDSCH-Repetition-Config-r15 [82] EXPLICIT CHOICE {
         release [0] NULL,
         setup [1] SEQUENCE {
            blindSubframePDSCH-Repetitions-r15 [0] BOOLEAN,
            blindSlotSubslotPDSCH-Repetitions-r15 [1] BOOLEAN,
            maxNumber-SubframePDSCH-Repetitions-r15 [2] ENUMERATED { n4(0), 
               n6(1) } OPTIONAL, -- Need ON
            maxNumber-SlotSubslotPDSCH-Repetitions-r15 [3] ENUMERATED { n4(0), 
               n6(1) } OPTIONAL, -- Need ON
            rv-SubframePDSCH-Repetitions-r15 [4] ENUMERATED { dlrvseq1(0), 
               dlrvseq2(1) } OPTIONAL, -- Need ON
            rv-SlotsublotPDSCH-Repetitions-r15 [5] ENUMERATED { dlrvseq1(0), 
               dlrvseq2(1) } OPTIONAL, -- Need ON
            numberOfProcesses-SubframePDSCH-Repetitions-r15 [6] INTEGER (1..16)
                OPTIONAL, -- Need ON
            numberOfProcesses-SlotSubslotPDSCH-Repetitions-r15 [7] INTEGER (1..16)
                OPTIONAL, -- Need ON
            mcs-restrictionSubframePDSCH-Repetitions-r15 [8] ENUMERATED { n0(0)
               , n1(1) } OPTIONAL, -- Need ON
            mcs-restrictionSlotSubslotPDSCH-Repetitions-r15 [9] ENUMERATED { 
               n0(0), n1(1) } OPTIONAL -- Need ON
         }
      } OPTIONAL
   ]],
   [[
      spucch-Config-v1550 [83] EXPLICIT SPUCCH-Config-v1550 OPTIONAL
   ]]
}

RLF-TimersAndConstants-r9 ::= CHOICE {
   release [0] NULL,
   setup [1] SEQUENCE {
      t301-r9 [0] ENUMERATED { ms100(0), ms200(1), ms300(2), ms400(3), ms600(4)
         , ms1000(5), ms1500(6), ms2000(7) },
      t310-r9 [1] ENUMERATED { ms0(0), ms50(1), ms100(2), ms200(3), ms500(4), 
         ms1000(5), ms2000(6) },
      n310-r9 [2] ENUMERATED { n1(0), n2(1), n3(2), n4(3), n6(4), n8(5), n10(6)
         , n20(7) },
      t311-r9 [3] ENUMERATED { ms1000(0), ms3000(1), ms5000(2), ms10000(3), 
         ms15000(4), ms20000(5), ms30000(6) },
      n311-r9 [4] ENUMERATED { n1(0), n2(1), n3(2), n4(3), n5(4), n6(5), n8(6)
         , n10(7) },
      ...
   }
}

MeasSubframePatternPCell-r10 ::= CHOICE {
   release [0] NULL,
   setup [1] EXPLICIT MeasSubframePattern-r10
}

CRS-AssistanceInfo-r11 ::= SEQUENCE {
   physCellId-r11 [0] PhysCellId,
   antennaPortsCount-r11 [1] ENUMERATED { an1(0), an2(1), an4(2), spare1(3) },
   mbsfn-SubframeConfigList-r11 [2] MBSFN-SubframeConfigList,
   ...,
   [[
      mbsfn-SubframeConfigList-v1430 [3] MBSFN-SubframeConfigList-v1430
          OPTIONAL
   ]]
}

CRS-AssistanceInfoList-r11 ::= SEQUENCE (SIZE (1..maxCellReport)) OF CRS-AssistanceInfo-r11

NeighCellsCRS-Info-r11 ::= CHOICE {
   release [0] NULL,
   setup [1] CRS-AssistanceInfoList-r11
}

NeighCellsToReleaseList-r12 ::= SEQUENCE (SIZE (1..maxNeighCell-r12)) OF PhysCellId

NeighCellsInfo-r12 ::= SEQUENCE {
   physCellId-r12 [0] PhysCellId,
   p-b-r12 [1] INTEGER (0..3),
   crs-PortsCount-r12 [2] ENUMERATED { n1(0), n2(1), n4(2), spare(3) },
   mbsfn-SubframeConfig-r12 [3] MBSFN-SubframeConfigList OPTIONAL, -- Need ON
   p-aList-r12 [4] SEQUENCE (SIZE (1..maxP-a-PerNeighCell-r12)) OF P-a,
   transmissionModeList-r12 [5] BIT STRING  (SIZE (8)),
   resAllocGranularity-r12 [6] INTEGER (1..4),
   ...
}

NeighCellsToAddModList-r12 ::= SEQUENCE (SIZE (1..maxNeighCell-r12)) OF NeighCellsInfo-r12

NAICS-AssistanceInfo-r12 ::= CHOICE {
   release [0] NULL,
   setup [1] SEQUENCE {
      neighCellsToReleaseList-r12 [0] NeighCellsToReleaseList-r12 OPTIONAL, -- Need ON
      neighCellsToAddModList-r12 [1] NeighCellsToAddModList-r12 OPTIONAL, -- Need ON
      servCellp-a-r12 [2] P-a OPTIONAL -- Need ON
   }
}

CRS-AssistanceInfo-r13 ::= SEQUENCE {
   physCellId-r13 [0] PhysCellId,
   antennaPortsCount-r13 [1] ENUMERATED { an1(0), an2(1), an4(2), spare1(3) },
   mbsfn-SubframeConfigList-r13 [2] MBSFN-SubframeConfigList OPTIONAL,
   ...,
   [[
      mbsfn-SubframeConfigList-v1430 [3] MBSFN-SubframeConfigList-v1430
          OPTIONAL
   ]]
}

CRS-AssistanceInfoList-r13 ::= SEQUENCE (SIZE (1..maxCellReport)) OF CRS-AssistanceInfo-r13

NeighCellsCRS-Info-r13 ::= CHOICE {
   release [0] NULL,
   setup [1] CRS-AssistanceInfoList-r13
}

RLF-TimersAndConstants-r13 ::= CHOICE {
   release [0] NULL,
   setup [1] SEQUENCE {
      t301-v1310 [0] ENUMERATED { ms2500(0), ms3000(1), ms3500(2), ms4000(3), 
         ms5000(4), ms6000(5), ms8000(6), ms10000(7) },
      ...,
      [[
         t310-v1330 [1] ENUMERATED { ms4000(0), ms6000(1) } OPTIONAL
      ]]
   }
}

SPS-ConfigUL-ToAddModList-r14 ::= SEQUENCE (SIZE (1..maxConfigSPS-r14)) OF SPS-ConfigUL

SPS-ConfigUL-ToReleaseList-r14 ::= SEQUENCE (SIZE (1..maxConfigSPS-r14)) OF SPS-ConfigIndex-r14

SPS-ConfigSL-r14 ::= SEQUENCE {
   sps-ConfigIndex-r14 [0] SPS-ConfigIndex-r14,
   semiPersistSchedIntervalSL-r14 [1] ENUMERATED { sf20(0), sf50(1), sf100(2), 
      sf200(3), sf300(4), sf400(5), sf500(6), sf600(7), sf700(8), sf800(9), 
      sf900(10), sf1000(11), spare4(12), spare3(13), spare2(14), spare1(15) }
}

SPS-ConfigSL-ToAddModList-r14 ::= SEQUENCE (SIZE (1..maxConfigSPS-r14)) OF SPS-ConfigSL-r14

SPS-ConfigSL-ToReleaseList-r14 ::= SEQUENCE (SIZE (1..maxConfigSPS-r14)) OF SPS-ConfigIndex-r14

SPS-Config-v1430 ::= SEQUENCE {
   ul-SPS-V-RNTI-r14 [0] C-RNTI OPTIONAL, -- Need OR
   sl-SPS-V-RNTI-r14 [1] C-RNTI OPTIONAL, -- Need OR
   sps-ConfigUL-ToAddModList-r14 [2] SPS-ConfigUL-ToAddModList-r14 OPTIONAL, -- Need ON
   sps-ConfigUL-ToReleaseList-r14 [3] SPS-ConfigUL-ToReleaseList-r14 OPTIONAL, -- Need ON
   sps-ConfigSL-ToAddModList-r14 [4] SPS-ConfigSL-ToAddModList-r14 OPTIONAL, -- Need ON
   sps-ConfigSL-ToReleaseList-r14 [5] SPS-ConfigSL-ToReleaseList-r14 OPTIONAL -- Need ON
}

SRB-ToAddModListExt-r15 ::= SEQUENCE (SIZE (1)) OF SRB-ToAddMod

SPS-ConfigUL-STTI-r15 ::= CHOICE {
   release [0] NULL,
   setup [1] SEQUENCE {
      semiPersistSchedIntervalUL-STTI-r15 [0] ENUMERATED { sTTI1(0), sTTI2(1), 
         sTTI3(2), sTTI4(3), sTTI6(4), sTTI8(5), sTTI12(6), sTTI16(7), 
         sTTI20(8), sTTI40(9), sTTI60(10), sTTI80(11), sTTI120(12), sTTI240(13)
         , spare2(14), spare1(15) },
      implicitReleaseAfter [1] ENUMERATED { e2(0), e3(1), e4(2), e8(3) },
      p0-Persistent-r15 [2] SEQUENCE {
         p0-NominalSPUSCH-Persistent-r15 [0] INTEGER (-126..24),
         p0-UE-SPUSCH-Persistent-r15 [1] INTEGER (-8..7)
      } OPTIONAL, -- Need OP
      twoIntervalsConfig-r15 [3] ENUMERATED { true(0) } OPTIONAL, -- Cond TDD
      p0-PersistentSubframeSet2-r15 [4] EXPLICIT CHOICE {
         release [0] NULL,
         setup [1] SEQUENCE {
            p0-NominalSPUSCH-PersistentSubframeSet2-r15 [0] INTEGER (-126..24),
            p0-UE-SPUSCH-PersistentSubframeSet2-r15 [1] INTEGER (-8..7)
         }
      } OPTIONAL, -- Need ON
      numberOfConfUL-SPS-Processes-STTI-r15 [5] INTEGER (1..12) OPTIONAL, -- Need OR
      sTTI-StartTimeUL-r15 [6] INTEGER (0..5),
      tpc-PDCCH-ConfigPUSCH-SPS-r15 [7] EXPLICIT TPC-PDCCH-Config OPTIONAL, -- Need ON
      cyclicShiftSPS-sTTI-r15 [8] ENUMERATED { cs0(0), cs1(1), cs2(2), cs3(3), 
         cs4(4), cs5(5), cs6(6), cs7(7) } OPTIONAL, -- Need ON
      ifdma-Config-SPS-r15 [9] BOOLEAN OPTIONAL, -- Need ON
      harq-ProcID-offset-r15 [10] INTEGER (0..15) OPTIONAL, -- Need ON
      rv-SPS-STTI-UL-Repetitions-r15 [11] ENUMERATED { ulrvseq1(0), ulrvseq2(1)
         , ulrvseq3(2) } OPTIONAL, -- Need ON
      sps-ConfigIndex-r15 [12] SPS-ConfigIndex-r15 OPTIONAL, -- Need OR
      tbs-scalingFactorSubslotSPS-UL-Repetitions-r15 [13] ENUMERATED { n6(0), 
         n12(1) } OPTIONAL, -- Need ON
      totalNumberPUSCH-SPS-STTI-UL-Repetitions-r15 [14] ENUMERATED { n2(0), 
         n3(1), n4(2), n6(3) } OPTIONAL,
      ...
   }
}

SPS-ConfigUL-STTI-ToAddModList-r15 ::= SEQUENCE (SIZE (1..maxConfigSPS-r15)) OF 
   SPS-ConfigUL-STTI-r15

SPS-ConfigUL-STTI-ToReleaseList-r15 ::= SEQUENCE (SIZE (1..maxConfigSPS-r15)) OF 
   SPS-ConfigIndex-r15

SPS-ConfigUL-ToAddModList-r15 ::= SEQUENCE (SIZE (1..maxConfigSPS-r15)) OF SPS-ConfigUL

SPS-ConfigUL-ToReleaseList-r15 ::= SEQUENCE (SIZE (1..maxConfigSPS-r15)) OF SPS-ConfigIndex-r15

SPS-Config-v1530 ::= SEQUENCE {
   semiPersistSchedC-RNTI-r15 [0] C-RNTI OPTIONAL, -- Need OR
   sps-ConfigDL-r15 [1] EXPLICIT SPS-ConfigDL OPTIONAL, -- Need ON
   sps-ConfigUL-STTI-ToAddModList-r15 [2] SPS-ConfigUL-STTI-ToAddModList-r15
       OPTIONAL, -- Need ON
   sps-ConfigUL-STTI-ToReleaseList-r15 [3] SPS-ConfigUL-STTI-ToReleaseList-r15
       OPTIONAL, -- Need ON
   sps-ConfigUL-ToAddModList-r15 [4] SPS-ConfigUL-ToAddModList-r15 OPTIONAL, -- Need ON
   sps-ConfigUL-ToReleaseList-r15 [5] SPS-ConfigUL-ToReleaseList-r15 OPTIONAL -- Need ON
}

CRS-AssistanceInfo-r15 ::= SEQUENCE {
   physCellId-r15 [0] PhysCellId,
   crs-IntfMitigEnabled-15 [1] ENUMERATED { enabled(0) } OPTIONAL -- Need ON
}

CRS-AssistanceInfoList-r15 ::= SEQUENCE (SIZE (1..maxCellReport)) OF CRS-AssistanceInfo-r15

NeighCellsCRS-Info-r15 ::= CHOICE {
   release [0] NULL,
   setup [1] CRS-AssistanceInfoList-r15
}

DRB-ToAddModList-r15 ::= SEQUENCE (SIZE (1..maxDRB-r15)) OF DRB-ToAddMod

DRB-ToReleaseList-r15 ::= SEQUENCE (SIZE (1..maxDRB-r15)) OF DRB-Identity

N1SPUCCH-AN-PersistentList-r15 ::= SEQUENCE (SIZE (1..4)) OF INTEGER (0..2047)

SPS-ConfigDL-STTI-r15 ::= CHOICE {
   release [0] NULL,
   setup [1] SEQUENCE {
      semiPersistSchedIntervalDL-STTI-r15 [0] ENUMERATED { sTTI1(0), sTTI2(1), 
         sTTI3(2), sTTI4(3), sTTI6(4), sTTI8(5), sTTI12(6), sTTI16(7), 
         sTTI20(8), sTTI40(9), sTTI60(10), sTTI80(11), sTTI120(12), sTTI240(13)
         , spare2(14), spare1(15) },
      numberOfConfSPS-Processes-STTI-r15 [1] INTEGER (1..12),
      twoAntennaPortActivated-r15 [2] EXPLICIT CHOICE {
         release [0] NULL,
         setup [1] SEQUENCE {
            n1SPUCCH-AN-PersistentListP1-r15 [0] N1SPUCCH-AN-PersistentList-r15
         }
      } OPTIONAL, -- Need ON
      sTTI-StartTimeDL-r15 [3] INTEGER (0..5),
      tpc-PDCCH-ConfigPUCCH-SPS-r15 [4] EXPLICIT TPC-PDCCH-Config OPTIONAL,
      ...
   }
}

SPS-Config-v1540 ::= SEQUENCE {
   sps-ConfigDL-STTI-r15 [0] EXPLICIT SPS-ConfigDL-STTI-r15 OPTIONAL -- Need OR
}

RadioResourceConfigDedicated ::= SEQUENCE {
   srb-ToAddModList [0] SRB-ToAddModList OPTIONAL, -- Cond HO-Conn
   drb-ToAddModList [1] DRB-ToAddModList OPTIONAL, -- Cond HO-toEUTRA
   drb-ToReleaseList [2] DRB-ToReleaseList OPTIONAL, -- Need ON
   mac-MainConfig [3] EXPLICIT CHOICE {
      explicitValue [0] MAC-MainConfig,
      defaultValue [1] NULL
   } OPTIONAL, -- Cond HO-toEUTRA2
   sps-Config [4] SPS-Config OPTIONAL, -- Need ON
   physicalConfigDedicated [5] PhysicalConfigDedicated OPTIONAL,
   ...,
   [[
      rlf-TimersAndConstants-r9 [6] EXPLICIT RLF-TimersAndConstants-r9 OPTIONAL
   ]],
   [[
      measSubframePatternPCell-r10 [7] EXPLICIT MeasSubframePatternPCell-r10
          OPTIONAL
   ]],
   [[
      neighCellsCRS-Info-r11 [8] EXPLICIT NeighCellsCRS-Info-r11 OPTIONAL
   ]],
   [[
      naics-Info-r12 [9] EXPLICIT NAICS-AssistanceInfo-r12 OPTIONAL
   ]],
   [[
      neighCellsCRS-Info-r13 [10] EXPLICIT NeighCellsCRS-Info-r13 OPTIONAL,
      rlf-TimersAndConstants-r13 [11] EXPLICIT RLF-TimersAndConstants-r13
          OPTIONAL
   ]],
   [[
      sps-Config-v1430 [12] SPS-Config-v1430 OPTIONAL
   ]],
   [[
      srb-ToAddModListExt-r15 [13] SRB-ToAddModListExt-r15 OPTIONAL,
      srb-ToReleaseListExt-r15 [14] INTEGER (4) OPTIONAL,
      sps-Config-v1530 [15] SPS-Config-v1530 OPTIONAL,
      crs-IntfMitigConfig-r15 [16] EXPLICIT CHOICE {
         release [0] NULL,
         setup [1] EXPLICIT CHOICE {
            crs-IntfMitigEnabled-15 [0] NULL,
            crs-IntfMitigNumPRBs-r15 [1] ENUMERATED { n6(0), n24(1) }
         }
      } OPTIONAL,
      neighCellsCRS-Info-r15 [17] EXPLICIT NeighCellsCRS-Info-r15 OPTIONAL,
      drb-ToAddModList-r15 [18] DRB-ToAddModList-r15 OPTIONAL,
      drb-ToReleaseList-r15 [19] DRB-ToReleaseList-r15 OPTIONAL,
      dummy [20] SEQUENCE (SIZE (1..2)) OF INTEGER (1..2) OPTIONAL
   ]],
   [[
      sps-Config-v1540 [21] SPS-Config-v1540 OPTIONAL
   ]]
}

RRCConnectionReestablishment-v8a0-IEs ::= SEQUENCE {
   lateNonCriticalExtension [0] OCTET STRING OPTIONAL,
   nonCriticalExtension [1] SEQUENCE {

   } OPTIONAL
}

RRCConnectionReestablishment-r8-IEs ::= SEQUENCE {
   radioResourceConfigDedicated [0] RadioResourceConfigDedicated,
   nextHopChainingCount [1] NextHopChainingCount,
   nonCriticalExtension [2] RRCConnectionReestablishment-v8a0-IEs OPTIONAL
}

RRCConnectionReestablishment ::= SEQUENCE {
   rrc-TransactionIdentifier [0] RRC-TransactionIdentifier,
   criticalExtensions [1] EXPLICIT CHOICE {
      c1 [0] EXPLICIT CHOICE {
         rrcConnectionReestablishment-r8 [0] 
            RRCConnectionReestablishment-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

RRCConnectionReestablishmentReject-v8a0-IEs ::= SEQUENCE {
   lateNonCriticalExtension [0] OCTET STRING OPTIONAL,
   nonCriticalExtension [1] SEQUENCE {

   } OPTIONAL
}

RRCConnectionReestablishmentReject-r8-IEs ::= SEQUENCE {
   nonCriticalExtension [0] RRCConnectionReestablishmentReject-v8a0-IEs
       OPTIONAL
}

RRCConnectionReestablishmentReject ::= SEQUENCE {
   criticalExtensions [0] EXPLICIT CHOICE {
      rrcConnectionReestablishmentReject-r8 [0] 
         RRCConnectionReestablishmentReject-r8-IEs,
      criticalExtensionsFuture [1] SEQUENCE {

      }
   }
}

RRCConnectionReject-v1320-IEs ::= SEQUENCE {
   rrc-SuspendIndication-r13 [0] ENUMERATED { true(0) } OPTIONAL, --	Need ON
   nonCriticalExtension [1] SEQUENCE {

   } OPTIONAL
}

RRCConnectionReject-v1130-IEs ::= SEQUENCE {
   deprioritisationReq-r11 [0] SEQUENCE {
      deprioritisationType-r11 [0] ENUMERATED { frequency(0), e-utra(1) },
      deprioritisationTimer-r11 [1] ENUMERATED { min5(0), min10(1), min15(2), 
         min30(3) }
   } OPTIONAL, -- Need ON
   nonCriticalExtension [1] RRCConnectionReject-v1320-IEs OPTIONAL
}

RRCConnectionReject-v1020-IEs ::= SEQUENCE {
   extendedWaitTime-r10 [0] INTEGER (1..1800) OPTIONAL, -- Need ON
   nonCriticalExtension [1] RRCConnectionReject-v1130-IEs OPTIONAL
}

RRCConnectionReject-v8a0-IEs ::= SEQUENCE {
   lateNonCriticalExtension [0] OCTET STRING OPTIONAL,
   nonCriticalExtension [1] RRCConnectionReject-v1020-IEs OPTIONAL
}

RRCConnectionReject-r8-IEs ::= SEQUENCE {
   waitTime [0] INTEGER (1..16),
   nonCriticalExtension [1] RRCConnectionReject-v8a0-IEs OPTIONAL
}

RRCConnectionReject ::= SEQUENCE {
   criticalExtensions [0] EXPLICIT CHOICE {
      c1 [0] EXPLICIT CHOICE {
         rrcConnectionReject-r8 [0] RRCConnectionReject-r8-IEs,
         spare3 [1] NULL,
         spare2 [2] NULL,
         spare1 [3] NULL
      },
      criticalExtensionsFuture [1] SEQUENCE {

      }
   }
}

RRCConnectionSetup-v8a0-IEs ::= SEQUENCE {
   lateNonCriticalExtension [0] OCTET STRING OPTIONAL,
   nonCriticalExtension [1] SEQUENCE {

   } OPTIONAL
}

RRCConnectionSetup-r8-IEs ::= SEQUENCE {
   radioResourceConfigDedicated [0] RadioResourceConfigDedicated,
   nonCriticalExtension [1] RRCConnectionSetup-v8a0-IEs OPTIONAL
}

RRCConnectionSetup ::= SEQUENCE {
   rrc-TransactionIdentifier [0] RRC-TransactionIdentifier,
   criticalExtensions [1] EXPLICIT CHOICE {
      c1 [0] EXPLICIT CHOICE {
         rrcConnectionSetup-r8 [0] RRCConnectionSetup-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

FreqPriorityEUTRA ::= SEQUENCE {
   carrierFreq [0] ARFCN-ValueEUTRA,
   cellReselectionPriority [1] CellReselectionPriority
}

FreqPriorityListEUTRA ::= SEQUENCE (SIZE (1..maxFreq)) OF FreqPriorityEUTRA

FreqsPriorityGERAN ::= SEQUENCE {
   carrierFreqs [0] CarrierFreqsGERAN,
   cellReselectionPriority [1] CellReselectionPriority
}

FreqsPriorityListGERAN ::= SEQUENCE (SIZE (1..maxGNFG)) OF FreqsPriorityGERAN

FreqPriorityUTRA-FDD ::= SEQUENCE {
   carrierFreq [0] ARFCN-ValueUTRA,
   cellReselectionPriority [1] CellReselectionPriority
}

FreqPriorityListUTRA-FDD ::= SEQUENCE (SIZE (1..maxUTRA-FDD-Carrier)) OF FreqPriorityUTRA-FDD

FreqPriorityUTRA-TDD ::= SEQUENCE {
   carrierFreq [0] ARFCN-ValueUTRA,
   cellReselectionPriority [1] CellReselectionPriority
}

FreqPriorityListUTRA-TDD ::= SEQUENCE (SIZE (1..maxUTRA-TDD-Carrier)) OF FreqPriorityUTRA-TDD

BandClassPriorityHRPD ::= SEQUENCE {
   bandClass [0] BandclassCDMA2000,
   cellReselectionPriority [1] CellReselectionPriority
}

BandClassPriorityListHRPD ::= SEQUENCE (SIZE (1..maxCDMA-BandClass)) OF BandClassPriorityHRPD

BandClassPriority1XRTT ::= SEQUENCE {
   bandClass [0] BandclassCDMA2000,
   cellReselectionPriority [1] CellReselectionPriority
}

BandClassPriorityList1XRTT ::= SEQUENCE (SIZE (1..maxCDMA-BandClass)) OF BandClassPriority1XRTT

FreqPriorityEUTRA-r12 ::= SEQUENCE {
   carrierFreq-r12 [0] ARFCN-ValueEUTRA-r9,
   cellReselectionPriority-r12 [1] CellReselectionPriority
}

FreqPriorityListExtEUTRA-r12 ::= SEQUENCE (SIZE (1..maxFreq)) OF FreqPriorityEUTRA-r12

FreqPriorityEUTRA-v1310 ::= SEQUENCE {
   cellReselectionSubPriority-r13 [0] CellReselectionSubPriority-r13 OPTIONAL -- Need ON
}

FreqPriorityListEUTRA-v1310 ::= SEQUENCE (SIZE (1..maxFreq)) OF FreqPriorityEUTRA-v1310
   

FreqPriorityListExtEUTRA-v1310 ::= SEQUENCE (SIZE (1..maxFreq)) OF 
   FreqPriorityEUTRA-v1310

FreqPriorityNR-r15 ::= SEQUENCE {
   carrierFreq-r15 [0] ARFCN-ValueNR-r15,
   cellReselectionPriority-r15 [1] CellReselectionPriority,
   cellReselectionSubPriority-r15 [2] CellReselectionSubPriority-r13 OPTIONAL -- Need OR
}

FreqPriorityListNR-r15 ::= SEQUENCE (SIZE (1..maxFreq)) OF FreqPriorityNR-r15

IdleModeMobilityControlInfo ::= SEQUENCE {
   freqPriorityListEUTRA [0] FreqPriorityListEUTRA OPTIONAL, -- Need ON
   freqPriorityListGERAN [1] FreqsPriorityListGERAN OPTIONAL, -- Need ON
   freqPriorityListUTRA-FDD [2] FreqPriorityListUTRA-FDD OPTIONAL, -- Need ON
   freqPriorityListUTRA-TDD [3] FreqPriorityListUTRA-TDD OPTIONAL, -- Need ON
   bandClassPriorityListHRPD [4] BandClassPriorityListHRPD OPTIONAL, -- Need ON
   bandClassPriorityList1XRTT [5] BandClassPriorityList1XRTT OPTIONAL, -- Need ON
   t320 [6] ENUMERATED { min5(0), min10(1), min20(2), min30(3), min60(4), 
      min120(5), min180(6), spare1(7) } OPTIONAL,
   ...,
   [[
      freqPriorityListExtEUTRA-r12 [7] FreqPriorityListExtEUTRA-r12 OPTIONAL
   ]],
   [[
      freqPriorityListEUTRA-v1310 [8] FreqPriorityListEUTRA-v1310 OPTIONAL,
      freqPriorityListExtEUTRA-v1310 [9] FreqPriorityListExtEUTRA-v1310
          OPTIONAL
   ]],
   [[
      freqPriorityListNR-r15 [10] FreqPriorityListNR-r15 OPTIONAL
   ]]
}

FreqPriorityEUTRA-v9e0 ::= SEQUENCE {
   carrierFreq-v9e0 [0] ARFCN-ValueEUTRA-v9e0 OPTIONAL -- Cond EARFCN-max
}

IdleModeMobilityControlInfo-v9e0 ::= SEQUENCE {
   freqPriorityListEUTRA-v9e0 [0] SEQUENCE (SIZE (1..maxFreq)) OF 
      FreqPriorityEUTRA-v9e0
}

CarrierFreqCDMA2000 ::= SEQUENCE {
   bandClass [0] BandclassCDMA2000,
   arfcn [1] ARFCN-ValueCDMA2000
}

CarrierFreqListUTRA-TDD-r10 ::= SEQUENCE (SIZE (1..maxFreqUTRA-TDD-r10)) OF ARFCN-ValueUTRA

RedirectedCarrierInfo-r15-IEs ::= CHOICE {
   eutra-r15 [0] ARFCN-ValueEUTRA-r9,
   geran-r15 [1] CarrierFreqsGERAN,
   utra-FDD-r15 [2] ARFCN-ValueUTRA,
   cdma2000-HRPD-r15 [3] CarrierFreqCDMA2000,
   cdma2000-1xRTT-r15 [4] CarrierFreqCDMA2000,
   utra-TDD-r15 [5] CarrierFreqListUTRA-TDD-r10
}

RRCEarlyDataComplete-r15-IEs ::= SEQUENCE {
   dedicatedInfoNAS-r15 [0] DedicatedInfoNAS OPTIONAL, -- Need ON
   extendedWaitTime-r15 [1] INTEGER (1..1800) OPTIONAL, -- Need ON
   idleModeMobilityControlInfo-r15 [2] IdleModeMobilityControlInfo OPTIONAL, -- Need OP
   idleModeMobilityControlInfoExt-r15 [3] IdleModeMobilityControlInfo-v9e0
       OPTIONAL, -- Cond IdleInfoEUTRA
   redirectedCarrierInfo-r15 [4] EXPLICIT RedirectedCarrierInfo-r15-IEs
       OPTIONAL, -- Need ON
   nonCriticalExtension [5] SEQUENCE {

   } OPTIONAL
}

RRCEarlyDataComplete-r15 ::= SEQUENCE {
   criticalExtensions [0] EXPLICIT CHOICE {
      rrcEarlyDataComplete-r15 [0] RRCEarlyDataComplete-r15-IEs,
      criticalExtensionsFuture [1] SEQUENCE {

      }
   }
}

DL-CCCH-MessageType ::= CHOICE {
   c1 [0] EXPLICIT CHOICE {
      rrcConnectionReestablishment [0] RRCConnectionReestablishment,
      rrcConnectionReestablishmentReject [1] RRCConnectionReestablishmentReject
         ,
      rrcConnectionReject [2] RRCConnectionReject,
      rrcConnectionSetup [3] RRCConnectionSetup
   },
   messageClassExtension [1] EXPLICIT CHOICE {
      c2 [0] EXPLICIT CHOICE {
         rrcEarlyDataComplete-r15 [0] RRCEarlyDataComplete-r15,
         spare3 [1] NULL,
         spare2 [2] NULL,
         spare1 [3] NULL
      },
      messageClassExtensionFuture-r15 [1] SEQUENCE {

      }
   }
}

DL-CCCH-Message ::= SEQUENCE {
   message [0] EXPLICIT DL-CCCH-MessageType
}

CSFBParametersResponseCDMA2000-v8a0-IEs ::= SEQUENCE {
   lateNonCriticalExtension [0] OCTET STRING OPTIONAL,
   nonCriticalExtension [1] SEQUENCE {

   } OPTIONAL
}

CSFBParametersResponseCDMA2000-r8-IEs ::= SEQUENCE {
   rand [0] RAND-CDMA2000,
   mobilityParameters [1] MobilityParametersCDMA2000,
   nonCriticalExtension [2] CSFBParametersResponseCDMA2000-v8a0-IEs OPTIONAL
}

CSFBParametersResponseCDMA2000 ::= SEQUENCE {
   rrc-TransactionIdentifier [0] RRC-TransactionIdentifier,
   criticalExtensions [1] EXPLICIT CHOICE {
      csfbParametersResponseCDMA2000-r8 [0] 
         CSFBParametersResponseCDMA2000-r8-IEs,
      criticalExtensionsFuture [1] SEQUENCE {

      }
   }
}

DLInformationTransfer-v8a0-IEs ::= SEQUENCE {
   lateNonCriticalExtension [0] OCTET STRING OPTIONAL,
   nonCriticalExtension [1] SEQUENCE {

   } OPTIONAL
}

DLInformationTransfer-r8-IEs ::= SEQUENCE {
   dedicatedInfoType [0] EXPLICIT CHOICE {
      dedicatedInfoNAS [0] DedicatedInfoNAS,
      dedicatedInfoCDMA2000-1XRTT [1] DedicatedInfoCDMA2000,
      dedicatedInfoCDMA2000-HRPD [2] DedicatedInfoCDMA2000
   },
   nonCriticalExtension [1] DLInformationTransfer-v8a0-IEs OPTIONAL
}

DLInformationTransfer-r15-IEs ::= SEQUENCE {
   dedicatedInfoType-r15 [0] EXPLICIT CHOICE {
      dedicatedInfoNAS-r15 [0] DedicatedInfoNAS,
      dedicatedInfoCDMA2000-1XRTT-r15 [1] DedicatedInfoCDMA2000,
      dedicatedInfoCDMA2000-HRPD-r15 [2] DedicatedInfoCDMA2000
   } OPTIONAL, -- Need ON
   timeReferenceInfo-r15 [1] TimeReferenceInfo-r15 OPTIONAL, -- Need ON
   nonCriticalExtension [2] DLInformationTransfer-v8a0-IEs OPTIONAL
}

DLInformationTransfer ::= SEQUENCE {
   rrc-TransactionIdentifier [0] RRC-TransactionIdentifier,
   criticalExtensions [1] EXPLICIT CHOICE {
      c1 [0] EXPLICIT CHOICE {
         dlInformationTransfer-r8 [0] DLInformationTransfer-r8-IEs,
         dlInformationTransfer-r15 [1] DLInformationTransfer-r15-IEs,
         spare2 [2] NULL,
         spare1 [3] NULL
      },
      criticalExtensionsFuture [1] SEQUENCE {

      }
   }
}

HandoverFromEUTRAPreparationRequest-v1020-IEs ::= SEQUENCE {
   dualRxTxRedirectIndicator-r10 [0] ENUMERATED { true(0) } OPTIONAL, -- Cond cdma2000-1XRTT
   redirectCarrierCDMA2000-1XRTT-r10 [1] CarrierFreqCDMA2000 OPTIONAL, -- Cond dualRxTxRedirect
   nonCriticalExtension [2] SEQUENCE {

   } OPTIONAL
}

HandoverFromEUTRAPreparationRequest-v920-IEs ::= SEQUENCE {
   concurrPrepCDMA2000-HRPD-r9 [0] BOOLEAN OPTIONAL, -- Cond cdma2000-Type
   nonCriticalExtension [1] HandoverFromEUTRAPreparationRequest-v1020-IEs
       OPTIONAL
}

HandoverFromEUTRAPreparationRequest-v890-IEs ::= SEQUENCE {
   lateNonCriticalExtension [0] OCTET STRING OPTIONAL,
   nonCriticalExtension [1] HandoverFromEUTRAPreparationRequest-v920-IEs
       OPTIONAL
}

HandoverFromEUTRAPreparationRequest-r8-IEs ::= SEQUENCE {
   cdma2000-Type [0] CDMA2000-Type,
   rand [1] RAND-CDMA2000 OPTIONAL, -- Cond cdma2000-Type
   mobilityParameters [2] MobilityParametersCDMA2000 OPTIONAL, -- Cond cdma2000-Type
   nonCriticalExtension [3] HandoverFromEUTRAPreparationRequest-v890-IEs
       OPTIONAL
}

HandoverFromEUTRAPreparationRequest ::= SEQUENCE {
   rrc-TransactionIdentifier [0] RRC-TransactionIdentifier,
   criticalExtensions [1] EXPLICIT CHOICE {
      c1 [0] EXPLICIT CHOICE {
         handoverFromEUTRAPreparationRequest-r8 [0] 
            HandoverFromEUTRAPreparationRequest-r8-IEs,
         spare3 [1] NULL,
         spare2 [2] NULL,
         spare1 [3] NULL
      },
      criticalExtensionsFuture [1] SEQUENCE {

      }
   }
}

SystemInfoListGERAN ::= SEQUENCE (SIZE (1..maxGERAN-SI)) OF OCTET STRING (SIZE (1..23))

SI-OrPSI-GERAN ::= CHOICE {
   si [0] SystemInfoListGERAN,
   psi [1] SystemInfoListGERAN
}

Handover ::= SEQUENCE {
   targetRAT-Type [0] ENUMERATED { utra(0), geran(1), cdma2000-1XRTT(2), 
      cdma2000-HRPD(3), nr(4), eutra(5), spare2(6), spare1(7), ... },
   targetRAT-MessageContainer [1] OCTET STRING,
   nas-SecurityParamFromEUTRA [2] OCTET STRING (SIZE (1)) OPTIONAL, -- Cond UTRAGERANEPC
   systemInformation [3] EXPLICIT SI-OrPSI-GERAN OPTIONAL -- Cond PSHO
}

PhysCellIdGERAN ::= SEQUENCE {
   networkColourCode [0] BIT STRING  (SIZE (3)),
   baseStationColourCode [1] BIT STRING  (SIZE (3))
}

CarrierFreqGERAN ::= SEQUENCE {
   arfcn [0] ARFCN-ValueGERAN,
   bandIndicator [1] BandIndicatorGERAN
}

CellChangeOrder ::= SEQUENCE {
   t304 [0] ENUMERATED { ms100(0), ms200(1), ms500(2), ms1000(3), ms2000(4), 
      ms4000(5), ms8000(6), ms10000-v1310(7) },
   targetRAT-Type [1] EXPLICIT CHOICE {
      geran [0] SEQUENCE {
         physCellId [0] PhysCellIdGERAN,
         carrierFreq [1] CarrierFreqGERAN,
         networkControlOrder [2] BIT STRING  (SIZE (2)) OPTIONAL, -- Need OP
         systemInformation [3] EXPLICIT SI-OrPSI-GERAN OPTIONAL -- Need OP
      },
      ...
   }
}

MobilityFromEUTRACommand-v8d0-IEs ::= SEQUENCE {
   bandIndicator [0] BandIndicatorGERAN OPTIONAL, -- Cond GERAN
   nonCriticalExtension [1] SEQUENCE {

   } OPTIONAL
}

MobilityFromEUTRACommand-v8a0-IEs ::= SEQUENCE {
   lateNonCriticalExtension [0] OCTET STRING OPTIONAL,
   nonCriticalExtension [1] MobilityFromEUTRACommand-v8d0-IEs OPTIONAL
}

MobilityFromEUTRACommand-r8-IEs ::= SEQUENCE {
   cs-FallbackIndicator [0] BOOLEAN,
   purpose [1] EXPLICIT CHOICE {
      handover [0] Handover,
      cellChangeOrder [1] CellChangeOrder
   },
   nonCriticalExtension [2] MobilityFromEUTRACommand-v8a0-IEs OPTIONAL
}

E-CSFB-r9 ::= SEQUENCE {
   messageContCDMA2000-1XRTT-r9 [0] OCTET STRING OPTIONAL, -- Need ON
   mobilityCDMA2000-HRPD-r9 [1] ENUMERATED { handover(0), redirection(1) }
       OPTIONAL, -- Need OP
   messageContCDMA2000-HRPD-r9 [2] OCTET STRING OPTIONAL, -- Cond concHO
   redirectCarrierCDMA2000-HRPD-r9 [3] CarrierFreqCDMA2000 OPTIONAL -- Cond concRedir
}

MobilityFromEUTRACommand-v1530-IEs ::= SEQUENCE {
   smtc-r15 [0] MTC-SSB-NR-r15 OPTIONAL, -- Need OP
   nonCriticalExtension [1] SEQUENCE {

   } OPTIONAL
}

MobilityFromEUTRACommand-v960-IEs ::= SEQUENCE {
   bandIndicator [0] BandIndicatorGERAN OPTIONAL, -- Cond GERAN
   nonCriticalExtension [1] MobilityFromEUTRACommand-v1530-IEs OPTIONAL
}

MobilityFromEUTRACommand-v930-IEs ::= SEQUENCE {
   lateNonCriticalExtension [0] OCTET STRING OPTIONAL,
   nonCriticalExtension [1] MobilityFromEUTRACommand-v960-IEs OPTIONAL
}

MobilityFromEUTRACommand-r9-IEs ::= SEQUENCE {
   cs-FallbackIndicator [0] BOOLEAN,
   purpose [1] EXPLICIT CHOICE {
      handover [0] Handover,
      cellChangeOrder [1] CellChangeOrder,
      e-CSFB-r9 [2] E-CSFB-r9,
      ...
   },
   nonCriticalExtension [2] MobilityFromEUTRACommand-v930-IEs OPTIONAL
}

MobilityFromEUTRACommand ::= SEQUENCE {
   rrc-TransactionIdentifier [0] RRC-TransactionIdentifier,
   criticalExtensions [1] EXPLICIT CHOICE {
      c1 [0] EXPLICIT CHOICE {
         mobilityFromEUTRACommand-r8 [0] MobilityFromEUTRACommand-r8-IEs,
         mobilityFromEUTRACommand-r9 [1] MobilityFromEUTRACommand-r9-IEs,
         spare2 [2] NULL,
         spare1 [3] NULL
      },
      criticalExtensionsFuture [1] SEQUENCE {

      }
   }
}

MeasObjectToRemoveList ::= SEQUENCE (SIZE (1..maxObjectId)) OF MeasObjectId

CellIndexList ::= SEQUENCE (SIZE (1..maxCellMeas)) OF CellIndex

CellsToAddMod ::= SEQUENCE {
   cellIndex [0] INTEGER (1..maxCellMeas),
   physCellId [1] PhysCellId,
   cellIndividualOffset [2] Q-OffsetRange
}

CellsToAddModList ::= SEQUENCE (SIZE (1..maxCellMeas)) OF CellsToAddMod

BlackCellsToAddMod ::= SEQUENCE {
   cellIndex [0] INTEGER (1..maxCellMeas),
   physCellIdRange [1] PhysCellIdRange
}

BlackCellsToAddModList ::= SEQUENCE (SIZE (1..maxCellMeas)) OF BlackCellsToAddMod

MeasSubframeCellList-r10 ::= SEQUENCE (SIZE (1..maxCellMeas)) OF PhysCellIdRange

MeasSubframePatternConfigNeigh-r10 ::= CHOICE {
   release [0] NULL,
   setup [1] SEQUENCE {
      measSubframePatternNeigh-r10 [0] EXPLICIT MeasSubframePattern-r10,
      measSubframeCellList-r10 [1] MeasSubframeCellList-r10 OPTIONAL -- Cond always
   }
}

AltTTT-CellsToAddMod-r12 ::= SEQUENCE {
   cellIndex-r12 [0] INTEGER (1..maxCellMeas),
   physCellIdRange-r12 [1] PhysCellIdRange
}

AltTTT-CellsToAddModList-r12 ::= SEQUENCE (SIZE (1..maxCellMeas)) OF 
   AltTTT-CellsToAddMod-r12

MeasCSI-RS-ToRemoveList-r12 ::= SEQUENCE (SIZE (1..maxCSI-RS-Meas-r12)) OF MeasCSI-RS-Id-r12

MeasCSI-RS-Config-r12 ::= SEQUENCE {
   measCSI-RS-Id-r12 [0] MeasCSI-RS-Id-r12,
   physCellId-r12 [1] INTEGER (0..503),
   scramblingIdentity-r12 [2] INTEGER (0..503),
   resourceConfig-r12 [3] INTEGER (0..31),
   subframeOffset-r12 [4] INTEGER (0..4),
   csi-RS-IndividualOffset-r12 [5] Q-OffsetRange,
   ...
}

MeasCSI-RS-ToAddModList-r12 ::= SEQUENCE (SIZE (1..maxCSI-RS-Meas-r12)) OF MeasCSI-RS-Config-r12

MeasDS-Config-r12 ::= CHOICE {
   release [0] NULL,
   setup [1] SEQUENCE {
      dmtc-PeriodOffset-r12 [0] EXPLICIT CHOICE {
         ms40-r12 [0] INTEGER (0..39),
         ms80-r12 [1] INTEGER (0..79),
         ms160-r12 [2] INTEGER (0..159),
         ...
      },
      ds-OccasionDuration-r12 [1] EXPLICIT CHOICE {
         durationFDD-r12 [0] INTEGER (1..maxDS-Duration-r12),
         durationTDD-r12 [1] INTEGER (2..maxDS-Duration-r12)
      },
      measCSI-RS-ToRemoveList-r12 [2] MeasCSI-RS-ToRemoveList-r12 OPTIONAL, -- Need ON
      measCSI-RS-ToAddModList-r12 [3] MeasCSI-RS-ToAddModList-r12 OPTIONAL,
      ...
   }
}

WhiteCellsToAddMod-r13 ::= SEQUENCE {
   cellIndex-r13 [0] INTEGER (1..maxCellMeas),
   physCellIdRange-r13 [1] PhysCellIdRange
}

WhiteCellsToAddModList-r13 ::= SEQUENCE (SIZE (1..maxCellMeas)) OF WhiteCellsToAddMod-r13

RMTC-Config-r13 ::= CHOICE {
   release [0] NULL,
   setup [1] SEQUENCE {
      rmtc-Period-r13 [0] ENUMERATED { ms40(0), ms80(1), ms160(2), ms320(3), 
         ms640(4) },
      rmtc-SubframeOffset-r13 [1] INTEGER (0..639) OPTIONAL, -- Need ON
      measDuration-r13 [2] ENUMERATED { sym1(0), sym14(1), sym28(2), sym42(3), 
         sym70(4) },
      ...
   }
}

Tx-ResourcePoolMeasList-r14 ::= SEQUENCE (SIZE (1..maxSL-PoolToMeasure-r14)) OF 
   SL-V2X-TxPoolReportIdentity-r14

MeasSensing-Config-r15 ::= SEQUENCE {
   sensingSubchannelNumber-r15 [0] INTEGER (1..20),
   sensingPeriodicity-r15 [1] ENUMERATED { ms20(0), ms50(1), ms100(2), ms200(3)
      , ms300(4), ms400(5), ms500(6), ms600(7), ms700(8), ms800(9), ms900(10), 
      ms1000(11) },
   sensingReselectionCounter-r15 [2] INTEGER (5..75),
   sensingPriority-r15 [3] INTEGER (1..8)
}

MeasObjectEUTRA ::= SEQUENCE {
   carrierFreq [0] ARFCN-ValueEUTRA,
   allowedMeasBandwidth [1] AllowedMeasBandwidth,
   presenceAntennaPort1 [2] PresenceAntennaPort1,
   neighCellConfig [3] NeighCellConfig,
   offsetFreq [4] Q-OffsetRange DEFAULT dB0,
--Cell list
   cellsToRemoveList [5] CellIndexList OPTIONAL, -- Need ON
   cellsToAddModList [6] CellsToAddModList OPTIONAL, -- Need ON
--Black list
   blackCellsToRemoveList [7] CellIndexList OPTIONAL, -- Need ON
   blackCellsToAddModList [8] BlackCellsToAddModList OPTIONAL, -- Need ON
   cellForWhichToReportCGI [9] PhysCellId OPTIONAL,
   ...,
   [[
      measCycleSCell-r10 [10] MeasCycleSCell-r10 OPTIONAL,
      measSubframePatternConfigNeigh-r10 [11] EXPLICIT 
         MeasSubframePatternConfigNeigh-r10 OPTIONAL
   ]],
   [[
      widebandRSRQ-Meas-r11 [12] BOOLEAN OPTIONAL
   ]],
   [[
      altTTT-CellsToRemoveList-r12 [13] CellIndexList OPTIONAL,
      altTTT-CellsToAddModList-r12 [14] AltTTT-CellsToAddModList-r12 OPTIONAL,
      t312-r12 [15] EXPLICIT CHOICE {
         release [0] NULL,
         setup [1] ENUMERATED { ms0(0), ms50(1), ms100(2), ms200(3), ms300(4), 
            ms400(5), ms500(6), ms1000(7) }
      } OPTIONAL,
      reducedMeasPerformance-r12 [16] BOOLEAN OPTIONAL,
      measDS-Config-r12 [17] EXPLICIT MeasDS-Config-r12 OPTIONAL
   ]],
   [[
      whiteCellsToRemoveList-r13 [18] CellIndexList OPTIONAL,
      whiteCellsToAddModList-r13 [19] WhiteCellsToAddModList-r13 OPTIONAL,
      rmtc-Config-r13 [20] EXPLICIT RMTC-Config-r13 OPTIONAL,
      carrierFreq-r13 [21] ARFCN-ValueEUTRA-v9e0 OPTIONAL
   ]],
   [[
      tx-ResourcePoolToRemoveList-r14 [22] Tx-ResourcePoolMeasList-r14 OPTIONAL
         ,
      tx-ResourcePoolToAddList-r14 [23] Tx-ResourcePoolMeasList-r14 OPTIONAL,
      fembms-MixedCarrier-r14 [24] BOOLEAN OPTIONAL
   ]],
   [[
      measSensing-Config-r15 [25] MeasSensing-Config-r15 OPTIONAL
   ]]
}

CellsToAddModUTRA-FDD ::= SEQUENCE {
   cellIndex [0] INTEGER (1..maxCellMeas),
   physCellId [1] PhysCellIdUTRA-FDD
}

CellsToAddModListUTRA-FDD ::= SEQUENCE (SIZE (1..maxCellMeas)) OF CellsToAddModUTRA-FDD

CellsToAddModUTRA-TDD ::= SEQUENCE {
   cellIndex [0] INTEGER (1..maxCellMeas),
   physCellId [1] PhysCellIdUTRA-TDD
}

CellsToAddModListUTRA-TDD ::= SEQUENCE (SIZE (1..maxCellMeas)) OF CellsToAddModUTRA-TDD

PhysCellIdRangeUTRA-FDD-r9 ::= SEQUENCE {
   start-r9 [0] PhysCellIdUTRA-FDD,
   range-r9 [1] INTEGER (2..512) OPTIONAL -- Need OP
}

PhysCellIdRangeUTRA-FDDList-r9 ::= SEQUENCE (SIZE (1..maxPhysCellIdRange-r9)) OF 
   PhysCellIdRangeUTRA-FDD-r9

CSG-AllowedReportingCells-r9 ::= SEQUENCE {
   physCellIdRangeUTRA-FDDList-r9 [0] PhysCellIdRangeUTRA-FDDList-r9 OPTIONAL -- Need OR
}

MeasObjectUTRA ::= SEQUENCE {
   carrierFreq [0] ARFCN-ValueUTRA,
   offsetFreq [1] Q-OffsetRangeInterRAT DEFAULT 0,
   cellsToRemoveList [2] CellIndexList OPTIONAL, -- Need ON
   cellsToAddModList [3] EXPLICIT CHOICE {
      cellsToAddModListUTRA-FDD [0] CellsToAddModListUTRA-FDD,
      cellsToAddModListUTRA-TDD [1] CellsToAddModListUTRA-TDD
   } OPTIONAL, -- Need ON
   cellForWhichToReportCGI [4] EXPLICIT CHOICE {
      utra-FDD [0] PhysCellIdUTRA-FDD,
      utra-TDD [1] PhysCellIdUTRA-TDD
   } OPTIONAL,
   ...,
   [[
      csg-allowedReportingCells-v930 [5] CSG-AllowedReportingCells-r9 OPTIONAL
   ]],
   [[
      reducedMeasPerformance-r12 [6] BOOLEAN OPTIONAL
   ]]
}

MeasObjectGERAN ::= SEQUENCE {
   carrierFreqs [0] CarrierFreqsGERAN,
   offsetFreq [1] Q-OffsetRangeInterRAT DEFAULT 0,
   ncc-Permitted [2] BIT STRING  (SIZE (8)) DEFAULT '11111111'B,
   cellForWhichToReportCGI [3] PhysCellIdGERAN OPTIONAL,
   ...
}

CellsToAddModCDMA2000 ::= SEQUENCE {
   cellIndex [0] INTEGER (1..maxCellMeas),
   physCellId [1] PhysCellIdCDMA2000
}

CellsToAddModListCDMA2000 ::= SEQUENCE (SIZE (1..maxCellMeas)) OF CellsToAddModCDMA2000

MeasObjectCDMA2000 ::= SEQUENCE {
   cdma2000-Type [0] CDMA2000-Type,
   carrierFreq [1] CarrierFreqCDMA2000,
   searchWindowSize [2] INTEGER (0..15) OPTIONAL, -- Need ON
   offsetFreq [3] Q-OffsetRangeInterRAT DEFAULT 0,
   cellsToRemoveList [4] CellIndexList OPTIONAL, -- Need ON
   cellsToAddModList [5] CellsToAddModListCDMA2000 OPTIONAL, -- Need ON
   cellForWhichToReportCGI [6] PhysCellIdCDMA2000 OPTIONAL,
   ...
}

WLAN-ChannelList-r13 ::= SEQUENCE (SIZE (1..maxWLAN-Channels-r13)) OF WLAN-Channel-r13

WLAN-CarrierInfo-r13 ::= SEQUENCE {
   operatingClass-r13 [0] INTEGER (0..255) OPTIONAL, -- Need ON
   countryCode-r13 [1] ENUMERATED { unitedStates(0), europe(1), japan(2), 
      global(3), ... } OPTIONAL,
                       -- Need ON
   channelNumbers-r13 [2] WLAN-ChannelList-r13 OPTIONAL,
   ...
}

WLAN-Id-List-r13 ::= SEQUENCE (SIZE (1..maxWLAN-Id-r13)) OF WLAN-Identifiers-r12

MeasObjectWLAN-r13 ::= SEQUENCE {
   carrierFreq-r13 [0] EXPLICIT CHOICE {
      bandIndicatorListWLAN-r13 [0] SEQUENCE (SIZE (1..maxWLAN-Bands-r13)) OF 
         WLAN-BandIndicator-r13,
      carrierInfoListWLAN-r13 [1] SEQUENCE (SIZE (1..maxWLAN-CarrierInfo-r13)) OF WLAN-CarrierInfo-r13
   } OPTIONAL, -- Need ON
   wlan-ToAddModList-r13 [1] WLAN-Id-List-r13 OPTIONAL, -- Need ON
   wlan-ToRemoveList-r13 [2] WLAN-Id-List-r13 OPTIONAL,
   ...
}

RS-ConfigSSB-NR-r15 ::= SEQUENCE {
   measTimingConfig-r15 [0] MTC-SSB-NR-r15,
   subcarrierSpacingSSB-r15 [1] ENUMERATED { kHz15(0), kHz30(1), kHz120(2), 
      kHz240(3) },
   ...,
   [[
      ssb-ToMeasure-r15 [2] EXPLICIT CHOICE {
         release [0] NULL,
         setup [1] EXPLICIT SSB-ToMeasure-r15
      } OPTIONAL
   ]]
}

CellsToAddModNR-r15 ::= SEQUENCE {
   cellIndex-r15 [0] INTEGER (1..maxCellMeas),
   physCellId-r15 [1] PhysCellIdNR-r15
}

CellsToAddModListNR-r15 ::= SEQUENCE (SIZE (1..maxCellMeas)) OF CellsToAddModNR-r15

MeasObjectNR-r15 ::= SEQUENCE {
   carrierFreq-r15 [0] ARFCN-ValueNR-r15,
   rs-ConfigSSB-r15 [1] RS-ConfigSSB-NR-r15,
   threshRS-Index-r15 [2] ThresholdListNR-r15 OPTIONAL, -- Need OR
   maxRS-IndexCellQual-r15 [3] MaxRS-IndexCellQualNR-r15 OPTIONAL, -- Need OR
   offsetFreq-r15 [4] Q-OffsetRangeInterRAT DEFAULT 0,
   blackCellsToRemoveList-r15 [5] CellIndexList OPTIONAL, -- Need ON
   blackCellsToAddModList-r15 [6] CellsToAddModListNR-r15 OPTIONAL, -- Need ON
   quantityConfigSet-r15 [7] INTEGER (1..maxQuantSetsNR-r15),
   cellsForWhichToReportSFTD-r15 [8] SEQUENCE (SIZE (1..maxCellSFTD)) OF PhysCellIdNR-r15
       OPTIONAL,
   ...,
   [[
      cellForWhichToReportCGI-r15 [9] PhysCellIdNR-r15 OPTIONAL,
      deriveSSB-IndexFromCell-r15 [10] BOOLEAN OPTIONAL,
      ss-RSSI-Measurement-r15 [11] SS-RSSI-Measurement-r15 OPTIONAL,
      bandNR-r15 [12] EXPLICIT CHOICE {
         release [0] NULL,
         setup [1] FreqBandIndicatorNR-r15
      } OPTIONAL
   ]]
}

MeasObjectToAddMod ::= SEQUENCE {
   measObjectId [0] MeasObjectId,
   measObject [1] EXPLICIT CHOICE {
      measObjectEUTRA [0] MeasObjectEUTRA,
      measObjectUTRA [1] MeasObjectUTRA,
      measObjectGERAN [2] MeasObjectGERAN,
      measObjectCDMA2000 [3] MeasObjectCDMA2000,
      ...,
      measObjectWLAN-r13 [4] MeasObjectWLAN-r13,
      measObjectNR-r15 [5] MeasObjectNR-r15
   }
}

MeasObjectToAddModList ::= SEQUENCE (SIZE (1..maxObjectId)) OF MeasObjectToAddMod

ReportConfigToRemoveList ::= SEQUENCE (SIZE (1..maxReportConfigId)) OF ReportConfigId

ThresholdEUTRA ::= CHOICE {
   threshold-RSRP [0] RSRP-Range,
   threshold-RSRQ [1] RSRQ-Range
}

RSRQ-RangeConfig-r12 ::= CHOICE {
   release [0] NULL,
   setup [1] RSRQ-Range-v1250
}

MeasRSSI-ReportConfig-r13 ::= SEQUENCE {
   channelOccupancyThreshold-r13 [0] RSSI-Range-r13 OPTIONAL -- Need OR
}

UL-DelayConfig-r13 ::= CHOICE {
   release [0] NULL,
   setup [1] SEQUENCE {
      delayThreshold-r13 [0] ENUMERATED { ms30(0), ms40(1), ms50(2), ms60(3), 
         ms70(4), ms80(5), ms90(6), ms100(7), ms150(8), ms300(9), ms500(10), 
         ms750(11), spare4(12), spare3(13), spare2(14), spare1(15) }
   }
}

BT-NameList-r15 ::= SEQUENCE (SIZE (1..maxBT-Name-r15)) OF BT-Name-r15

BT-NameListConfig-r15 ::= CHOICE {
   release [0] NULL,
   setup [1] BT-NameList-r15
}

WLAN-NameList-r15 ::= SEQUENCE (SIZE (1..maxWLAN-Name-r15)) OF WLAN-Name-r15

WLAN-NameListConfig-r15 ::= CHOICE {
   release [0] NULL,
   setup [1] WLAN-NameList-r15
}

ReportConfigEUTRA ::= SEQUENCE {
   triggerType [0] EXPLICIT CHOICE {
      event [0] SEQUENCE {
         eventId [0] EXPLICIT CHOICE {
            eventA1 [0] SEQUENCE {
               a1-Threshold [0] EXPLICIT ThresholdEUTRA
            },
            eventA2 [1] SEQUENCE {
               a2-Threshold [0] EXPLICIT ThresholdEUTRA
            },
            eventA3 [2] SEQUENCE {
               a3-Offset [0] INTEGER (-30..30),
               reportOnLeave [1] BOOLEAN
            },
            eventA4 [3] SEQUENCE {
               a4-Threshold [0] EXPLICIT ThresholdEUTRA
            },
            eventA5 [4] SEQUENCE {
               a5-Threshold1 [0] EXPLICIT ThresholdEUTRA,
               a5-Threshold2 [1] EXPLICIT ThresholdEUTRA
            },
            ...,
            eventA6-r10 [5] SEQUENCE {
               a6-Offset-r10 [0] INTEGER (-30..30),
               a6-ReportOnLeave-r10 [1] BOOLEAN
            },
            eventC1-r12 [6] SEQUENCE {
               c1-Threshold-r12 [0] ThresholdEUTRA-v1250,
               c1-ReportOnLeave-r12 [1] BOOLEAN
            },
            eventC2-r12 [7] SEQUENCE {
               c2-RefCSI-RS-r12 [0] MeasCSI-RS-Id-r12,
               c2-Offset-r12 [1] INTEGER (-30..30),
               c2-ReportOnLeave-r12 [2] BOOLEAN
            },
            eventV1-r14 [8] SEQUENCE {
               v1-Threshold-r14 [0] SL-CBR-r14
            },
            eventV2-r14 [9] SEQUENCE {
               v2-Threshold-r14 [0] SL-CBR-r14
            },
            eventH1-r15 [10] SEQUENCE {
               h1-ThresholdOffset-r15 [0] INTEGER (0..300),
               h1-Hysteresis-15 [1] INTEGER (1..16)
            },
            eventH2-r15 [11] SEQUENCE {
               h2-ThresholdOffset-r15 [0] INTEGER (0..300),
               h2-Hysteresis-15 [1] INTEGER (1..16)
            }
         },
         hysteresis [1] Hysteresis,
         timeToTrigger [2] TimeToTrigger
      },
      periodical [1] SEQUENCE {
         purpose [0] ENUMERATED { reportStrongestCells(0), reportCGI(1) }
      }
   },
   triggerQuantity [1] ENUMERATED { rsrp(0), rsrq(1) },
   reportQuantity [2] ENUMERATED { sameAsTriggerQuantity(0), both(1) },
   maxReportCells [3] INTEGER (1..maxCellReport),
   reportInterval [4] ReportInterval,
   reportAmount [5] ENUMERATED { r1(0), r2(1), r4(2), r8(3), r16(4), r32(5), 
      r64(6), infinity(7) },
   ...,
   [[
      si-RequestForHO-r9 [6] ENUMERATED { setup(0) } OPTIONAL,
      ue-RxTxTimeDiffPeriodical-r9 [7] ENUMERATED { setup(0) } OPTIONAL
   ]],
   [[
      includeLocationInfo-r10 [8] ENUMERATED { true(0) } OPTIONAL,
      reportAddNeighMeas-r10 [9] ENUMERATED { setup(0) } OPTIONAL
   ]],
   [[
      alternativeTimeToTrigger-r12 [10] EXPLICIT CHOICE {
         release [0] NULL,
         setup [1] TimeToTrigger
      } OPTIONAL,
      useT312-r12 [11] BOOLEAN OPTIONAL,
      usePSCell-r12 [12] BOOLEAN OPTIONAL,
      aN-Threshold1-v1250 [13] EXPLICIT RSRQ-RangeConfig-r12 OPTIONAL,
      a5-Threshold2-v1250 [14] EXPLICIT RSRQ-RangeConfig-r12 OPTIONAL,
      reportStrongestCSI-RSs-r12 [15] BOOLEAN OPTIONAL,
      reportCRS-Meas-r12 [16] BOOLEAN OPTIONAL,
      triggerQuantityCSI-RS-r12 [17] BOOLEAN OPTIONAL
   ]],
   [[
      reportSSTD-Meas-r13 [18] BOOLEAN OPTIONAL,
      rs-sinr-Config-r13 [19] EXPLICIT CHOICE {
         release [0] NULL,
         setup [1] SEQUENCE {
            triggerQuantity-v1310 [0] ENUMERATED { sinr(0) } OPTIONAL, -- Need ON
            aN-Threshold1-r13 [1] RS-SINR-Range-r13 OPTIONAL, -- Need ON
            a5-Threshold2-r13 [2] RS-SINR-Range-r13 OPTIONAL, -- Need ON
            reportQuantity-v1310 [3] ENUMERATED { rsrpANDsinr(0), 
               rsrqANDsinr(1), all(2) }
         }
      } OPTIONAL,
      useWhiteCellList-r13 [20] BOOLEAN OPTIONAL,
      measRSSI-ReportConfig-r13 [21] MeasRSSI-ReportConfig-r13 OPTIONAL,
      includeMultiBandInfo-r13 [22] ENUMERATED { true(0) } OPTIONAL,
      ul-DelayConfig-r13 [23] EXPLICIT UL-DelayConfig-r13 OPTIONAL
   ]],
   [[
      ue-RxTxTimeDiffPeriodicalTDD-r13 [24] BOOLEAN OPTIONAL
   ]],
   [[
      purpose-v1430 [25] ENUMERATED { reportLocation(0), sidelink(1), spare2(2)
         , spare1(3) } OPTIONAL
   ]],
   [[
      maxReportRS-Index-r15 [26] INTEGER (0..maxRS-IndexReport-r15) OPTIONAL
   ]],
   [[
      includeBT-Meas-r15 [27] EXPLICIT BT-NameListConfig-r15 OPTIONAL,
      includeWLAN-Meas-r15 [28] EXPLICIT WLAN-NameListConfig-r15 OPTIONAL,
      purpose-r15 [29] ENUMERATED { sensing(0) } OPTIONAL,
      numberOfTriggeringCells-r15 [30] INTEGER (2..maxCellReport) OPTIONAL,
      a4-a5-ReportOnLeave-r15 [31] BOOLEAN OPTIONAL
   ]]
}

ThresholdUTRA ::= CHOICE {
   utra-RSCP [0] INTEGER (-5..91),
   utra-EcN0 [1] INTEGER (0..49)
}

ThresholdNR-r15 ::= CHOICE {
   nr-RSRP-r15 [0] RSRP-RangeNR-r15,
   nr-RSRQ-r15 [1] RSRQ-RangeNR-r15,
   nr-SINR-r15 [2] RS-SINR-RangeNR-r15
}

ReportQuantityWLAN-r13 ::= SEQUENCE {
   bandRequestWLAN-r13 [0] ENUMERATED { true(0) } OPTIONAL, -- Need OR
   carrierInfoRequestWLAN-r13 [1] ENUMERATED { true(0) } OPTIONAL, -- Need OR
   availableAdmissionCapacityRequestWLAN-r13 [2] ENUMERATED { true(0) }
       OPTIONAL, -- Need OR
   backhaulDL-BandwidthRequestWLAN-r13 [3] ENUMERATED { true(0) } OPTIONAL, -- Need OR
   backhaulUL-BandwidthRequestWLAN-r13 [4] ENUMERATED { true(0) } OPTIONAL, -- Need OR
   channelUtilizationRequestWLAN-r13 [5] ENUMERATED { true(0) } OPTIONAL, -- Need OR
   stationCountRequestWLAN-r13 [6] ENUMERATED { true(0) } OPTIONAL,
   ...
}

ReportQuantityNR-r15 ::= SEQUENCE {
   ss-rsrp [0] BOOLEAN,
   ss-rsrq [1] BOOLEAN,
   ss-sinr [2] BOOLEAN
}

ReportConfigInterRAT ::= SEQUENCE {
   triggerType [0] EXPLICIT CHOICE {
      event [0] SEQUENCE {
         eventId [0] EXPLICIT CHOICE {
            eventB1 [0] SEQUENCE {
               b1-Threshold [0] EXPLICIT CHOICE {
                  b1-ThresholdUTRA [0] EXPLICIT ThresholdUTRA,
                  b1-ThresholdGERAN [1] ThresholdGERAN,
                  b1-ThresholdCDMA2000 [2] ThresholdCDMA2000
               }
            },
            eventB2 [1] SEQUENCE {
               b2-Threshold1 [0] EXPLICIT ThresholdEUTRA,
               b2-Threshold2 [1] EXPLICIT CHOICE {
                  b2-Threshold2UTRA [0] EXPLICIT ThresholdUTRA,
                  b2-Threshold2GERAN [1] ThresholdGERAN,
                  b2-Threshold2CDMA2000 [2] ThresholdCDMA2000
               }
            },
            ...,
            eventW1-r13 [2] SEQUENCE {
               w1-Threshold-r13 [0] WLAN-RSSI-Range-r13
            },
            eventW2-r13 [3] SEQUENCE {
               w2-Threshold1-r13 [0] WLAN-RSSI-Range-r13,
               w2-Threshold2-r13 [1] WLAN-RSSI-Range-r13
            },
            eventW3-r13 [4] SEQUENCE {
               w3-Threshold-r13 [0] WLAN-RSSI-Range-r13
            },
            eventB1-NR-r15 [5] SEQUENCE {
               b1-ThresholdNR-r15 [0] EXPLICIT ThresholdNR-r15,
               reportOnLeave-r15 [1] BOOLEAN
            },
            eventB2-NR-r15 [6] SEQUENCE {
               b2-Threshold1-r15 [0] EXPLICIT ThresholdEUTRA,
               b2-Threshold2NR-r15 [1] EXPLICIT ThresholdNR-r15,
               reportOnLeave-r15 [2] BOOLEAN
            }
         },
         hysteresis [1] Hysteresis,
         timeToTrigger [2] TimeToTrigger
      },
      periodical [1] SEQUENCE {
         purpose [0] ENUMERATED { reportStrongestCells(0), 
            reportStrongestCellsForSON(1), reportCGI(2) }
      }
   },
   maxReportCells [1] INTEGER (1..maxCellReport),
   reportInterval [2] ReportInterval,
   reportAmount [3] ENUMERATED { r1(0), r2(1), r4(2), r8(3), r16(4), r32(5), 
      r64(6), infinity(7) },
   ...,
   [[
      si-RequestForHO-r9 [4] ENUMERATED { setup(0) } OPTIONAL
   ]],
   [[
      reportQuantityUTRA-FDD-r10 [5] ENUMERATED { both(0) } OPTIONAL
   ]],
   [[
      includeLocationInfo-r11 [6] BOOLEAN OPTIONAL
   ]],
   [[
      b2-Threshold1-v1250 [7] EXPLICIT CHOICE {
         release [0] NULL,
         setup [1] RSRQ-Range-v1250
      } OPTIONAL
   ]],
   [[
      reportQuantityWLAN-r13 [8] ReportQuantityWLAN-r13 OPTIONAL
   ]],
   [[
      reportAnyWLAN-r14 [9] BOOLEAN OPTIONAL
   ]],
   [[
      reportQuantityCellNR-r15 [10] ReportQuantityNR-r15 OPTIONAL,
      maxReportRS-Index-r15 [11] INTEGER (0..maxRS-IndexReport-r15) OPTIONAL,
      reportQuantityRS-IndexNR-r15 [12] ReportQuantityNR-r15 OPTIONAL,
      reportRS-IndexResultsNR [13] BOOLEAN OPTIONAL,
      reportSFTD-Meas-r15 [14] ENUMERATED { pSCell(0), neighborCells(1) }
          OPTIONAL
   ]]
}

ReportConfigToAddMod ::= SEQUENCE {
   reportConfigId [0] ReportConfigId,
   reportConfig [1] EXPLICIT CHOICE {
      reportConfigEUTRA [0] ReportConfigEUTRA,
      reportConfigInterRAT [1] ReportConfigInterRAT
   }
}

ReportConfigToAddModList ::= SEQUENCE (SIZE (1..maxReportConfigId)) OF ReportConfigToAddMod

MeasIdToRemoveList ::= SEQUENCE (SIZE (1..maxMeasId)) OF MeasId

MeasIdToAddMod ::= SEQUENCE {
   measId [0] MeasId,
   measObjectId [1] MeasObjectId,
   reportConfigId [2] ReportConfigId
}

MeasIdToAddModList ::= SEQUENCE (SIZE (1..maxMeasId)) OF MeasIdToAddMod

QuantityConfigEUTRA ::= SEQUENCE {
   filterCoefficientRSRP [0] FilterCoefficient DEFAULT fc4,
   filterCoefficientRSRQ [1] FilterCoefficient DEFAULT fc4
}

QuantityConfigUTRA ::= SEQUENCE {
   measQuantityUTRA-FDD [0] ENUMERATED { cpich-RSCP(0), cpich-EcN0(1) },
   measQuantityUTRA-TDD [1] ENUMERATED { pccpch-RSCP(0) },
   filterCoefficient [2] FilterCoefficient DEFAULT fc4
}

QuantityConfigGERAN ::= SEQUENCE {
   measQuantityGERAN [0] ENUMERATED { rssi(0) },
   filterCoefficient [1] FilterCoefficient DEFAULT fc2
}

QuantityConfigCDMA2000 ::= SEQUENCE {
   measQuantityCDMA2000 [0] ENUMERATED { pilotStrength(0), 
      pilotPnPhaseAndPilotStrength(1) }
}

QuantityConfigUTRA-v1020 ::= SEQUENCE {
   filterCoefficient2-FDD-r10 [0] FilterCoefficient DEFAULT fc4
}

QuantityConfigEUTRA-v1250 ::= SEQUENCE {
   filterCoefficientCSI-RSRP-r12 [0] FilterCoefficient OPTIONAL -- Need OR
}

QuantityConfigEUTRA-v1310 ::= SEQUENCE {
   filterCoefficientRS-SINR-r13 [0] FilterCoefficient DEFAULT fc4
}

QuantityConfigWLAN-r13 ::= SEQUENCE {
   measQuantityWLAN-r13 [0] ENUMERATED { rssiWLAN(0) },
   filterCoefficient-r13 [1] FilterCoefficient DEFAULT fc4
}

QuantityConfigRS-NR-r15 ::= SEQUENCE {
   filterCoeff-RSRP-r15 [0] FilterCoefficient DEFAULT fc4,
   filterCoeff-RSRQ-r15 [1] FilterCoefficient DEFAULT fc4,
   filterCoefficient-SINR-r13 [2] FilterCoefficient DEFAULT fc4
}

QuantityConfigNR-r15 ::= SEQUENCE {
   measQuantityCellNR-r15 [0] QuantityConfigRS-NR-r15,
   measQuantityRS-IndexNR-r15 [1] QuantityConfigRS-NR-r15 OPTIONAL
}

QuantityConfigNRList-r15 ::= SEQUENCE (SIZE (1..maxQuantSetsNR-r15)) OF QuantityConfigNR-r15

QuantityConfig ::= SEQUENCE {
   quantityConfigEUTRA [0] QuantityConfigEUTRA OPTIONAL, -- Need ON
   quantityConfigUTRA [1] QuantityConfigUTRA OPTIONAL, -- Need ON
   quantityConfigGERAN [2] QuantityConfigGERAN OPTIONAL, -- Need ON
   quantityConfigCDMA2000 [3] QuantityConfigCDMA2000 OPTIONAL,
   ...,
   [[
      quantityConfigUTRA-v1020 [4] QuantityConfigUTRA-v1020 OPTIONAL
   ]],
   [[
      quantityConfigEUTRA-v1250 [5] QuantityConfigEUTRA-v1250 OPTIONAL
   ]],
   [[
      quantityConfigEUTRA-v1310 [6] QuantityConfigEUTRA-v1310 OPTIONAL,
      quantityConfigWLAN-r13 [7] QuantityConfigWLAN-r13 OPTIONAL
   ]],
   [[
      quantityConfigNRList-r15 [8] QuantityConfigNRList-r15 OPTIONAL
   ]]
}

MeasGapConfig ::= CHOICE {
   release [0] NULL,
   setup [1] SEQUENCE {
      gapOffset [0] EXPLICIT CHOICE {
         gp0 [0] INTEGER (0..39),
         gp1 [1] INTEGER (0..79),
         ...,
         gp2-r14 [2] INTEGER (0..39),
         gp3-r14 [3] INTEGER (0..79),
         gp-ncsg0-r14 [4] INTEGER (0..39),
         gp-ncsg1-r14 [5] INTEGER (0..79),
         gp-ncsg2-r14 [6] INTEGER (0..39),
         gp-ncsg3-r14 [7] INTEGER (0..79),
         gp-nonUniform1-r14 [8] INTEGER (0..1279),
         gp-nonUniform2-r14 [9] INTEGER (0..2559),
         gp-nonUniform3-r14 [10] INTEGER (0..5119),
         gp-nonUniform4-r14 [11] INTEGER (0..10239),
         gp4-r15 [12] INTEGER (0..19),
         gp5-r15 [13] INTEGER (0..159),
         gp6-r15 [14] INTEGER (0..19),
         gp7-r15 [15] INTEGER (0..39),
         gp8-r15 [16] INTEGER (0..79),
         gp9-r15 [17] INTEGER (0..159),
         gp10-r15 [18] INTEGER (0..19),
         gp11-r15 [19] INTEGER (0..159)
      }
   }
}

MeasObjectEUTRA-v9e0 ::= SEQUENCE {
   carrierFreq-v9e0 [0] ARFCN-ValueEUTRA-v9e0
}

MeasObjectToAddMod-v9e0 ::= SEQUENCE {
   measObjectEUTRA-v9e0 [0] MeasObjectEUTRA-v9e0 OPTIONAL -- Cond eutra
}

MeasObjectToAddModList-v9e0 ::= SEQUENCE (SIZE (1..maxObjectId)) OF MeasObjectToAddMod-v9e0
   

MeasIdToRemoveListExt-r12 ::= SEQUENCE (SIZE (1..maxMeasId)) OF MeasId-v1250

MeasIdToAddModExt-r12 ::= SEQUENCE {
   measId-v1250 [0] MeasId-v1250,
   measObjectId-r12 [1] MeasObjectId,
   reportConfigId-r12 [2] ReportConfigId
}

MeasIdToAddModListExt-r12 ::= SEQUENCE (SIZE (1..maxMeasId)) OF MeasIdToAddModExt-r12

MeasObjectToRemoveListExt-r13 ::= SEQUENCE (SIZE (1..maxObjectId)) OF MeasObjectId-v1310

MeasObjectToAddModExt-r13 ::= SEQUENCE {
   measObjectId-r13 [0] MeasObjectId-v1310,
   measObject-r13 [1] EXPLICIT CHOICE {
      measObjectEUTRA-r13 [0] MeasObjectEUTRA,
      measObjectUTRA-r13 [1] MeasObjectUTRA,
      measObjectGERAN-r13 [2] MeasObjectGERAN,
      measObjectCDMA2000-r13 [3] MeasObjectCDMA2000,
      ...,
      measObjectWLAN-v1320 [4] MeasObjectWLAN-r13,
      measObjectNR-r15 [5] MeasObjectNR-r15
   }
}

MeasObjectToAddModListExt-r13 ::= SEQUENCE (SIZE (1..maxObjectId)) OF 
   MeasObjectToAddModExt-r13

MeasIdToAddMod-v1310 ::= SEQUENCE {
   measObjectId-v1310 [0] MeasObjectId-v1310 OPTIONAL
}

MeasIdToAddModList-v1310 ::= SEQUENCE (SIZE (1..maxMeasId)) OF MeasIdToAddMod-v1310

MeasIdToAddModListExt-v1310 ::= SEQUENCE (SIZE (1..maxMeasId)) OF MeasIdToAddMod-v1310

MeasGapConfigToRemoveList-r14 ::= SEQUENCE (SIZE (1..maxServCell-r13)) OF ServCellIndex-r13

MeasGapConfigPerCC-r14 ::= SEQUENCE {
   servCellId-r14 [0] ServCellIndex-r13,
   measGapConfigCC-r14 [1] EXPLICIT MeasGapConfig
}

MeasGapConfigToAddModList-r14 ::= SEQUENCE (SIZE (1..maxServCell-r13)) OF 
   MeasGapConfigPerCC-r14

MeasGapConfigPerCC-List-r14 ::= CHOICE {
   release [0] NULL,
   setup [1] SEQUENCE {
      measGapConfigToRemoveList-r14 [0] MeasGapConfigToRemoveList-r14 OPTIONAL,
          -- Need ON
      measGapConfigToAddModList-r14 [1] MeasGapConfigToAddModList-r14 OPTIONAL -- Need ON
   }
}

MeasGapSharingConfig-r14 ::= CHOICE {
   release [0] NULL,
   setup [1] SEQUENCE {
      measGapSharingScheme-r14 [0] ENUMERATED { scheme00(0), scheme01(1), 
         scheme10(2), scheme11(3) }
   }
}

MeasGapConfigDensePRS-r15 ::= CHOICE {
   release [0] NULL,
   setup [1] SEQUENCE {
      gapOffsetDensePRS-r15 [0] EXPLICIT CHOICE {
         rstd0-r15 [0] INTEGER (0..79),
         rstd1-r15 [1] INTEGER (0..159),
         rstd2-r15 [2] INTEGER (0..319),
         rstd3-r15 [3] INTEGER (0..639),
         rstd4-r15 [4] INTEGER (0..1279),
         rstd5-r15 [5] INTEGER (0..159),
         rstd6-r15 [6] INTEGER (0..319),
         rstd7-r15 [7] INTEGER (0..639),
         rstd8-r15 [8] INTEGER (0..1279),
         rstd9-r15 [9] INTEGER (0..319),
         rstd10-r15 [10] INTEGER (0..639),
         rstd11-r15 [11] INTEGER (0..1279),
         rstd12-r15 [12] INTEGER (0..319),
         rstd13-r15 [13] INTEGER (0..639),
         rstd14-r15 [14] INTEGER (0..1279),
         rstd15-r15 [15] INTEGER (0..639),
         rstd16-r15 [16] INTEGER (0..1279),
         rstd17-r15 [17] INTEGER (0..639),
         rstd18-r15 [18] INTEGER (0..1279),
         rstd19-r15 [19] INTEGER (0..639),
         rstd20-r15 [20] INTEGER (0..1279),
         ...
      }
   }
}

MeasConfig ::= SEQUENCE {
--Measurement objects
   measObjectToRemoveList [0] MeasObjectToRemoveList OPTIONAL, -- Need ON
   measObjectToAddModList [1] MeasObjectToAddModList OPTIONAL, -- Need ON
--Reporting configurations
   reportConfigToRemoveList [2] ReportConfigToRemoveList OPTIONAL, -- Need ON
   reportConfigToAddModList [3] ReportConfigToAddModList OPTIONAL, -- Need ON
--Measurement identities
   measIdToRemoveList [4] MeasIdToRemoveList OPTIONAL, -- Need ON
   measIdToAddModList [5] MeasIdToAddModList OPTIONAL, -- Need ON
--Other parameters
   quantityConfig [6] QuantityConfig OPTIONAL, -- Need ON
   measGapConfig [7] EXPLICIT MeasGapConfig OPTIONAL, -- Need ON
   s-Measure [8] RSRP-Range OPTIONAL, -- Need ON
   preRegistrationInfoHRPD [9] PreRegistrationInfoHRPD OPTIONAL, -- Need OP
   speedStatePars [10] EXPLICIT CHOICE {
      release [0] NULL,
      setup [1] SEQUENCE {
         mobilityStateParameters [0] MobilityStateParameters,
         timeToTrigger-SF [1] SpeedStateScaleFactors
      }
   } OPTIONAL,
   ...,
   [[
      measObjectToAddModList-v9e0 [11] MeasObjectToAddModList-v9e0 OPTIONAL
   ]],
   [[
      allowInterruptions-r11 [12] BOOLEAN OPTIONAL
   ]],
   [[
      measScaleFactor-r12 [13] EXPLICIT CHOICE {
         release [0] NULL,
         setup [1] MeasScaleFactor-r12
      } OPTIONAL,
      measIdToRemoveListExt-r12 [14] MeasIdToRemoveListExt-r12 OPTIONAL,
      measIdToAddModListExt-r12 [15] MeasIdToAddModListExt-r12 OPTIONAL,
      measRSRQ-OnAllSymbols-r12 [16] BOOLEAN OPTIONAL
   ]],
   [[
      measObjectToRemoveListExt-r13 [17] MeasObjectToRemoveListExt-r13 OPTIONAL
         ,
      measObjectToAddModListExt-r13 [18] MeasObjectToAddModListExt-r13 OPTIONAL
         ,
      measIdToAddModList-v1310 [19] MeasIdToAddModList-v1310 OPTIONAL,
      measIdToAddModListExt-v1310 [20] MeasIdToAddModListExt-v1310 OPTIONAL
   ]],
   [[
      measGapConfigPerCC-List-r14 [21] EXPLICIT MeasGapConfigPerCC-List-r14
          OPTIONAL,
      measGapSharingConfig-r14 [22] EXPLICIT MeasGapSharingConfig-r14 OPTIONAL
   ]],
   [[
      fr1-Gap-r15 [23] BOOLEAN OPTIONAL,
      mgta-r15 [24] BOOLEAN OPTIONAL
   ]],
   [[
      measGapConfigDensePRS-r15 [25] EXPLICIT MeasGapConfigDensePRS-r15
          OPTIONAL,
      heightThreshRef-r15 [26] EXPLICIT CHOICE {
         release [0] NULL,
         setup [1] INTEGER (0..31)
      } OPTIONAL
   ]]
}

CarrierFreqEUTRA ::= SEQUENCE {
   dl-CarrierFreq [0] ARFCN-ValueEUTRA,
   ul-CarrierFreq [1] ARFCN-ValueEUTRA OPTIONAL -- Cond FDD
}

CarrierBandwidthEUTRA ::= SEQUENCE {
   dl-Bandwidth [0] ENUMERATED { n6(0), n15(1), n25(2), n50(3), n75(4), n100(5)
      , spare10(6), spare9(7), spare8(8), spare7(9), spare6(10), spare5(11), 
      spare4(12), spare3(13), spare2(14), spare1(15) },
   ul-Bandwidth [1] ENUMERATED { n6(0), n15(1), n25(2), n50(3), n75(4), n100(5)
      , spare10(6), spare9(7), spare8(8), spare7(9), spare6(10), spare5(11), 
      spare4(12), spare3(13), spare2(14), spare1(15) } OPTIONAL -- Need OP
}

PRACH-Config ::= SEQUENCE {
   rootSequenceIndex [0] INTEGER (0..837),
   prach-ConfigInfo [1] PRACH-ConfigInfo OPTIONAL -- Need ON
}

AntennaInfoCommon ::= SEQUENCE {
   antennaPortsCount [0] ENUMERATED { an1(0), an2(1), an4(2), spare1(3) }
}

PRACH-Config-v1310 ::= SEQUENCE {
   rsrp-ThresholdsPrachInfoList-r13 [0] RSRP-ThresholdsPrachInfoList-r13
       OPTIONAL, -- Cond MP
   mpdcch-startSF-CSS-RA-r13 [1] EXPLICIT CHOICE {
      fdd-r13 [0] ENUMERATED { v1(0), v1dot5(1), v2(2), v2dot5(3), v4(4), v5(5)
         , v8(6), v10(7) },
      tdd-r13 [1] ENUMERATED { v1(0), v2(1), v4(2), v5(3), v8(4), v10(5), 
         v20(6), spare(7) }
   } OPTIONAL, -- Cond MP
   prach-HoppingOffset-r13 [2] INTEGER (0..94) OPTIONAL, -- Need OR
   prach-ParametersListCE-r13 [3] PRACH-ParametersListCE-r13 OPTIONAL, -- Cond MP
   initial-CE-level-r13 [4] INTEGER (0..3) OPTIONAL -- Need OR
}

RadioResourceConfigCommon ::= SEQUENCE {
   rach-ConfigCommon [0] RACH-ConfigCommon OPTIONAL, -- Need ON
   prach-Config [1] PRACH-Config,
   pdsch-ConfigCommon [2] PDSCH-ConfigCommon OPTIONAL, -- Need ON
   pusch-ConfigCommon [3] PUSCH-ConfigCommon,
   phich-Config [4] PHICH-Config OPTIONAL, -- Need ON
   pucch-ConfigCommon [5] PUCCH-ConfigCommon OPTIONAL, -- Need ON
   soundingRS-UL-ConfigCommon [6] EXPLICIT SoundingRS-UL-ConfigCommon OPTIONAL,
       -- Need ON
   uplinkPowerControlCommon [7] UplinkPowerControlCommon OPTIONAL, -- Need ON
   antennaInfoCommon [8] AntennaInfoCommon OPTIONAL, -- Need ON
   p-Max [9] P-Max OPTIONAL, -- Need OP
   tdd-Config [10] TDD-Config OPTIONAL, -- Cond TDD
   ul-CyclicPrefixLength [11] UL-CyclicPrefixLength,
   ...,
   [[
      uplinkPowerControlCommon-v1020 [12] UplinkPowerControlCommon-v1020
          OPTIONAL
   ]],
   [[
      tdd-Config-v1130 [13] TDD-Config-v1130 OPTIONAL
   ]],
   [[
      pusch-ConfigCommon-v1270 [14] PUSCH-ConfigCommon-v1270 OPTIONAL
   ]],
   [[
      prach-Config-v1310 [15] PRACH-Config-v1310 OPTIONAL,
      freqHoppingParameters-r13 [16] FreqHoppingParameters-r13 OPTIONAL,
      pdsch-ConfigCommon-v1310 [17] PDSCH-ConfigCommon-v1310 OPTIONAL,
      pucch-ConfigCommon-v1310 [18] PUCCH-ConfigCommon-v1310 OPTIONAL,
      pusch-ConfigCommon-v1310 [19] PUSCH-ConfigCommon-v1310 OPTIONAL,
      uplinkPowerControlCommon-v1310 [20] UplinkPowerControlCommon-v1310
          OPTIONAL
   ]],
   [[
      highSpeedConfig-r14 [21] HighSpeedConfig-r14 OPTIONAL,
      prach-Config-v1430 [22] PRACH-Config-v1430 OPTIONAL,
      pucch-ConfigCommon-v1430 [23] PUCCH-ConfigCommon-v1430 OPTIONAL,
      tdd-Config-v1430 [24] TDD-Config-v1430 OPTIONAL
   ]],
   [[
      tdd-Config-v1450 [25] TDD-Config-v1450 OPTIONAL
   ]],
   [[
      uplinkPowerControlCommon-v1530 [26] UplinkPowerControlCommon-v1530
          OPTIONAL,
      highSpeedConfig-v1530 [27] HighSpeedConfig-v1530 OPTIONAL
   ]]
}

RACH-ConfigDedicated ::= SEQUENCE {
   ra-PreambleIndex [0] INTEGER (0..63),
   ra-PRACH-MaskIndex [1] INTEGER (0..15)
}

CarrierFreqEUTRA-v9e0 ::= SEQUENCE {
   dl-CarrierFreq-v9e0 [0] ARFCN-ValueEUTRA-r9,
   ul-CarrierFreq-v9e0 [1] ARFCN-ValueEUTRA-r9 OPTIONAL -- Cond FDD
}

MobilityControlInfoV2X-r14 ::= SEQUENCE {
   v2x-CommTxPoolExceptional-r14 [0] SL-CommResourcePoolV2X-r14 OPTIONAL, -- Need OR
   v2x-CommRxPool-r14 [1] SL-CommRxPoolListV2X-r14 OPTIONAL, -- Need OR
   v2x-CommSyncConfig-r14 [2] SL-SyncConfigListV2X-r14 OPTIONAL, -- Need OR
   cbr-MobilityTxConfigList-r14 [3] SL-CBR-CommonTxConfigList-r14 OPTIONAL -- Need OR
}

RACH-Skip-r14 ::= SEQUENCE {
   targetTA-r14 [0] EXPLICIT CHOICE {
      ta0-r14 [0] NULL,
      mcg-PTAG-r14 [1] NULL,
      scg-PTAG-r14 [2] NULL,
      mcg-STAG-r14 [3] STAG-Id-r11,
      scg-STAG-r14 [4] STAG-Id-r11
   },
   ul-ConfigInfo-r14 [1] SEQUENCE {
      numberOfConfUL-Processes-r14 [0] INTEGER (1..8),
      ul-SchedInterval-r14 [1] ENUMERATED { sf2(0), sf5(1), sf10(2) },
      ul-StartSubframe-r14 [2] INTEGER (0..9),
      ul-Grant-r14 [3] BIT STRING  (SIZE (16))
   } OPTIONAL -- Need OR
}

MobilityControlInfo ::= SEQUENCE {
   targetPhysCellId [0] PhysCellId,
   carrierFreq [1] CarrierFreqEUTRA OPTIONAL, -- Cond HO-toEUTRA2
   carrierBandwidth [2] CarrierBandwidthEUTRA OPTIONAL, -- Cond HO-toEUTRA
   additionalSpectrumEmission [3] AdditionalSpectrumEmission OPTIONAL, -- Cond HO-toEUTRA
   t304 [4] ENUMERATED { ms50(0), ms100(1), ms150(2), ms200(3), ms500(4), 
      ms1000(5), ms2000(6), ms10000-v1310(7) },
   newUE-Identity [5] C-RNTI,
   radioResourceConfigCommon [6] RadioResourceConfigCommon,
   rach-ConfigDedicated [7] RACH-ConfigDedicated OPTIONAL,
   ...,
   [[
      carrierFreq-v9e0 [8] CarrierFreqEUTRA-v9e0 OPTIONAL
   ]],
   [[
      drb-ContinueROHC-r11 [9] ENUMERATED { true(0) } OPTIONAL
   ]],
   [[
      mobilityControlInfoV2X-r14 [10] MobilityControlInfoV2X-r14 OPTIONAL,
      handoverWithoutWT-Change-r14 [11] ENUMERATED { keepLWA-Config(0), 
         sendEndMarker(1) } OPTIONAL,
      makeBeforeBreak-r14 [12] ENUMERATED { true(0) } OPTIONAL,
      rach-Skip-r14 [13] RACH-Skip-r14 OPTIONAL,
      sameSFN-Indication-r14 [14] ENUMERATED { true(0) } OPTIONAL
   ]],
   [[
      mib-RepetitionStatus-r14 [15] BOOLEAN OPTIONAL,
      schedulingInfoSIB1-BR-r14 [16] INTEGER (0..31) OPTIONAL
   ]]
}

SecurityAlgorithmConfig ::= SEQUENCE {
   cipheringAlgorithm [0] CipheringAlgorithm-r12,
   integrityProtAlgorithm [1] ENUMERATED { eia0-v920(0), eia1(1), eia2(2), 
      eia3-v1130(3), spare4(4), spare3(5), spare2(6), spare1(7), ... }
}

SecurityConfigHO ::= SEQUENCE {
   handoverType [0] EXPLICIT CHOICE {
      intraLTE [0] SEQUENCE {
         securityAlgorithmConfig [0] SecurityAlgorithmConfig OPTIONAL, -- Cond fullConfig
         keyChangeIndicator [1] BOOLEAN,
         nextHopChainingCount [2] NextHopChainingCount
      },
      interRAT [1] SEQUENCE {
         securityAlgorithmConfig [0] SecurityAlgorithmConfig,
         nas-SecurityParamToEUTRA [1] OCTET STRING (SIZE (6))
      }
   },
   ...
}

AntennaInfoDedicated-v10i0 ::= SEQUENCE {
   maxLayersMIMO-r10 [0] ENUMERATED { twoLayers(0), fourLayers(1), 
      eightLayers(2) } OPTIONAL -- Need OR
}

MobilityControlInfo-v10l0 ::= SEQUENCE {
   additionalSpectrumEmission-v10l0 [0] AdditionalSpectrumEmission-v10l0
       OPTIONAL -- Need ON
}

RadioResourceConfigCommonSCell-v10l0 ::= SEQUENCE {
--UL configuration
   ul-Configuration-v10l0 [0] SEQUENCE {
      additionalSpectrumEmissionSCell-v10l0 [0] 
         AdditionalSpectrumEmission-v10l0
   }
}

SCellToAddMod-v10l0 ::= SEQUENCE {
   radioResourceConfigCommonSCell-v10l0 [0] 
      RadioResourceConfigCommonSCell-v10l0 OPTIONAL
}

SCellToAddModList-v10l0 ::= SEQUENCE (SIZE (1..maxSCell-r10)) OF SCellToAddMod-v10l0

RadioResourceConfigCommonPSCell-v12f0 ::= SEQUENCE {
   basicFields-v12f0 [0] RadioResourceConfigCommonSCell-v10l0
}

PSCellToAddMod-v12f0 ::= SEQUENCE {
   radioResourceConfigCommonPSCell-r12 [0] 
      RadioResourceConfigCommonPSCell-v12f0 OPTIONAL
}

SCG-ConfigPartSCG-v12f0 ::= SEQUENCE {
   pSCellToAddMod-v12f0 [0] PSCellToAddMod-v12f0 OPTIONAL, -- Need ON
   sCellToAddModListSCG-v12f0 [1] SCellToAddModList-v10l0 OPTIONAL -- Need ON
}

SCG-Configuration-v12f0 ::= CHOICE {
   release [0] NULL,
   setup [1] SEQUENCE {
      scg-ConfigPartSCG-v12f0 [0] SCG-ConfigPartSCG-v12f0 OPTIONAL -- Need ON
   }
}

PUCCH-ConfigDedicated-v1370 ::= SEQUENCE {
   pucch-Format-v1370 [0] EXPLICIT CHOICE {
      release [0] NULL,
      setup [1] PUCCH-Format3-Conf-r13
   }
}

PhysicalConfigDedicated-v1370 ::= SEQUENCE {
   pucch-ConfigDedicated-v1370 [0] PUCCH-ConfigDedicated-v1370 OPTIONAL -- Cond PUCCH-Format4or5
}

RadioResourceConfigDedicated-v1370 ::= SEQUENCE {
   physicalConfigDedicated-v1370 [0] PhysicalConfigDedicated-v1370 OPTIONAL -- Need ON
}

SCellToAddModExt-v1370 ::= SEQUENCE {
   radioResourceConfigCommonSCell-v1370 [0] 
      RadioResourceConfigCommonSCell-v10l0 OPTIONAL
}

SCellToAddModListExt-v1370 ::= SEQUENCE (SIZE (1..maxSCell-r13)) OF SCellToAddModExt-v1370

PUCCH-ConfigDedicated-v13c0 ::= SEQUENCE {
   channelSelection-v13c0 [0] SEQUENCE {
      n1PUCCH-AN-CS-v13c0 [0] EXPLICIT CHOICE {
         release [0] NULL,
         setup [1] SEQUENCE {
            n1PUCCH-AN-CS-ListP1-v13c0 [0] SEQUENCE (SIZE (2..4)) OF INTEGER (0..2047)
         }
      }
   }
}

PhysicalConfigDedicated-v13c0 ::= SEQUENCE {
   pucch-ConfigDedicated-v13c0 [0] PUCCH-ConfigDedicated-v13c0
}

RadioResourceConfigDedicated-v13c0 ::= SEQUENCE {
   physicalConfigDedicated-v13c0 [0] PhysicalConfigDedicated-v13c0
}

PhysicalConfigDedicatedSCell-v13c0 ::= SEQUENCE {
   pucch-SCell-v13c0 [0] EXPLICIT CHOICE {
      release [0] NULL,
      setup [1] SEQUENCE {
         pucch-ConfigDedicated-v13c0 [0] PUCCH-ConfigDedicated-v13c0
      }
   }
}

RadioResourceConfigDedicatedSCell-v13c0 ::= SEQUENCE {
   physicalConfigDedicatedSCell-v13c0 [0] PhysicalConfigDedicatedSCell-v13c0
}

SCellToAddMod-v13c0 ::= SEQUENCE {
   radioResourceConfigDedicatedSCell-v13c0 [0] 
      RadioResourceConfigDedicatedSCell-v13c0 OPTIONAL
}

SCellToAddModList-v13c0 ::= SEQUENCE (SIZE (1..maxSCell-r10)) OF SCellToAddMod-v13c0

SCellToAddModListExt-v13c0 ::= SEQUENCE (SIZE (1..maxSCell-r13)) OF SCellToAddMod-v13c0

SCG-ConfigPartSCG-v13c0 ::= SEQUENCE {
   sCellToAddModListSCG-v13c0 [0] SCellToAddModList-v13c0 OPTIONAL, -- Need ON
   sCellToAddModListSCG-Ext-v13c0 [1] SCellToAddModListExt-v13c0 OPTIONAL -- Need ON
}

SCG-Configuration-v13c0 ::= CHOICE {
   release [0] NULL,
   setup [1] SEQUENCE {
      scg-ConfigPartSCG-v13c0 [0] SCG-ConfigPartSCG-v13c0 OPTIONAL -- Need ON
   }
}

RRCConnectionReconfiguration-v13c0-IEs ::= SEQUENCE {
   radioResourceConfigDedicated-v13c0 [0] RadioResourceConfigDedicated-v13c0
       OPTIONAL, -- Need ON
   sCellToAddModList-v13c0 [1] SCellToAddModList-v13c0 OPTIONAL, -- Need ON
   sCellToAddModListExt-v13c0 [2] SCellToAddModListExt-v13c0 OPTIONAL, -- Need ON
   scg-Configuration-v13c0 [3] EXPLICIT SCG-Configuration-v13c0 OPTIONAL, -- Need ON
--Following field is only for late non-critical extensions from REL-13 onwards
   nonCriticalExtension [4] SEQUENCE {

   } OPTIONAL
}

RRCConnectionReconfiguration-v1370-IEs ::= SEQUENCE {
   radioResourceConfigDedicated-v1370 [0] RadioResourceConfigDedicated-v1370
       OPTIONAL, -- Need ON
   sCellToAddModListExt-v1370 [1] SCellToAddModListExt-v1370 OPTIONAL, -- Need ON
   nonCriticalExtension [2] RRCConnectionReconfiguration-v13c0-IEs OPTIONAL
}

RRCConnectionReconfiguration-v12f0-IEs ::= SEQUENCE {
   scg-Configuration-v12f0 [0] EXPLICIT SCG-Configuration-v12f0 OPTIONAL, -- Cond nonFullConfig
--Following field is only for late non-critical extensions from REL-12
   lateNonCriticalExtension [1] OCTET STRING OPTIONAL,
   nonCriticalExtension [2] RRCConnectionReconfiguration-v1370-IEs OPTIONAL
}

RRCConnectionReconfiguration-v10l0-IEs ::= SEQUENCE {
   mobilityControlInfo-v10l0 [0] MobilityControlInfo-v10l0 OPTIONAL,
   sCellToAddModList-v10l0 [1] SCellToAddModList-v10l0 OPTIONAL, -- Need ON
--Following field is only for late non-critical extensions from REL-10 to REL-11
   lateNonCriticalExtension [2] OCTET STRING OPTIONAL,
   nonCriticalExtension [3] RRCConnectionReconfiguration-v12f0-IEs OPTIONAL
}

RRCConnectionReconfiguration-v10i0-IEs ::= SEQUENCE {
   antennaInfoDedicatedPCell-v10i0 [0] AntennaInfoDedicated-v10i0 OPTIONAL, -- Need ON
   nonCriticalExtension [1] RRCConnectionReconfiguration-v10l0-IEs OPTIONAL
}

-- Late non-critical extensions:
RRCConnectionReconfiguration-v8m0-IEs ::= SEQUENCE {
--Following field is only for pre REL-10 late non-critical extensions
   lateNonCriticalExtension [0] OCTET STRING OPTIONAL,
   nonCriticalExtension [1] RRCConnectionReconfiguration-v10i0-IEs OPTIONAL
}

ReportProximityConfig-r9 ::= SEQUENCE {
   proximityIndicationEUTRA-r9 [0] ENUMERATED { enabled(0) } OPTIONAL, -- Need OR
   proximityIndicationUTRA-r9 [1] ENUMERATED { enabled(0) } OPTIONAL -- Need OR
}

CandidateServingFreqListNR-r15 ::= SEQUENCE (SIZE (1..maxFreqIDC-r11)) OF ARFCN-ValueNR-r15

IDC-Config-r11 ::= SEQUENCE {
   idc-Indication-r11 [0] ENUMERATED { setup(0) } OPTIONAL, -- Need OR
   autonomousDenialParameters-r11 [1] SEQUENCE {
      autonomousDenialSubframes-r11 [0] ENUMERATED { n2(0), n5(1), n10(2), 
         n15(3), n20(4), n30(5), spare2(6), spare1(7) },
      autonomousDenialValidity-r11 [1] ENUMERATED { sf200(0), sf500(1), 
         sf1000(2), sf2000(3), spare4(4), spare3(5), spare2(6), spare1(7) }
   } OPTIONAL,
   ...,
   [[
      idc-Indication-UL-CA-r11 [2] ENUMERATED { setup(0) } OPTIONAL
   ]],
   [[
      idc-HardwareSharingIndication-r13 [3] ENUMERATED { setup(0) } OPTIONAL
   ]],
   [[
      idc-Indication-MRDC-r15 [4] EXPLICIT CHOICE {
         release [0] NULL,
         setup [1] CandidateServingFreqListNR-r15
      } OPTIONAL
   ]]
}

PowerPrefIndicationConfig-r11 ::= CHOICE {
   release [0] NULL,
   setup [1] SEQUENCE {
      powerPrefIndicationTimer-r11 [0] ENUMERATED { s0(0), s0dot5(1), s1(2), 
         s2(3), s5(4), s10(5), s20(6), s30(7), s60(8), s90(9), s120(10), 
         s300(11), s600(12), spare3(13), spare2(14), spare1(15) }
   }
}

ObtainLocationConfig-r11 ::= SEQUENCE {
   obtainLocation-r11 [0] ENUMERATED { setup(0) } OPTIONAL -- Need OR
}

OtherConfig-r9 ::= SEQUENCE {
   reportProximityConfig-r9 [0] ReportProximityConfig-r9 OPTIONAL,
   ...,
   [[
      idc-Config-r11 [1] IDC-Config-r11 OPTIONAL,
      powerPrefIndicationConfig-r11 [2] EXPLICIT PowerPrefIndicationConfig-r11
          OPTIONAL,
      obtainLocationConfig-r11 [3] ObtainLocationConfig-r11 OPTIONAL
   ]],
   [[
      bw-PreferenceIndicationTimer-r14 [4] ENUMERATED { s0(0), s0dot5(1), s1(2)
         , s2(3), s5(4), s10(5), s20(6), s30(7), s60(8), s90(9), s120(10), 
         s300(11), s600(12), spare3(13), spare2(14), spare1(15) } OPTIONAL,
      sps-AssistanceInfoReport-r14 [5] BOOLEAN OPTIONAL,
      delayBudgetReportingConfig-r14 [6] EXPLICIT CHOICE {
         release [0] NULL,
         setup [1] SEQUENCE {
            delayBudgetReportingProhibitTimer-r14 [0] ENUMERATED { s0(0), 
               s0dot4(1), s0dot8(2), s1dot6(3), s3(4), s6(5), s12(6), s30(7) }
         }
      } OPTIONAL,
      rlm-ReportConfig-r14 [7] EXPLICIT CHOICE {
         release [0] NULL,
         setup [1] SEQUENCE {
            rlmReportTimer-r14 [0] ENUMERATED { s0(0), s0dot5(1), s1(2), s2(3)
               , s5(4), s10(5), s20(6), s30(7), s60(8), s90(9), s120(10), 
               s300(11), s600(12), spare3(13), spare2(14), spare1(15) },
            rlmReportRep-MPDCCH-r14 [1] ENUMERATED { setup(0) } OPTIONAL -- Need OR
         }
      } OPTIONAL
   ]],
   [[
      overheatingAssistanceConfig-r14 [8] EXPLICIT CHOICE {
         release [0] NULL,
         setup [1] SEQUENCE {
            overheatingIndicationProhibitTimer-r14 [0] ENUMERATED { s0(0), 
               s0dot5(1), s1(2), s2(3), s5(4), s10(5), s20(6), s30(7), s60(8), 
               s90(9), s120(10), s300(11), s600(12), spare3(13), spare2(14), 
               spare1(15) }
         }
      } OPTIONAL
   ]],
   [[
      measConfigAppLayer-r15 [9] EXPLICIT CHOICE {
         release [0] NULL,
         setup [1] SEQUENCE {
            measConfigAppLayerContainer-r15 [0] OCTET STRING (SIZE (1..1000)),
            serviceType-r15 [1] ENUMERATED { qoe(0), qoemtsi(1), spare6(2), 
               spare5(3), spare4(4), spare3(5), spare2(6), spare1(7) }
         }
      } OPTIONAL,
      ailc-BitConfig-r15 [10] BOOLEAN OPTIONAL,
      bt-NameListConfig-r15 [11] EXPLICIT BT-NameListConfig-r15 OPTIONAL,
      wlan-NameListConfig-r15 [12] EXPLICIT WLAN-NameListConfig-r15 OPTIONAL
   ]]
}

SCellToReleaseList-r10 ::= SEQUENCE (SIZE (1..maxSCell-r10)) OF SCellIndex-r10

UplinkPowerControlCommonSCell-r10 ::= SEQUENCE {
   p0-NominalPUSCH-r10 [0] INTEGER (-126..24),
   alpha-r10 [1] Alpha-r12
}

PRACH-ConfigSCell-r10 ::= SEQUENCE {
   prach-ConfigIndex-r10 [0] INTEGER (0..63)
}

RACH-ConfigCommonSCell-r11 ::= SEQUENCE {
   powerRampingParameters-r11 [0] PowerRampingParameters,
   ra-SupervisionInfo-r11 [1] SEQUENCE {
      preambleTransMax-r11 [0] PreambleTransMax
   },
   ...
}

UplinkPowerControlCommonSCell-v1130 ::= SEQUENCE {
   deltaPreambleMsg3-r11 [0] INTEGER (-1..6)
}

UplinkPowerControlCommonSCell-v1310 ::= SEQUENCE {
--For uplink power control the additional/ missing fields are signalled (compared to SCell)
   p0-NominalPUCCH [0] INTEGER (-127..-96),
   deltaFList-PUCCH [1] DeltaFList-PUCCH,
   deltaF-PUCCH-Format3-r12 [2] ENUMERATED { deltaF-1(0), deltaF0(1), 
      deltaF1(2), deltaF2(3), deltaF3(4), deltaF4(5), deltaF5(6), deltaF6(7) }
       OPTIONAL, -- Need OR
   deltaF-PUCCH-Format1bCS-r12 [3] ENUMERATED { deltaF1(0), deltaF2(1), 
      spare2(2), spare1(3) } OPTIONAL, -- Need OR
   deltaF-PUCCH-Format4-r13 [4] ENUMERATED { deltaF16(0), deltaF15(1), 
      deltaF14(2), deltaF13(3), deltaF12(4), deltaF11(5), deltaF10(6), 
      spare1(7) } OPTIONAL, -- Need OR
   deltaF-PUCCH-Format5-13 [5] ENUMERATED { deltaF13(0), deltaF12(1), 
      deltaF11(2), deltaF10(3), deltaF9(4), deltaF8(5), deltaF7(6), spare1(7) }
       OPTIONAL -- Need OR
}

HighSpeedConfigSCell-r14 ::= SEQUENCE {
   highSpeedEnhancedDemodulationFlag-r14 [0] ENUMERATED { true(0) } OPTIONAL -- Need OR
}

UplinkPowerControlCommonPUSCH-LessCell-v1430 ::= SEQUENCE {
   p0-Nominal-PeriodicSRS-r14 [0] INTEGER (-126..24) OPTIONAL, -- Need OR
   p0-Nominal-AperiodicSRS-r14 [1] INTEGER (-126..24) OPTIONAL, -- Need OR
   alpha-SRS-r14 [2] Alpha-r12 OPTIONAL -- Need OR
}

RadioResourceConfigCommonSCell-r10 ::= SEQUENCE {
--DL configuration as well as configuration applicable for DL and UL
   nonUL-Configuration-r10 [0] SEQUENCE {
--1: Cell characteristics
      dl-Bandwidth-r10 [0] ENUMERATED { n6(0), n15(1), n25(2), n50(3), n75(4), 
         n100(5) },
--2: Physical configuration, general
      antennaInfoCommon-r10 [1] AntennaInfoCommon,
      mbsfn-SubframeConfigList-r10 [2] MBSFN-SubframeConfigList OPTIONAL, -- Need OR
--3: Physical configuration, control
      phich-Config-r10 [3] PHICH-Config,
--4: Physical configuration, physical channels
      pdsch-ConfigCommon-r10 [4] PDSCH-ConfigCommon,
      tdd-Config-r10 [5] TDD-Config OPTIONAL -- Cond TDDSCell
   },
--UL configuration
   ul-Configuration-r10 [1] SEQUENCE {
      ul-FreqInfo-r10 [0] SEQUENCE {
         ul-CarrierFreq-r10 [0] ARFCN-ValueEUTRA OPTIONAL, -- Need OP
         ul-Bandwidth-r10 [1] ENUMERATED { n6(0), n15(1), n25(2), n50(3), 
            n75(4), n100(5) } OPTIONAL, -- Need OP
         additionalSpectrumEmissionSCell-r10 [2] AdditionalSpectrumEmission
      },
      p-Max-r10 [1] P-Max OPTIONAL, -- Need OP
      uplinkPowerControlCommonSCell-r10 [2] UplinkPowerControlCommonSCell-r10,
--A special version of IE UplinkPowerControlCommon may be introduced
--3: Physical configuration, control
      soundingRS-UL-ConfigCommon-r10 [3] EXPLICIT SoundingRS-UL-ConfigCommon,
      ul-CyclicPrefixLength-r10 [4] UL-CyclicPrefixLength,
--4: Physical configuration, physical channels
      prach-ConfigSCell-r10 [5] PRACH-ConfigSCell-r10 OPTIONAL, -- Cond TDD-OR-NoR11
      pusch-ConfigCommon-r10 [6] PUSCH-ConfigCommon
   } OPTIONAL,
   ...,
   [[
      ul-CarrierFreq-v1090 [2] ARFCN-ValueEUTRA-v9e0 OPTIONAL
   ]],
   [[
      rach-ConfigCommonSCell-r11 [3] RACH-ConfigCommonSCell-r11 OPTIONAL,
      prach-ConfigSCell-r11 [4] PRACH-Config OPTIONAL,
      tdd-Config-v1130 [5] TDD-Config-v1130 OPTIONAL,
      uplinkPowerControlCommonSCell-v1130 [6] 
         UplinkPowerControlCommonSCell-v1130 OPTIONAL
   ]],
   [[
      pusch-ConfigCommon-v1270 [7] PUSCH-ConfigCommon-v1270 OPTIONAL
   ]],
   [[
      pucch-ConfigCommon-r13 [8] PUCCH-ConfigCommon OPTIONAL,
      uplinkPowerControlCommonSCell-v1310 [9] 
         UplinkPowerControlCommonSCell-v1310 OPTIONAL
   ]],
   [[
      highSpeedConfigSCell-r14 [10] HighSpeedConfigSCell-r14 OPTIONAL,
      prach-Config-v1430 [11] PRACH-Config-v1430 OPTIONAL,
      ul-Configuration-r14 [12] SEQUENCE {
         ul-FreqInfo-r14 [0] SEQUENCE {
            ul-CarrierFreq-r14 [0] ARFCN-ValueEUTRA-r9 OPTIONAL, -- Need OP
            ul-Bandwidth-r14 [1] ENUMERATED { n6(0), n15(1), n25(2), n50(3), 
               n75(4), n100(5) } OPTIONAL, -- Need OP
            additionalSpectrumEmissionSCell-r14 [2] AdditionalSpectrumEmission
         },
         p-Max-r14 [1] P-Max OPTIONAL, -- Need OP
         soundingRS-UL-ConfigCommon-r14 [2] EXPLICIT SoundingRS-UL-ConfigCommon
            ,
         ul-CyclicPrefixLength-r14 [3] UL-CyclicPrefixLength,
         prach-ConfigSCell-r14 [4] PRACH-ConfigSCell-r10 OPTIONAL, -- Cond TDD-OR-NoR11		
         uplinkPowerControlCommonPUSCH-LessCell-v1430 [5] 
            UplinkPowerControlCommonPUSCH-LessCell-v1430 OPTIONAL -- Need OR
      } OPTIONAL,
      harq-ReferenceConfig-r14 [13] ENUMERATED { sa2(0), sa4(1), sa5(2) }
          OPTIONAL,
      soundingRS-FlexibleTiming-r14 [14] ENUMERATED { true(0) } OPTIONAL
   ]],
   [[
      mbsfn-SubframeConfigList-v1430 [15] MBSFN-SubframeConfigList-v1430
          OPTIONAL
   ]],
   [[
      uplinkPowerControlCommonSCell-v1530 [16] UplinkPowerControlCommon-v1530
          OPTIONAL
   ]]
}

CrossCarrierSchedulingConfig-r10 ::= SEQUENCE {
   schedulingCellInfo-r10 [0] EXPLICIT CHOICE {
      own-r10 [0] SEQUENCE {
                          -- No cross carrier scheduling
         cif-Presence-r10 [0] BOOLEAN
      },
      other-r10 [1] SEQUENCE {
                            -- Cross carrier scheduling
         schedulingCellId-r10 [0] ServCellIndex-r10,
         pdsch-Start-r10 [1] INTEGER (1..4)
      }
   }
}

PUSCH-ConfigDedicatedSCell-r10 ::= SEQUENCE {
   groupHoppingDisabled-r10 [0] ENUMERATED { true(0) } OPTIONAL, -- Need OR
   dmrs-WithOCC-Activated-r10 [1] ENUMERATED { true(0) } OPTIONAL -- Need OR
}

UplinkPowerControlDedicatedSCell-r10 ::= SEQUENCE {
   p0-UE-PUSCH-r10 [0] INTEGER (-8..7),
   deltaMCS-Enabled-r10 [1] ENUMERATED { en0(0), en1(1) },
   accumulationEnabled-r10 [2] BOOLEAN,
   pSRS-Offset-r10 [3] INTEGER (0..15),
   pSRS-OffsetAp-r10 [4] INTEGER (0..15) OPTIONAL, -- Need OR
   filterCoefficient-r10 [5] FilterCoefficient DEFAULT fc4,
   pathlossReferenceLinking-r10 [6] ENUMERATED { pCell(0), sCell(1) }
}

CQI-ReportConfigSCell-r10 ::= SEQUENCE {
   cqi-ReportModeAperiodic-r10 [0] CQI-ReportModeAperiodic OPTIONAL, -- Need OR
   nomPDSCH-RS-EPRE-Offset-r10 [1] INTEGER (-1..6),
   cqi-ReportPeriodicSCell-r10 [2] EXPLICIT CQI-ReportPeriodic-r10 OPTIONAL, -- Need ON
   pmi-RI-Report-r10 [3] ENUMERATED { setup(0) } OPTIONAL -- Cond PMIRISCell
}

SchedulingRequestConfigSCell-r13 ::= CHOICE {
   release [0] NULL,
   setup [1] SEQUENCE {
      sr-PUCCH-ResourceIndex-r13 [0] INTEGER (0..2047),
      sr-PUCCH-ResourceIndexP1-r13 [1] INTEGER (0..2047) OPTIONAL, -- Need OR
      sr-ConfigIndex-r13 [2] INTEGER (0..157),
      dsr-TransMax-r13 [3] ENUMERATED { n4(0), n8(1), n16(2), n32(3), n64(4), 
         spare3(5), spare2(6), spare1(7) }
   }
}

TPC-PDCCH-ConfigSCell-r13 ::= CHOICE {
   release [0] NULL,
   setup [1] SEQUENCE {
      tpc-Index-PUCCH-SCell-r13 [0] EXPLICIT TPC-Index
   }
}

UplinkPowerControlDedicatedSCell-v1310 ::= SEQUENCE {
--Release 8
   p0-UE-PUCCH [0] INTEGER (-8..7),
--Release 10
   deltaTxD-OffsetListPUCCH-r10 [1] DeltaTxD-OffsetListPUCCH-r10 OPTIONAL -- Need OR
}

CrossCarrierSchedulingConfig-r13 ::= SEQUENCE {
   schedulingCellInfo-r13 [0] EXPLICIT CHOICE {
      own-r13 [0] SEQUENCE {
                          -- No cross carrier scheduling
         cif-Presence-r13 [0] BOOLEAN
      },
      other-r13 [1] SEQUENCE {
                           -- Cross carrier scheduling
         schedulingCellId-r13 [0] ServCellIndex-r13,
         pdsch-Start-r13 [1] INTEGER (1..4),
         cif-InSchedulingCell-r13 [2] INTEGER (1..7)
      }
   }
}

PDCCH-ConfigSCell-r13 ::= SEQUENCE {
   skipMonitoringDCI-format0-1A-r13 [0] ENUMERATED { true(0) } OPTIONAL -- Need OR
}

LAA-SCellConfiguration-r13 ::= SEQUENCE {
   subframeStartPosition-r13 [0] ENUMERATED { s0(0), s07(1) },
   laa-SCellSubframeConfig-r13 [1] BIT STRING  (SIZE (8))
}

CrossCarrierSchedulingConfigLAA-UL-r14 ::= SEQUENCE {
   schedulingCellId-r14 [0] ServCellIndex-r13,
   cif-InSchedulingCell-r14 [1] INTEGER (1..7)
}

LBT-Config-r14 ::= CHOICE {
   maxEnergyDetectionThreshold-r14 [0] INTEGER (-85..-52),
   energyDetectionThresholdOffset-r14 [1] INTEGER (-13..20)
}

PDCCH-CandidateReductionsLAA-UL-r14 ::= CHOICE {
   release [0] NULL,
   setup [1] SEQUENCE {
      pdcch-candidateReductionAL1-r14 [0] PDCCH-CandidateReductionValue-r13,
      pdcch-candidateReductionAL2-r14 [1] PDCCH-CandidateReductionValue-r13,
      pdcch-candidateReductionAL3-r14 [2] PDCCH-CandidateReductionValue-r14,
      pdcch-candidateReductionAL4-r14 [3] PDCCH-CandidateReductionValue-r14,
      pdcch-candidateReductionAL5-r14 [4] PDCCH-CandidateReductionValue-r14
   }
}

PDCCH-ConfigLAA-r14 ::= SEQUENCE {
   maxNumberOfSchedSubframes-Format0B-r14 [0] ENUMERATED { sf2(0), sf3(1), 
      sf4(2) } OPTIONAL, -- Need OR
   maxNumberOfSchedSubframes-Format4B-r14 [1] ENUMERATED { sf2(0), sf3(1), 
      sf4(2) } OPTIONAL, -- Need OR
   skipMonitoringDCI-Format0A-r14 [2] ENUMERATED { true(0) } OPTIONAL, -- Need OR
   skipMonitoringDCI-Format4A-r14 [3] ENUMERATED { true(0) } OPTIONAL, -- Need OR
   pdcch-CandidateReductions-Format0A-r14 [4] EXPLICIT 
      PDCCH-CandidateReductions-r13 OPTIONAL, -- Need ON
   pdcch-CandidateReductions-Format4A-r14 [5] EXPLICIT 
      PDCCH-CandidateReductionsLAA-UL-r14 OPTIONAL, -- Need ON
   pdcch-CandidateReductions-Format0B-r14 [6] EXPLICIT 
      PDCCH-CandidateReductionsLAA-UL-r14 OPTIONAL, -- Need ON
   pdcch-CandidateReductions-Format4B-r14 [7] EXPLICIT 
      PDCCH-CandidateReductionsLAA-UL-r14 OPTIONAL -- Need ON
}

SoundingRS-UL-ConfigDedicatedAperiodic-v1430 ::= CHOICE {
   release [0] NULL,
   setup [1] SEQUENCE {
      srs-SubframeIndication-r14 [0] INTEGER (1..4) OPTIONAL -- Need ON
   }
}

LAA-SCellConfiguration-v1430 ::= SEQUENCE {
   crossCarrierSchedulingConfig-UL-r14 [0] EXPLICIT CHOICE {
      release [0] NULL,
      setup [1] SEQUENCE {
         crossCarrierSchedulingConfigLAA-UL-r14 [0] 
            CrossCarrierSchedulingConfigLAA-UL-r14
      }
   } OPTIONAL, -- Cond Cross-Carrier-ConfigUL
   lbt-Config-r14 [1] EXPLICIT LBT-Config-r14 OPTIONAL, -- Need ON
   pdcch-ConfigLAA-r14 [2] PDCCH-ConfigLAA-r14 OPTIONAL, -- Need ON
   absenceOfAnyOtherTechnology-r14 [3] ENUMERATED { true(0) } OPTIONAL, -- Need OR
   soundingRS-UL-ConfigDedicatedAperiodic-v1430 [4] EXPLICIT 
      SoundingRS-UL-ConfigDedicatedAperiodic-v1430 OPTIONAL -- Need ON
}

UplinkPUSCH-LessPowerControlDedicated-v1430 ::= SEQUENCE {
   p0-UE-PeriodicSRS-r14 [0] INTEGER (-8..7) OPTIONAL, -- Need OR
   p0-UE-AperiodicSRS-r14 [1] INTEGER (-8..7) OPTIONAL, -- Need OR
   accumulationEnabled-r14 [2] BOOLEAN
}

SoundingRS-AperiodicSet-r14 ::= SEQUENCE {
   srs-CC-SetIndexList-r14 [0] SEQUENCE (SIZE (1..4)) OF SRS-CC-SetIndex-r14
       OPTIONAL,
                       -- Cond SRS-Trigger-TypeA
   soundingRS-UL-ConfigDedicatedAperiodic-r14 [1] EXPLICIT 
      SoundingRS-UL-ConfigDedicatedAperiodic-r10
}

SoundingRS-AperiodicSetUpPTsExt-r14 ::= SEQUENCE {
   srs-CC-SetIndexList-r14 [0] SEQUENCE (SIZE (1..4)) OF SRS-CC-SetIndex-r14
       OPTIONAL,
                       -- Cond SRS-Trigger-TypeA
   soundingRS-UL-ConfigDedicatedAperiodicUpPTsExt-r14 [1] EXPLICIT 
      SoundingRS-UL-ConfigDedicatedAperiodicUpPTsExt-r13
}

PUSCH-ConfigDedicatedSCell-v1430 ::= SEQUENCE {
   enable256QAM-r14 [0] EXPLICIT Enable256QAM-r14 OPTIONAL -- Need OR
}

PDSCH-ConfigDedicatedSCell-v1430 ::= SEQUENCE {
   tbsIndexAlt2-r14 [0] ENUMERATED { b33(0) } OPTIONAL -- Need OR
}

CQI-ReportPeriodicSCell-r15 ::= CHOICE {
   release [0] NULL,
   setup [1] SEQUENCE {
      cqi-pmi-ConfigIndexDormant-r15 [0] INTEGER (0..1023),
      ri-ConfigIndexDormant-r15 [1] INTEGER (0..1023) OPTIONAL, -- Need OR
      csi-SubframePatternDormant-r15 [2] EXPLICIT CHOICE {
         release [0] NULL,
         setup [1] SEQUENCE {
            csi-MeasSubframeSet1-r15 [0] EXPLICIT MeasSubframePattern-r10,
            csi-MeasSubframeSet2-r15 [1] EXPLICIT MeasSubframePattern-r10
         }
      } OPTIONAL, -- Need ON
      cqi-FormatIndicatorDormant-r15 [3] EXPLICIT CHOICE {
         widebandCQI-r15 [0] SEQUENCE {
            csi-ReportMode-r15 [0] ENUMERATED { submode1(0), submode2(1) }
                OPTIONAL -- Need OR
         },
         subbandCQI-r15 [1] SEQUENCE {
            k-r15 [0] INTEGER (1..4),
            periodicityFactor-r15 [1] ENUMERATED { n2(0), n4(1) }
         }
      } OPTIONAL -- Need OR
   }
}

CQI-ReportConfigSCell-r15 ::= SEQUENCE {
   cqi-ReportPeriodicSCell-r15 [0] EXPLICIT CQI-ReportPeriodicSCell-r15
       OPTIONAL, -- Need ON
   altCQI-Table-1024QAM-r15 [1] ENUMERATED { allSubframes(0), 
      csi-SubframeSet1(1), csi-SubframeSet2(2), spare1(3) } OPTIONAL -- Need OP
}

CQI-ShortConfigSCell-r15 ::= CHOICE {
   release [0] NULL,
   setup [1] SEQUENCE {
      cqi-pmi-ConfigIndexShort-r15 [0] INTEGER (0..1023),
      ri-ConfigIndexShort-r15 [1] INTEGER (0..1023) OPTIONAL, -- Need OR
      cqi-FormatIndicatorShort-r15 [2] EXPLICIT CHOICE {
         widebandCQI-Short-r15 [0] SEQUENCE {
            csi-ReportModeShort-r15 [0] ENUMERATED { submode1(0), submode2(1) }
                OPTIONAL -- Need OR
         },
         subbandCQI-Short-r15 [1] SEQUENCE {
            k-r15 [0] INTEGER (1..4),
            periodicityFactor-r15 [1] ENUMERATED { n2(0), n4(1) }
         }
      } OPTIONAL -- Need OR
   }
}

AUL-Config-r15 ::= CHOICE {
   release [0] NULL,
   setup [1] SEQUENCE {
      aul-CRNTI-r15 [0] C-RNTI,
      aul-Subframes-r15 [1] BIT STRING  (SIZE (40)),
      aul-HARQ-Processes-r15 [2] INTEGER (1..16),
      transmissionModeUL-AUL-r15 [3] ENUMERATED { tm1(0), tm2(1) },
      aul-StartingFullBW-InsideMCOT-r15 [4] BIT STRING  (SIZE (5)),
      aul-StartingFullBW-OutsideMCOT-r15 [5] BIT STRING  (SIZE (7)),
      aul-StartingPartialBW-InsideMCOT-r15 [6] ENUMERATED { o34(0), o43(1), 
         o52(2), o61(3), oOS1(4) },
      aul-StartingPartialBW-OutsideMCOT-r15 [7] ENUMERATED { o16(0), o25(1), 
         o34(2), o43(3), o52(4), o61(5), oOS1(6) },
      aul-RetransmissionTimer-r15 [8] ENUMERATED { psf4(0), psf5(1), psf6(2), 
         psf8(3), psf10(4), psf12(5), psf20(6), psf28(7), psf37(8), psf44(9), 
         psf68(10), psf84(11), psf100(12), psf116(13), psf132(14), psf164(15), 
         psf324(16) },
      endingSymbolAUL-r15 [9] INTEGER (12..13),
      subframeOffsetCOT-Sharing-r15 [10] INTEGER (2..4),
      contentionWindowSizeTimer-r15 [11] ENUMERATED { n0(0), n5(1), n10(2) }
   }
}

PUSCH-ModeConfigLAA-r15 ::= SEQUENCE {
   laa-PUSCH-Mode1 [0] BOOLEAN,
   laa-PUSCH-Mode2 [1] BOOLEAN,
   laa-PUSCH-Mode3 [2] BOOLEAN
}

LAA-SCellConfiguration-v1530 ::= SEQUENCE {
   aul-Config-r15 [0] EXPLICIT AUL-Config-r15 OPTIONAL, -- Need ON
   pusch-ModeConfigLAA-r15 [1] PUSCH-ModeConfigLAA-r15 OPTIONAL -- Need OR
}

PUSCH-ConfigDedicatedScell-v1530 ::= SEQUENCE {
   uci-OnPUSCH-r15 [0] EXPLICIT CHOICE {
      release [0] NULL,
      setup [1] SEQUENCE {
         betaOffsetAUL-r15 [0] INTEGER (0..15)
      }
   }
}

PhysicalConfigDedicatedSCell-r10 ::= SEQUENCE {
--DL configuration as well as configuration applicable for DL and UL
   nonUL-Configuration-r10 [0] SEQUENCE {
      antennaInfo-r10 [0] AntennaInfoDedicated-r10 OPTIONAL, -- Need ON
      crossCarrierSchedulingConfig-r10 [1] CrossCarrierSchedulingConfig-r10
          OPTIONAL, -- Need ON
      csi-RS-Config-r10 [2] CSI-RS-Config-r10 OPTIONAL, -- Need ON
      pdsch-ConfigDedicated-r10 [3] PDSCH-ConfigDedicated OPTIONAL -- Need ON
   } OPTIONAL, -- Cond SCellAdd
--UL configuration
   ul-Configuration-r10 [1] SEQUENCE {
      antennaInfoUL-r10 [0] AntennaInfoUL-r10 OPTIONAL, -- Need ON
      pusch-ConfigDedicatedSCell-r10 [1] PUSCH-ConfigDedicatedSCell-r10
          OPTIONAL, -- Cond PUSCH-SCell1
      uplinkPowerControlDedicatedSCell-r10 [2] 
         UplinkPowerControlDedicatedSCell-r10 OPTIONAL, -- Need ON
      cqi-ReportConfigSCell-r10 [3] CQI-ReportConfigSCell-r10 OPTIONAL, -- Need ON
      soundingRS-UL-ConfigDedicated-r10 [4] EXPLICIT 
         SoundingRS-UL-ConfigDedicated OPTIONAL, -- Need ON
      soundingRS-UL-ConfigDedicated-v1020 [5] 
         SoundingRS-UL-ConfigDedicated-v1020 OPTIONAL, -- Need ON
      soundingRS-UL-ConfigDedicatedAperiodic-r10 [6] EXPLICIT 
         SoundingRS-UL-ConfigDedicatedAperiodic-r10 OPTIONAL -- Need ON
   } OPTIONAL,
   ...,
   [[
      csi-RS-ConfigNZPToReleaseList-r11 [2] CSI-RS-ConfigNZPToReleaseList-r11
          OPTIONAL,
      csi-RS-ConfigNZPToAddModList-r11 [3] CSI-RS-ConfigNZPToAddModList-r11
          OPTIONAL,
      csi-RS-ConfigZPToReleaseList-r11 [4] CSI-RS-ConfigZPToReleaseList-r11
          OPTIONAL,
      csi-RS-ConfigZPToAddModList-r11 [5] CSI-RS-ConfigZPToAddModList-r11
          OPTIONAL,
      epdcch-Config-r11 [6] EPDCCH-Config-r11 OPTIONAL,
      pdsch-ConfigDedicated-v1130 [7] PDSCH-ConfigDedicated-v1130 OPTIONAL,
      cqi-ReportConfig-v1130 [8] CQI-ReportConfig-v1130 OPTIONAL,
      pusch-ConfigDedicated-v1130 [9] PUSCH-ConfigDedicated-v1130 OPTIONAL,
      uplinkPowerControlDedicatedSCell-v1130 [10] 
         UplinkPowerControlDedicated-v1130 OPTIONAL
   ]],
   [[
      antennaInfo-v1250 [11] AntennaInfoDedicated-v1250 OPTIONAL,
      eimta-MainConfigSCell-r12 [12] EXPLICIT EIMTA-MainConfigServCell-r12
          OPTIONAL,
      cqi-ReportConfigSCell-v1250 [13] CQI-ReportConfig-v1250 OPTIONAL,
      uplinkPowerControlDedicatedSCell-v1250 [14] 
         UplinkPowerControlDedicated-v1250 OPTIONAL,
      csi-RS-Config-v1250 [15] CSI-RS-Config-v1250 OPTIONAL
   ]],
   [[
      pdsch-ConfigDedicated-v1280 [16] PDSCH-ConfigDedicated-v1280 OPTIONAL
   ]],
   [[
      pucch-Cell-r13 [17] ENUMERATED { true(0) } OPTIONAL,
      pucch-SCell [18] EXPLICIT CHOICE {
         release [0] NULL,
         setup [1] SEQUENCE {
            pucch-ConfigDedicated-r13 [0] PUCCH-ConfigDedicated-r13 OPTIONAL, -- Need ON
            schedulingRequestConfig-r13 [1] EXPLICIT 
               SchedulingRequestConfigSCell-r13 OPTIONAL, -- Need ON
            tpc-PDCCH-ConfigPUCCH-SCell-r13 [2] EXPLICIT 
               TPC-PDCCH-ConfigSCell-r13 OPTIONAL, -- Need ON
            pusch-ConfigDedicated-r13 [3] PUSCH-ConfigDedicated-r13 OPTIONAL, -- Cond PUSCH-SCell
            uplinkPowerControlDedicated-r13 [4] 
               UplinkPowerControlDedicatedSCell-v1310 OPTIONAL -- Need ON
         }
      } OPTIONAL,
      crossCarrierSchedulingConfig-r13 [19] CrossCarrierSchedulingConfig-r13
          OPTIONAL,
      pdcch-ConfigSCell-r13 [20] PDCCH-ConfigSCell-r13 OPTIONAL,
      cqi-ReportConfig-v1310 [21] CQI-ReportConfig-v1310 OPTIONAL,
      pdsch-ConfigDedicated-v1310 [22] PDSCH-ConfigDedicated-v1310 OPTIONAL,
      soundingRS-UL-ConfigDedicated-v1310 [23] EXPLICIT 
         SoundingRS-UL-ConfigDedicated-v1310 OPTIONAL,
      soundingRS-UL-ConfigDedicatedUpPTsExt-r13 [24] EXPLICIT 
         SoundingRS-UL-ConfigDedicatedUpPTsExt-r13 OPTIONAL,
      soundingRS-UL-ConfigDedicatedAperiodic-v1310 [25] EXPLICIT 
         SoundingRS-UL-ConfigDedicatedAperiodic-v1310 OPTIONAL,
      soundingRS-UL-ConfigDedicatedAperiodicUpPTsExt-r13 [26] EXPLICIT 
         SoundingRS-UL-ConfigDedicatedAperiodicUpPTsExt-r13 OPTIONAL,
      csi-RS-Config-v1310 [27] CSI-RS-Config-v1310 OPTIONAL,
      laa-SCellConfiguration-r13 [28] LAA-SCellConfiguration-r13 OPTIONAL,
      csi-RS-ConfigNZPToAddModListExt-r13 [29] 
         CSI-RS-ConfigNZPToAddModListExt-r13 OPTIONAL,
      csi-RS-ConfigNZPToReleaseListExt-r13 [30] 
         CSI-RS-ConfigNZPToReleaseListExt-r13 OPTIONAL
   ]],
   [[
      cqi-ReportConfig-v1320 [31] CQI-ReportConfig-v1320 OPTIONAL
   ]],
   [[
      laa-SCellConfiguration-v1430 [32] LAA-SCellConfiguration-v1430 OPTIONAL,
      typeB-SRS-TPC-PDCCH-Config-r14 [33] EXPLICIT SRS-TPC-PDCCH-Config-r14
          OPTIONAL,
      uplinkPUSCH-LessPowerControlDedicated-v1430 [34] 
         UplinkPUSCH-LessPowerControlDedicated-v1430 OPTIONAL,
      soundingRS-UL-PeriodicConfigDedicatedList-r14 [35] SEQUENCE (SIZE (1..2)
         ) OF SoundingRS-UL-ConfigDedicated OPTIONAL,
      soundingRS-UL-PeriodicConfigDedicatedUpPTsExtList-r14 [36] SEQUENCE (
         SIZE (1..4)) OF SoundingRS-UL-ConfigDedicatedUpPTsExt-r13 OPTIONAL,
      soundingRS-UL-AperiodicConfigDedicatedList-r14 [37] SEQUENCE (SIZE (1..2)
         ) OF SoundingRS-AperiodicSet-r14 OPTIONAL,
      soundingRS-UL-ConfigDedicatedApUpPTsExtList-r14 [38] SEQUENCE (SIZE (1..4)
         ) OF SoundingRS-AperiodicSetUpPTsExt-r14 OPTIONAL,
      must-Config-r14 [39] EXPLICIT CHOICE {
         release [0] NULL,
         setup [1] SEQUENCE {
            k-max-r14 [0] ENUMERATED { l1(0), l3(1) },
            p-a-must-r14 [1] ENUMERATED { dB-6(0), dB-4dot77(1), dB-3(2), 
               dB-1dot77(3), dB0(4), dB1(5), dB2(6), dB3(7) } OPTIONAL -- Need ON
         }
      } OPTIONAL,
      pusch-ConfigDedicated-v1430 [40] PUSCH-ConfigDedicatedSCell-v1430
          OPTIONAL,
      csi-RS-Config-v1430 [41] CSI-RS-Config-v1430 OPTIONAL,
      csi-RS-ConfigZP-ApList-r14 [42] EXPLICIT CSI-RS-ConfigZP-ApList-r14
          OPTIONAL,
      cqi-ReportConfig-v1430 [43] CQI-ReportConfig-v1430 OPTIONAL,
      semiOpenLoop-r14 [44] BOOLEAN OPTIONAL,
      pdsch-ConfigDedicatedSCell-v1430 [45] PDSCH-ConfigDedicatedSCell-v1430
          OPTIONAL
   ]],
   [[
      csi-RS-Config-v1480 [46] CSI-RS-Config-v1480 OPTIONAL
   ]],
   [[
      physicalConfigDedicatedSTTI-r15 [47] EXPLICIT 
         PhysicalConfigDedicatedSTTI-r15 OPTIONAL,
      pdsch-ConfigDedicated-v1530 [48] PDSCH-ConfigDedicated-v1530 OPTIONAL,
      dummy [49] CQI-ReportConfig-v1530 OPTIONAL,
      cqi-ReportConfigSCell-r15 [50] CQI-ReportConfigSCell-r15 OPTIONAL,
      cqi-ShortConfigSCell-r15 [51] EXPLICIT CQI-ShortConfigSCell-r15 OPTIONAL
         ,
      csi-RS-Config-v1530 [52] CSI-RS-Config-v1530 OPTIONAL,
      uplinkPowerControlDedicatedSCell-v1530 [53] 
         UplinkPowerControlDedicated-v1530 OPTIONAL,
      laa-SCellConfiguration-v1530 [54] LAA-SCellConfiguration-v1530 OPTIONAL,
      pusch-ConfigDedicated-v1530 [55] PUSCH-ConfigDedicatedScell-v1530
          OPTIONAL,
      semiStaticCFI-Config-r15 [56] EXPLICIT CHOICE {
         release [0] NULL,
         setup [1] EXPLICIT CHOICE {
            cfi-Config-r15 [0] CFI-Config-r15,
            cfi-PatternConfig-r15 [1] CFI-PatternConfig-r15
         }
      } OPTIONAL,
      blindPDSCH-Repetition-Config-r15 [57] EXPLICIT CHOICE {
         release [0] NULL,
         setup [1] SEQUENCE {
            blindSubframePDSCH-Repetitions-r15 [0] BOOLEAN,
            blindSlotSubslotPDSCH-Repetitions-r15 [1] BOOLEAN,
            maxNumber-SubframePDSCH-Repetitions-r15 [2] ENUMERATED { n4(0), 
               n6(1) } OPTIONAL, -- Need ON
            maxNumber-SlotSubslotPDSCH-Repetitions-r15 [3] ENUMERATED { n4(0), 
               n6(1) } OPTIONAL, -- Need ON
            rv-SubframePDSCH-Repetitions-r15 [4] ENUMERATED { dlrvseq1(0), 
               dlrvseq2(1) } OPTIONAL, -- Need ON
            rv-SlotsublotPDSCH-Repetitions-r15 [5] ENUMERATED { dlrvseq1(0), 
               dlrvseq2(1) } OPTIONAL, -- Need ON
            numberOfProcesses-SubframePDSCH-Repetitions-r15 [6] INTEGER (1..16)
                OPTIONAL, -- Need ON
            numberOfProcesses-SlotSubslotPDSCH-Repetitions-r15 [7] INTEGER (1..16)
                OPTIONAL, -- Need ON
            mcs-restrictionSubframePDSCH-Repetitions-r15 [8] ENUMERATED { n0(0)
               , n1(1) } OPTIONAL, -- Need ON
            mcs-restrictionSlotSubslotPDSCH-Repetitions-r15 [9] ENUMERATED { 
               n0(0), n1(1) } OPTIONAL -- Need ON
         }
      } OPTIONAL
   ]],
   [[
      spucch-Config-v1550 [58] EXPLICIT SPUCCH-Config-v1550 OPTIONAL
   ]]
}

MAC-MainConfigSCell-r11 ::= SEQUENCE {
   stag-Id-r11 [0] STAG-Id-r11 OPTIONAL,
   ...
}

PhysicalConfigDedicatedSCell-v1370 ::= SEQUENCE {
   pucch-SCell-v1370 [0] EXPLICIT CHOICE {
      release [0] NULL,
      setup [1] SEQUENCE {
         pucch-ConfigDedicated-v1370 [0] PUCCH-ConfigDedicated-v1370 OPTIONAL -- Cond PUCCH-Format4or5
      }
   }
}

RadioResourceConfigDedicatedSCell-r10 ::= SEQUENCE {
--UE specific configuration extensions applicable for an SCell
   physicalConfigDedicatedSCell-r10 [0] PhysicalConfigDedicatedSCell-r10
       OPTIONAL,
   ...,
   [[
      mac-MainConfigSCell-r11 [1] MAC-MainConfigSCell-r11 OPTIONAL
   ]],
   [[
      naics-Info-r12 [2] EXPLICIT NAICS-AssistanceInfo-r12 OPTIONAL
   ]],
   [[
      neighCellsCRS-InfoSCell-r13 [3] EXPLICIT NeighCellsCRS-Info-r13 OPTIONAL
   ]],
   [[
      physicalConfigDedicatedSCell-v1370 [4] PhysicalConfigDedicatedSCell-v1370
          OPTIONAL
   ]],
   [[
      crs-IntfMitigEnabled-r15 [5] BOOLEAN OPTIONAL,
      neighCellsCRS-Info-r15 [6] EXPLICIT NeighCellsCRS-Info-r15 OPTIONAL,
      sps-Config-v1530 [7] SPS-Config-v1530 OPTIONAL
   ]]
}

SCellToAddMod-r10 ::= SEQUENCE {
   sCellIndex-r10 [0] SCellIndex-r10,
   cellIdentification-r10 [1] SEQUENCE {
      physCellId-r10 [0] PhysCellId,
      dl-CarrierFreq-r10 [1] ARFCN-ValueEUTRA
   } OPTIONAL, -- Cond SCellAdd
   radioResourceConfigCommonSCell-r10 [2] RadioResourceConfigCommonSCell-r10
       OPTIONAL, -- Cond SCellAdd
   radioResourceConfigDedicatedSCell-r10 [3] 
      RadioResourceConfigDedicatedSCell-r10 OPTIONAL,
   ...,
   [[
      dl-CarrierFreq-v1090 [4] ARFCN-ValueEUTRA-v9e0 OPTIONAL
   ]],
   [[
      antennaInfoDedicatedSCell-v10i0 [5] AntennaInfoDedicated-v10i0 OPTIONAL
   ]],
   [[
      srs-SwitchFromServCellIndex-r14 [6] INTEGER (0..31) OPTIONAL
   ]],
   [[
      sCellState-r15 [7] ENUMERATED { activated(0), dormant(1) } OPTIONAL
   ]]
}

SCellToAddModList-r10 ::= SEQUENCE (SIZE (1..maxSCell-r10)) OF SCellToAddMod-r10

PowerCoordinationInfo-r12 ::= SEQUENCE {
   p-MeNB-r12 [0] INTEGER (1..16),
   p-SeNB-r12 [1] INTEGER (1..16),
   powerControlMode-r12 [2] INTEGER (1..2)
}

DRB-ToAddModSCG-r12 ::= SEQUENCE {
   drb-Identity-r12 [0] DRB-Identity,
   drb-Type-r12 [1] EXPLICIT CHOICE {
      split-r12 [0] NULL,
      scg-r12 [1] SEQUENCE {
         eps-BearerIdentity-r12 [0] INTEGER (0..15) OPTIONAL, -- Cond DRB-Setup
         pdcp-Config-r12 [1] PDCP-Config OPTIONAL -- Cond PDCP-S
      }
   } OPTIONAL, -- Cond SetupS2
   rlc-ConfigSCG-r12 [2] EXPLICIT RLC-Config OPTIONAL, -- Cond SetupS
   rlc-Config-v1250 [3] RLC-Config-v1250 OPTIONAL, -- Need ON
   logicalChannelIdentitySCG-r12 [4] INTEGER (3..10) OPTIONAL, -- Cond DRB-SetupS
   logicalChannelConfigSCG-r12 [5] LogicalChannelConfig OPTIONAL,
   ...,
   [[
      rlc-Config-v1430 [6] EXPLICIT RLC-Config-v1430 OPTIONAL
   ]],
   [[
      logicalChannelIdentitySCG-r15 [7] INTEGER (32..38) OPTIONAL,
      rlc-Config-v1530 [8] EXPLICIT RLC-Config-v1530 OPTIONAL,
      rlc-BearerConfigSecondary-r15 [9] EXPLICIT RLC-BearerConfig-r15 OPTIONAL
   ]],
   [[
      rlc-Config-v1560 [10] RLC-Config-v1510 OPTIONAL
   ]]
}

DRB-ToAddModListSCG-r12 ::= SEQUENCE (SIZE (1..maxDRB)) OF DRB-ToAddModSCG-r12

RLF-TimersAndConstantsSCG-r12 ::= CHOICE {
   release [0] NULL,
   setup [1] SEQUENCE {
      t313-r12 [0] ENUMERATED { ms0(0), ms50(1), ms100(2), ms200(3), ms500(4), 
         ms1000(5), ms2000(6) },
      n313-r12 [1] ENUMERATED { n1(0), n2(1), n3(2), n4(3), n6(4), n8(5), 
         n10(6), n20(7) },
      n314-r12 [2] ENUMERATED { n1(0), n2(1), n3(2), n4(3), n5(4), n6(5), n8(6)
         , n10(7) },
      ...
   }
}

DRB-ToAddModListSCG-r15 ::= SEQUENCE (SIZE (1..maxDRB-r15)) OF DRB-ToAddModSCG-r12

SRB-ToReleaseList-r15 ::= SEQUENCE (SIZE (1..2)) OF INTEGER (1..2)

RadioResourceConfigDedicatedSCG-r12 ::= SEQUENCE {
   drb-ToAddModListSCG-r12 [0] DRB-ToAddModListSCG-r12 OPTIONAL, -- Need ON
   mac-MainConfigSCG-r12 [1] MAC-MainConfig OPTIONAL, -- Need ON
   rlf-TimersAndConstantsSCG-r12 [2] EXPLICIT RLF-TimersAndConstantsSCG-r12
       OPTIONAL,
   ...,
   [[
      drb-ToAddModListSCG-r15 [3] DRB-ToAddModListSCG-r15 OPTIONAL
   ]],
   [[
      srb-ToAddModListSCG-r15 [4] SRB-ToAddModList OPTIONAL,
      srb-ToReleaseListSCG-r15 [5] SRB-ToReleaseList-r15 OPTIONAL
   ]],
   [[
      drb-ToReleaseListSCG-r15 [6] DRB-ToReleaseList-r15 OPTIONAL
   ]]
}

UplinkPowerControlCommonPSCell-r12 ::= SEQUENCE {
--For uplink power control the additional/ missing fields are signalled (compared to SCell)
   deltaF-PUCCH-Format3-r12 [0] ENUMERATED { deltaF-1(0), deltaF0(1), 
      deltaF1(2), deltaF2(3), deltaF3(4), deltaF4(5), deltaF5(6), deltaF6(7) },
   deltaF-PUCCH-Format1bCS-r12 [1] ENUMERATED { deltaF1(0), deltaF2(1), 
      spare2(2), spare1(3) },
   p0-NominalPUCCH-r12 [2] INTEGER (-127..-96),
   deltaFList-PUCCH-r12 [3] DeltaFList-PUCCH
}

RadioResourceConfigCommonPSCell-r12 ::= SEQUENCE {
   basicFields-r12 [0] RadioResourceConfigCommonSCell-r10,
   pucch-ConfigCommon-r12 [1] PUCCH-ConfigCommon,
   rach-ConfigCommon-r12 [2] RACH-ConfigCommon,
   uplinkPowerControlCommonPSCell-r12 [3] UplinkPowerControlCommonPSCell-r12,
   ...,
   [[
      uplinkPowerControlCommonPSCell-v1310 [4] UplinkPowerControlCommon-v1310
          OPTIONAL
   ]],
   [[
      uplinkPowerControlCommonPSCell-v1530 [5] UplinkPowerControlCommon-v1530
          OPTIONAL
   ]]
}

RadioResourceConfigDedicatedPSCell-r12 ::= SEQUENCE {
--UE specific configuration extensions applicable for an PSCell
   physicalConfigDedicatedPSCell-r12 [0] PhysicalConfigDedicated OPTIONAL, -- Need ON
   sps-Config-r12 [1] SPS-Config OPTIONAL, -- Need ON
   naics-Info-r12 [2] EXPLICIT NAICS-AssistanceInfo-r12 OPTIONAL,
   ...,
   [[
      neighCellsCRS-InfoPSCell-r13 [3] EXPLICIT NeighCellsCRS-Info-r13 OPTIONAL
   ]],
   [[
      sps-Config-v1430 [4] SPS-Config-v1430 OPTIONAL
   ]],
   [[
      sps-Config-v1530 [5] SPS-Config-v1530 OPTIONAL,
      crs-IntfMitigEnabled-r15 [6] BOOLEAN OPTIONAL,
      neighCellsCRS-Info-r15 [7] EXPLICIT NeighCellsCRS-Info-r15 OPTIONAL
   ]],
   [[
      sps-Config-v1540 [8] SPS-Config-v1540 OPTIONAL
   ]]
}

RadioResourceConfigDedicatedPSCell-v1370 ::= SEQUENCE {
   physicalConfigDedicatedPSCell-v1370 [0] PhysicalConfigDedicated-v1370
       OPTIONAL -- Need ON
}

RadioResourceConfigDedicatedPSCell-v13c0 ::= SEQUENCE {
   physicalConfigDedicatedPSCell-v13c0 [0] PhysicalConfigDedicated-v13c0
}

PSCellToAddMod-r12 ::= SEQUENCE {
   sCellIndex-r12 [0] SCellIndex-r10,
   cellIdentification-r12 [1] SEQUENCE {
      physCellId-r12 [0] PhysCellId,
      dl-CarrierFreq-r12 [1] ARFCN-ValueEUTRA-r9
   } OPTIONAL, -- Cond SCellAdd
   radioResourceConfigCommonPSCell-r12 [2] RadioResourceConfigCommonPSCell-r12
       OPTIONAL, -- Cond SCellAdd
   radioResourceConfigDedicatedPSCell-r12 [3] 
      RadioResourceConfigDedicatedPSCell-r12 OPTIONAL,
   ...,
   [[
      antennaInfoDedicatedPSCell-v1280 [4] AntennaInfoDedicated-v10i0 OPTIONAL
   ]],
   [[
      sCellIndex-r13 [5] SCellIndex-r13 OPTIONAL
   ]],
   [[
      radioResourceConfigDedicatedPSCell-v1370 [6] 
         RadioResourceConfigDedicatedPSCell-v1370 OPTIONAL
   ]],
   [[
      radioResourceConfigDedicatedPSCell-v13c0 [7] 
         RadioResourceConfigDedicatedPSCell-v13c0 OPTIONAL
   ]]
}

MobilityControlInfoSCG-r12 ::= SEQUENCE {
   t307-r12 [0] ENUMERATED { ms50(0), ms100(1), ms150(2), ms200(3), ms500(4), 
      ms1000(5), ms2000(6), spare1(7) },
   ue-IdentitySCG-r12 [1] C-RNTI OPTIONAL, -- Cond SCGEst,
   rach-ConfigDedicated-r12 [2] RACH-ConfigDedicated OPTIONAL, -- Need OP
   cipheringAlgorithmSCG-r12 [3] CipheringAlgorithm-r12 OPTIONAL,
   ...,
   [[
      makeBeforeBreakSCG-r14 [4] ENUMERATED { true(0) } OPTIONAL,
      rach-SkipSCG-r14 [5] RACH-Skip-r14 OPTIONAL
   ]]
}

SCellToReleaseListExt-r13 ::= SEQUENCE (SIZE (1..maxSCell-r13)) OF SCellIndex-r13

SCellToAddModExt-r13 ::= SEQUENCE {
   sCellIndex-r13 [0] SCellIndex-r13,
   cellIdentification-r13 [1] SEQUENCE {
      physCellId-r13 [0] PhysCellId,
      dl-CarrierFreq-r13 [1] ARFCN-ValueEUTRA-r9
   } OPTIONAL, -- Cond SCellAdd
   radioResourceConfigCommonSCell-r13 [2] RadioResourceConfigCommonSCell-r10
       OPTIONAL, -- Cond SCellAdd
   radioResourceConfigDedicatedSCell-r13 [3] 
      RadioResourceConfigDedicatedSCell-r10 OPTIONAL, -- Cond SCellAdd2
   antennaInfoDedicatedSCell-r13 [4] AntennaInfoDedicated-v10i0 OPTIONAL -- Need ON
}

SCellToAddModListExt-r13 ::= SEQUENCE (SIZE (1..maxSCell-r13)) OF SCellToAddModExt-r13

RadioResourceConfigCommonSCell-v1440 ::= SEQUENCE {
   ul-Configuration-v1440 [0] SEQUENCE {
      ul-FreqInfo-v1440 [0] SEQUENCE {
         additionalSpectrumEmissionSCell-v1440 [0] 
            AdditionalSpectrumEmission-v10l0
      }
   }
}

RadioResourceConfigCommonPSCell-v1440 ::= SEQUENCE {
   basicFields-v1440 [0] RadioResourceConfigCommonSCell-v1440
}

PSCellToAddMod-v1440 ::= SEQUENCE {
   radioResourceConfigCommonPSCell-r14 [0] 
      RadioResourceConfigCommonPSCell-v1440 OPTIONAL
}

SCellGroupToReleaseList-r15 ::= SEQUENCE (SIZE (1..maxSCellGroups-r15)) OF SCellGroupIndex-r15

SCellConfigCommon-r15 ::= SEQUENCE {
   radioResourceConfigCommonSCell-r15 [0] RadioResourceConfigCommonSCell-r10
       OPTIONAL, -- Need ON
   radioResourceConfigDedicatedSCell-r15 [1] 
      RadioResourceConfigDedicatedSCell-r10 OPTIONAL, -- Need ON
   antennaInfoDedicatedSCell-r15 [2] AntennaInfoDedicated-v10i0 OPTIONAL -- Need ON
}

SCellGroupToAddMod-r15 ::= SEQUENCE {
   sCellGroupIndex-r15 [0] SCellGroupIndex-r15,
   sCellConfigCommon-r15 [1] SCellConfigCommon-r15 OPTIONAL, -- Need ON
   sCellToReleaseList-r15 [2] SCellToReleaseListExt-r13 OPTIONAL, -- Need ON
   sCellToAddModList-r15 [3] SCellToAddModListExt-r13 OPTIONAL -- Need ON
}

SCellGroupToAddModList-r15 ::= SEQUENCE (SIZE (1..maxSCellGroups-r15)) OF SCellGroupToAddMod-r15

TDM-PatternConfig-r15 ::= CHOICE {
   release [0] NULL,
   setup [1] SEQUENCE {
      subframeAssignment-r15 [0] SubframeAssignment-r15,
      harq-Offset-r15 [1] INTEGER (0..9)
   }
}

SCG-ConfigPartSCG-r12 ::= SEQUENCE {
   radioResourceConfigDedicatedSCG-r12 [0] RadioResourceConfigDedicatedSCG-r12
       OPTIONAL, -- Need ON
   sCellToReleaseListSCG-r12 [1] SCellToReleaseList-r10 OPTIONAL, -- Need ON
   pSCellToAddMod-r12 [2] PSCellToAddMod-r12 OPTIONAL, -- Need ON
   sCellToAddModListSCG-r12 [3] SCellToAddModList-r10 OPTIONAL, -- Need ON
   mobilityControlInfoSCG-r12 [4] MobilityControlInfoSCG-r12 OPTIONAL,
   ...,
   [[
      sCellToReleaseListSCG-Ext-r13 [5] SCellToReleaseListExt-r13 OPTIONAL,
      sCellToAddModListSCG-Ext-r13 [6] SCellToAddModListExt-r13 OPTIONAL
   ]],
   [[
      sCellToAddModListSCG-Ext-v1370 [7] SCellToAddModListExt-v1370 OPTIONAL
   ]],
   [[
      pSCellToAddMod-v1440 [8] PSCellToAddMod-v1440 OPTIONAL
   ]],
   [[
      sCellGroupToReleaseListSCG-r15 [9] SCellGroupToReleaseList-r15 OPTIONAL,
      sCellGroupToAddModListSCG-r15 [10] SCellGroupToAddModList-r15 OPTIONAL
   ]],
   [[
      measConfigSN-r15 [11] MeasConfig OPTIONAL,
      tdm-PatternConfigNE-DC-r15 [12] EXPLICIT TDM-PatternConfig-r15 OPTIONAL
   ]],
   [[
      p-MaxEUTRA-r15 [13] P-Max OPTIONAL
   ]]
}

SCG-Configuration-r12 ::= CHOICE {
   release [0] NULL,
   setup [1] SEQUENCE {
      scg-ConfigPartMCG-r12 [0] SEQUENCE {
         scg-Counter-r12 [0] INTEGER (0..65535) OPTIONAL, -- Need ON
         powerCoordinationInfo-r12 [1] PowerCoordinationInfo-r12 OPTIONAL,
         ...
      } OPTIONAL, -- Need ON
      scg-ConfigPartSCG-r12 [1] SCG-ConfigPartSCG-r12 OPTIONAL -- Need ON
   }
}

SL-SyncTxControl-r12 ::= SEQUENCE {
   networkControlledSyncTx-r12 [0] ENUMERATED { on(0), off(1) } OPTIONAL -- Need OP
}

SL-TF-IndexPair-r12 ::= SEQUENCE {
   discSF-Index-r12 [0] INTEGER (1..200) OPTIONAL, -- Need ON
   discPRB-Index-r12 [1] INTEGER (1..50) OPTIONAL -- Need ON
}

SL-TF-IndexPairList-r12 ::= SEQUENCE (SIZE (1..maxSL-TF-IndexPair-r12)) OF SL-TF-IndexPair-r12

SL-HoppingConfigDisc-r12 ::= SEQUENCE {
   a-r12 [0] INTEGER (1..200),
   b-r12 [1] INTEGER (1..10),
   c-r12 [2] ENUMERATED { n1(0), n5(1) }
}

SL-TxPoolToReleaseList-r12 ::= SEQUENCE (SIZE (1..maxSL-TxPool-r12)) OF SL-TxPoolIdentity-r12

SL-DiscTxPoolToAddMod-r12 ::= SEQUENCE {
   poolIdentity-r12 [0] SL-TxPoolIdentity-r12,
   pool-r12 [1] SL-DiscResourcePool-r12
}

SL-DiscTxPoolToAddModList-r12 ::= SEQUENCE (SIZE (1..maxSL-TxPool-r12)) OF 
   SL-DiscTxPoolToAddMod-r12

SL-TF-IndexPair-r12b ::= SEQUENCE {
   discSF-Index-r12b [0] INTEGER (0..209) OPTIONAL, -- Need ON
   discPRB-Index-r12b [1] INTEGER (0..49) OPTIONAL -- Need ON
}

SL-TF-IndexPairList-r12b ::= SEQUENCE (SIZE (1..maxSL-TF-IndexPair-r12)) OF SL-TF-IndexPair-r12b

SL-DiscTxConfigScheduled-r13 ::= SEQUENCE {
   discTxConfig-r13 [0] SL-DiscResourcePool-r12 OPTIONAL, -- Need ON
   discTF-IndexList-r13 [1] SL-TF-IndexPairList-r12b OPTIONAL, -- Need ON
   discHoppingConfig-r13 [2] SL-HoppingConfigDisc-r12 OPTIONAL,
   ...
}

SL-DiscTxPoolDedicated-r13 ::= SEQUENCE {
   poolToReleaseList-r13 [0] SL-TxPoolToReleaseList-r12 OPTIONAL, -- Need ON
   poolToAddModList-r13 [1] SL-DiscTxPoolToAddModList-r12 OPTIONAL -- Need ON
}

SL-DiscTxRefCarrierDedicated-r13 ::= CHOICE {
   pCell [0] NULL,
   sCell [1] SCellIndex-r10
}

SL-DiscTxResource-r13 ::= CHOICE {
   release [0] NULL,
   setup [1] EXPLICIT CHOICE {
      scheduled-r13 [0] SL-DiscTxConfigScheduled-r13,
      ue-Selected-r13 [1] SL-DiscTxPoolDedicated-r13
   }
}

SL-DiscTxResourceInfoPerFreq-r13 ::= SEQUENCE {
   discTxCarrierFreq-r13 [0] ARFCN-ValueEUTRA-r9,
   discTxResources-r13 [1] EXPLICIT SL-DiscTxResource-r13 OPTIONAL, -- Need OR
   discTxResourcesPS-r13 [2] EXPLICIT SL-DiscTxResource-r13 OPTIONAL, -- Need OR
   discTxRefCarrierDedicated-r13 [3] EXPLICIT SL-DiscTxRefCarrierDedicated-r13
       OPTIONAL, -- Need OR
   discCellSelectionInfo-r13 [4] CellSelectionInfoNFreq-r13 OPTIONAL,
   ...
}

SL-DiscTxInfoInterFreqListAdd-r13 ::= SEQUENCE {
   discTxFreqToAddModList-r13 [0] SEQUENCE (SIZE (1..maxFreq)) OF 
      SL-DiscTxResourceInfoPerFreq-r13 OPTIONAL, -- Need ON
   discTxFreqToReleaseList-r13 [1] SEQUENCE (SIZE (1..maxFreq)) OF ARFCN-ValueEUTRA-r9
       OPTIONAL,
   ...
}

SL-GapPattern-r13 ::= SEQUENCE {
   gapPeriod-r13 [0] ENUMERATED { sf40(0), sf60(1), sf70(2), sf80(3), sf120(4)
      , sf140(5), sf160(6), sf240(7), sf280(8), sf320(9), sf640(10), sf1280(11)
      , sf2560(12), sf5120(13), sf10240(14) },
   gapOffset-r12 [1] EXPLICIT SL-OffsetIndicator-r12,
   gapSubframeBitmap-r13 [2] BIT STRING  (SIZE (1..10240)),
   ...
}

SL-GapPatternList-r13 ::= SEQUENCE (SIZE (1..maxSL-GP-r13)) OF SL-GapPattern-r13

SL-GapConfig-r13 ::= SEQUENCE {
   gapPatternList-r13 [0] SL-GapPatternList-r13
}

SL-DiscSysInfoToReportFreqList-r13 ::= SEQUENCE (SIZE (1..maxFreq)) OF 
   ARFCN-ValueEUTRA-r9

SL-DiscConfig-r12 ::= SEQUENCE {
   discTxResources-r12 [0] EXPLICIT CHOICE {
      release [0] NULL,
      setup [1] EXPLICIT CHOICE {
         scheduled-r12 [0] SEQUENCE {
            discTxConfig-r12 [0] SL-DiscResourcePool-r12 OPTIONAL, -- Need ON
            discTF-IndexList-r12 [1] SL-TF-IndexPairList-r12 OPTIONAL, -- Need ON
            discHoppingConfig-r12 [2] SL-HoppingConfigDisc-r12 OPTIONAL
               -- Need ON
         },
         ue-Selected-r12 [1] SEQUENCE {
            discTxPoolDedicated-r12 [0] SEQUENCE {
               poolToReleaseList-r12 [0] SL-TxPoolToReleaseList-r12 OPTIONAL, -- Need ON
               poolToAddModList-r12 [1] SL-DiscTxPoolToAddModList-r12 OPTIONAL -- Need ON
            } OPTIONAL -- Need ON
         }
      }
   } OPTIONAL,
   ...,
   [[
      discTF-IndexList-v1260 [1] EXPLICIT CHOICE {
         release [0] NULL,
         setup [1] SEQUENCE {
            discTF-IndexList-r12b [0] SL-TF-IndexPairList-r12b
         }
      } OPTIONAL
   ]],
   [[
      discTxResourcesPS-r13 [2] EXPLICIT CHOICE {
         release [0] NULL,
         setup [1] EXPLICIT CHOICE {
            scheduled-r13 [0] SL-DiscTxConfigScheduled-r13,
            ue-Selected-r13 [1] SEQUENCE {
               discTxPoolPS-Dedicated-r13 [0] SL-DiscTxPoolDedicated-r13
            }
         }
      } OPTIONAL,
      discTxInterFreqInfo-r13 [3] EXPLICIT CHOICE {
         release [0] NULL,
         setup [1] SEQUENCE {
            discTxCarrierFreq-r13 [0] ARFCN-ValueEUTRA-r9 OPTIONAL, -- Need OR
            discTxRefCarrierDedicated-r13 [1] EXPLICIT 
               SL-DiscTxRefCarrierDedicated-r13 OPTIONAL, -- Need OR
            discTxInfoInterFreqListAdd-r13 [2] 
               SL-DiscTxInfoInterFreqListAdd-r13 OPTIONAL -- Need ON
         }
      } OPTIONAL,
      gapRequestsAllowedDedicated-r13 [4] BOOLEAN OPTIONAL,
      discRxGapConfig-r13 [5] EXPLICIT CHOICE {
         release [0] NULL,
         setup [1] SL-GapConfig-r13
      } OPTIONAL,
      discTxGapConfig-r13 [6] EXPLICIT CHOICE {
         release [0] NULL,
         setup [1] SL-GapConfig-r13
      } OPTIONAL,
      discSysInfoToReportConfig-r13 [7] EXPLICIT CHOICE {
         release [0] NULL,
         setup [1] SL-DiscSysInfoToReportFreqList-r13
      } OPTIONAL
   ]]
}

MAC-MainConfigSL-r12 ::= SEQUENCE {
   periodic-BSR-TimerSL [0] PeriodicBSR-Timer-r12 OPTIONAL, -- Need ON
   retx-BSR-TimerSL [1] RetxBSR-Timer-r12
}

SL-CommTxPoolToAddMod-r12 ::= SEQUENCE {
   poolIdentity-r12 [0] SL-TxPoolIdentity-r12,
   pool-r12 [1] SL-CommResourcePool-r12
}

SL-CommTxPoolToAddModList-r12 ::= SEQUENCE (SIZE (1..maxSL-TxPool-r12)) OF 
   SL-CommTxPoolToAddMod-r12

LogicalChGroupInfoList-r13 ::= SEQUENCE (SIZE (1..maxLCG-r13)) OF SL-PriorityList-r13

SL-TxPoolToReleaseListExt-r13 ::= SEQUENCE (SIZE (1..maxSL-TxPool-v1310)) OF 
   SL-TxPoolIdentity-v1310

SL-CommTxPoolToAddModExt-r13 ::= SEQUENCE {
   poolIdentity-v1310 [0] SL-TxPoolIdentity-v1310,
   pool-r13 [1] SL-CommResourcePool-r12
}

SL-CommTxPoolToAddModListExt-r13 ::= SEQUENCE (SIZE (1..maxSL-TxPool-v1310)) OF 
   SL-CommTxPoolToAddModExt-r13

SL-CommConfig-r12 ::= SEQUENCE {
   commTxResources-r12 [0] EXPLICIT CHOICE {
      release [0] NULL,
      setup [1] EXPLICIT CHOICE {
         scheduled-r12 [0] SEQUENCE {
            sl-RNTI-r12 [0] C-RNTI,
            mac-MainConfig-r12 [1] MAC-MainConfigSL-r12,
            sc-CommTxConfig-r12 [2] SL-CommResourcePool-r12,
            mcs-r12 [3] INTEGER (0..28) OPTIONAL -- Need OP
         },
         ue-Selected-r12 [1] SEQUENCE {
--Pool for normal usage
            commTxPoolNormalDedicated-r12 [0] SEQUENCE {
               poolToReleaseList-r12 [0] SL-TxPoolToReleaseList-r12 OPTIONAL, -- Need ON
               poolToAddModList-r12 [1] SL-CommTxPoolToAddModList-r12 OPTIONAL -- Need ON
            }
         }
      }
   } OPTIONAL,
   ...,
   [[
      commTxResources-v1310 [1] EXPLICIT CHOICE {
         release [0] NULL,
         setup [1] EXPLICIT CHOICE {
            scheduled-v1310 [0] SEQUENCE {
               logicalChGroupInfoList-r13 [0] LogicalChGroupInfoList-r13,
               multipleTx-r13 [1] BOOLEAN
            },
            ue-Selected-v1310 [1] SEQUENCE {
               commTxPoolNormalDedicatedExt-r13 [0] SEQUENCE {
                  poolToReleaseListExt-r13 [0] SL-TxPoolToReleaseListExt-r13
                      OPTIONAL, -- Need ON
                  poolToAddModListExt-r13 [1] SL-CommTxPoolToAddModListExt-r13
                      OPTIONAL -- Need ON
               }
            }
         }
      } OPTIONAL,
      commTxAllowRelayDedicated-r13 [2] BOOLEAN OPTIONAL
   ]]
}

WLAN-SuspendConfig-r14 ::= SEQUENCE {
   wlan-SuspendResumeAllowed-r14 [0] BOOLEAN OPTIONAL, -- Need ON
   wlan-SuspendTriggersStatusReport-r14 [1] BOOLEAN OPTIONAL -- Need ON
}

WLAN-MobilityConfig-r13 ::= SEQUENCE {
   wlan-ToReleaseList-r13 [0] WLAN-Id-List-r13 OPTIONAL, -- Need ON
   wlan-ToAddList-r13 [1] WLAN-Id-List-r13 OPTIONAL, -- Need ON
   associationTimer-r13 [2] ENUMERATED { s10(0), s30(1), s60(2), s120(3), 
      s240(4) } OPTIONAL, -- Need OR
   successReportRequested-r13 [3] ENUMERATED { true(0) } OPTIONAL,
   ...,
   [[
      wlan-SuspendConfig-r14 [4] WLAN-SuspendConfig-r14 OPTIONAL
   ]]
}

LWA-Config-r13 ::= SEQUENCE {
   lwa-MobilityConfig-r13 [0] WLAN-MobilityConfig-r13 OPTIONAL, -- Need ON
   lwa-WT-Counter-r13 [1] INTEGER (0..65535) OPTIONAL,
   ...,
   [[
      wt-MAC-Address-r14 [2] OCTET STRING (SIZE (6)) OPTIONAL
   ]]
}

LWA-Configuration-r13 ::= CHOICE {
   release [0] NULL,
   setup [1] SEQUENCE {
      lwa-Config-r13 [0] LWA-Config-r13
   }
}

IP-Address-r13 ::= CHOICE {
   ipv4-r13 [0] BIT STRING  (SIZE (32)),
   ipv6-r13 [1] BIT STRING  (SIZE (128))
}

IKE-Identity-r13 ::= SEQUENCE {
   idI-r13 [0] OCTET STRING
}

TunnelConfigLWIP-r13 ::= SEQUENCE {
   ip-Address-r13 [0] EXPLICIT IP-Address-r13,
   ike-Identity-r13 [1] IKE-Identity-r13,
   ...,
   [[
      lwip-Counter-r13 [2] INTEGER (0..65535) OPTIONAL
   ]]
}

LWIP-Config-r13 ::= SEQUENCE {
   lwip-MobilityConfig-r13 [0] WLAN-MobilityConfig-r13 OPTIONAL, -- Need ON
   tunnelConfigLWIP-r13 [1] TunnelConfigLWIP-r13 OPTIONAL,
   ...
}

LWIP-Configuration-r13 ::= CHOICE {
   release [0] NULL,
   setup [1] SEQUENCE {
      lwip-Config-r13 [0] LWIP-Config-r13
   }
}

RCLWI-Config-r13 ::= SEQUENCE {
   command [0] EXPLICIT CHOICE {
      steerToWLAN-r13 [0] SEQUENCE {
         mobilityConfig-r13 [0] WLAN-Id-List-r12
      },
      steerToLTE-r13 [1] NULL
   },
   ...
}

RCLWI-Configuration-r13 ::= CHOICE {
   release [0] NULL,
   setup [1] SEQUENCE {
      rclwi-Config-r13 [0] RCLWI-Config-r13
   }
}

SL-TxPoolToReleaseListV2X-r14 ::= SEQUENCE (SIZE (1..maxSL-V2X-TxPool-r14)) OF 
   SL-V2X-TxPoolIdentity-r14

SL-TxPoolToAddMod-r14 ::= SEQUENCE {
   poolIdentity-r14 [0] SL-V2X-TxPoolIdentity-r14,
   pool-r14 [1] SL-CommResourcePoolV2X-r14
}

SL-TxPoolToAddModListV2X-r14 ::= SEQUENCE (SIZE (1..maxSL-V2X-TxPool-r14)) OF SL-TxPoolToAddMod-r14

SL-ReliabilityList-r15 ::= SEQUENCE (SIZE (1..maxSL-Reliability-r15)) OF SL-Reliability-r15

LogicalChGroupInfoList-v1530 ::= SEQUENCE (SIZE (1..maxLCG-r13)) OF SL-ReliabilityList-r15
   

SL-V2X-ConfigDedicated-r14 ::= SEQUENCE {
   commTxResources-r14 [0] EXPLICIT CHOICE {
      release [0] NULL,
      setup [1] EXPLICIT CHOICE {
         scheduled-r14 [0] SEQUENCE {
            sl-V-RNTI-r14 [0] C-RNTI,
            mac-MainConfig-r14 [1] MAC-MainConfigSL-r12,
            v2x-SchedulingPool-r14 [2] SL-CommResourcePoolV2X-r14 OPTIONAL, -- Need ON
            mcs-r14 [3] INTEGER (0..31) OPTIONAL, -- Need OR
            logicalChGroupInfoList-r14 [4] LogicalChGroupInfoList-r13
         },
         ue-Selected-r14 [1] SEQUENCE {
--Pool for normal usage
            v2x-CommTxPoolNormalDedicated-r14 [0] SEQUENCE {
               poolToReleaseList-r14 [0] SL-TxPoolToReleaseListV2X-r14 OPTIONAL
                  , -- Need ON
               poolToAddModList-r14 [1] SL-TxPoolToAddModListV2X-r14 OPTIONAL, -- Need ON
               v2x-CommTxPoolSensingConfig-r14 [2] 
                  SL-CommTxPoolSensingConfig-r14 OPTIONAL
                  -- Need ON
            }
         }
      }
   } OPTIONAL, -- Need ON
   v2x-InterFreqInfoList-r14 [1] SL-InterFreqInfoListV2X-r14 OPTIONAL, -- Need ON
   thresSL-TxPrioritization-r14 [2] SL-Priority-r13 OPTIONAL, -- Need OR
   typeTxSync-r14 [3] SL-TypeTxSync-r14 OPTIONAL, -- Need OR
   cbr-DedicatedTxConfigList-r14 [4] SL-CBR-CommonTxConfigList-r14 OPTIONAL,
   ...,
   [[
      commTxResources-v1530 [5] EXPLICIT CHOICE {
         release [0] NULL,
         setup [1] EXPLICIT CHOICE {
            scheduled-v1530 [0] SEQUENCE {
               logicalChGroupInfoList-v1530 [0] LogicalChGroupInfoList-v1530
                   OPTIONAL, -- Need OR
               mcs-r15 [1] INTEGER (0..31) OPTIONAL -- Need OR
            },
            ue-Selected-v1530 [1] SEQUENCE {
               v2x-FreqSelectionConfigList-r15 [0] 
                  SL-V2X-FreqSelectionConfigList-r15 OPTIONAL --Need OR
            }
         }
      } OPTIONAL,
      v2x-PacketDuplicationConfig-r15 [6] SL-V2X-PacketDuplicationConfig-r15
          OPTIONAL,
      syncFreqList-r15 [7] SL-V2X-SyncFreqList-r15 OPTIONAL,
      slss-TxMultiFreq-r15 [8] ENUMERATED { true(0) } OPTIONAL
   ]],
   [[
      slss-TxDisabled-r15 [9] ENUMERATED { true(0) } OPTIONAL
   ]]
}

SCellToAddModExt-v1430 ::= SEQUENCE {
   srs-SwitchFromServCellIndex-r14 [0] INTEGER (0..31) OPTIONAL,
   ...,
   [[
      sCellState-r15 [1] ENUMERATED { activated(0), dormant(1) } OPTIONAL
   ]]
}

SCellToAddModListExt-v1430 ::= SEQUENCE (SIZE (1..maxSCell-r13)) OF SCellToAddModExt-v1430

SecurityConfigHO-v1530 ::= SEQUENCE {
   handoverType-v1530 [0] EXPLICIT CHOICE {
      intra5GC-r15 [0] SEQUENCE {
         securityAlgorithmConfig-r15 [0] SecurityAlgorithmConfig OPTIONAL, -- Cond HO-toEUTRA
         keyChangeIndicator-r15 [1] BOOLEAN,
         nextHopChainingCount-r15 [2] NextHopChainingCount,
         nas-Container-r15 [3] OCTET STRING OPTIONAL -- Need ON
      },
      fivegc-ToEPC-r15 [1] SEQUENCE {
         securityAlgorithmConfig-r15 [0] SecurityAlgorithmConfig,
         nextHopChainingCount-r15 [1] NextHopChainingCount
      },
      epc-To5GC-r15 [2] SEQUENCE {
         securityAlgorithmConfig-r15 [0] SecurityAlgorithmConfig,
         nas-Container-r15 [1] OCTET STRING
      }
   },
   ...
}

RRCConnectionReconfiguration-v1530-IEs ::= SEQUENCE {
   securityConfigHO-v1530 [0] SecurityConfigHO-v1530 OPTIONAL, -- Cond HO-5GC
   sCellGroupToReleaseList-r15 [1] SCellGroupToReleaseList-r15 OPTIONAL, -- Need ON
   sCellGroupToAddModList-r15 [2] SCellGroupToAddModList-r15 OPTIONAL, -- Need ON
   dedicatedInfoNASList-r15 [3] SEQUENCE (SIZE (1..maxDRB-r15)) OF DedicatedInfoNAS
       OPTIONAL, -- Cond nonHO
   p-MaxUE-FR1-r15 [4] P-Max OPTIONAL, -- Need OR
   smtc-r15 [5] MTC-SSB-NR-r15 OPTIONAL, -- Need OP
   nonCriticalExtension [6] SEQUENCE {

   } OPTIONAL
}

RRCConnectionReconfiguration-v1510-IEs ::= SEQUENCE {
   nr-Config-r15 [0] EXPLICIT CHOICE {
      release [0] NULL,
      setup [1] SEQUENCE {
         endc-ReleaseAndAdd-r15 [0] BOOLEAN,
         nr-SecondaryCellGroupConfig-r15 [1] OCTET STRING OPTIONAL, -- Need ON
         p-MaxEUTRA-r15 [2] P-Max OPTIONAL -- Need ON
      }
   } OPTIONAL, -- Need ON
   sk-Counter-r15 [1] INTEGER (0..65535) OPTIONAL, -- Need ON
   nr-RadioBearerConfig1-r15 [2] OCTET STRING OPTIONAL, -- Need ON
   nr-RadioBearerConfig2-r15 [3] OCTET STRING OPTIONAL, -- Need ON
   tdm-PatternConfig-r15 [4] EXPLICIT TDM-PatternConfig-r15 OPTIONAL, -- Cond FDD-PCell
   nonCriticalExtension [5] RRCConnectionReconfiguration-v1530-IEs OPTIONAL
}

RRCConnectionReconfiguration-v1430-IEs ::= SEQUENCE {
   sl-V2X-ConfigDedicated-r14 [0] SL-V2X-ConfigDedicated-r14 OPTIONAL, -- Need ON
   sCellToAddModListExt-v1430 [1] SCellToAddModListExt-v1430 OPTIONAL, -- Need ON
   perCC-GapIndicationRequest-r14 [2] ENUMERATED { true(0) } OPTIONAL, -- Need ON
   systemInformationBlockType2Dedicated-r14 [3] OCTET STRING (CONTAINING 
      SystemInformationBlockType2) OPTIONAL, -- Cond nonHO
   nonCriticalExtension [4] RRCConnectionReconfiguration-v1510-IEs OPTIONAL
}

RRCConnectionReconfiguration-v1310-IEs ::= SEQUENCE {
   sCellToReleaseListExt-r13 [0] SCellToReleaseListExt-r13 OPTIONAL, -- Need ON
   sCellToAddModListExt-r13 [1] SCellToAddModListExt-r13 OPTIONAL, -- Need ON
   lwa-Configuration-r13 [2] EXPLICIT LWA-Configuration-r13 OPTIONAL, -- Need ON
   lwip-Configuration-r13 [3] EXPLICIT LWIP-Configuration-r13 OPTIONAL, -- Need ON
   rclwi-Configuration-r13 [4] EXPLICIT RCLWI-Configuration-r13 OPTIONAL, -- Need ON
   nonCriticalExtension [5] RRCConnectionReconfiguration-v1430-IEs OPTIONAL
}

RRCConnectionReconfiguration-v1250-IEs ::= SEQUENCE {
   wlan-OffloadInfo-r12 [0] EXPLICIT CHOICE {
      release [0] NULL,
      setup [1] SEQUENCE {
         wlan-OffloadConfigDedicated-r12 [0] WLAN-OffloadConfig-r12,
         t350-r12 [1] ENUMERATED { min5(0), min10(1), min20(2), min30(3), 
            min60(4), min120(5), min180(6), spare1(7) } OPTIONAL -- Need OR
      }
   } OPTIONAL, -- Need ON
   scg-Configuration-r12 [1] EXPLICIT SCG-Configuration-r12 OPTIONAL, -- Cond nonFullConfig
   sl-SyncTxControl-r12 [2] SL-SyncTxControl-r12 OPTIONAL, -- Need ON
   sl-DiscConfig-r12 [3] SL-DiscConfig-r12 OPTIONAL, -- Need ON
   sl-CommConfig-r12 [4] SL-CommConfig-r12 OPTIONAL, -- Need ON
   nonCriticalExtension [5] RRCConnectionReconfiguration-v1310-IEs OPTIONAL
}

RRCConnectionReconfiguration-v1130-IEs ::= SEQUENCE {
   systemInformationBlockType1Dedicated-r11 [0] OCTET STRING (CONTAINING 
      SystemInformationBlockType1) OPTIONAL, -- Need ON
   nonCriticalExtension [1] RRCConnectionReconfiguration-v1250-IEs OPTIONAL
}

RRCConnectionReconfiguration-v1020-IEs ::= SEQUENCE {
   sCellToReleaseList-r10 [0] SCellToReleaseList-r10 OPTIONAL, -- Need ON
   sCellToAddModList-r10 [1] SCellToAddModList-r10 OPTIONAL, -- Need ON
   nonCriticalExtension [2] RRCConnectionReconfiguration-v1130-IEs OPTIONAL
}

-- Regular non-critical extensions:
RRCConnectionReconfiguration-v920-IEs ::= SEQUENCE {
   otherConfig-r9 [0] OtherConfig-r9 OPTIONAL, -- Need ON
   fullConfig-r9 [1] ENUMERATED { true(0) } OPTIONAL, -- Cond HO-Reestab
   nonCriticalExtension [2] RRCConnectionReconfiguration-v1020-IEs OPTIONAL
}

RRCConnectionReconfiguration-v890-IEs ::= SEQUENCE {
   lateNonCriticalExtension [0] OCTET STRING (CONTAINING 
      RRCConnectionReconfiguration-v8m0-IEs) OPTIONAL,
   nonCriticalExtension [1] RRCConnectionReconfiguration-v920-IEs OPTIONAL
}

RRCConnectionReconfiguration-r8-IEs ::= SEQUENCE {
   measConfig [0] MeasConfig OPTIONAL, -- Need ON
   mobilityControlInfo [1] MobilityControlInfo OPTIONAL, -- Cond HO
   dedicatedInfoNASList [2] SEQUENCE (SIZE (1..maxDRB)) OF DedicatedInfoNAS OPTIONAL, -- Cond nonHO
   radioResourceConfigDedicated [3] RadioResourceConfigDedicated OPTIONAL, -- Cond HO-toEUTRA
   securityConfigHO [4] SecurityConfigHO OPTIONAL, -- Cond HO-toEPC
   nonCriticalExtension [5] RRCConnectionReconfiguration-v890-IEs OPTIONAL
}

RRCConnectionReconfiguration ::= SEQUENCE {
   rrc-TransactionIdentifier [0] RRC-TransactionIdentifier,
   criticalExtensions [1] EXPLICIT CHOICE {
      c1 [0] EXPLICIT CHOICE {
         rrcConnectionReconfiguration-r8 [0] 
            RRCConnectionReconfiguration-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

CarrierInfoNR-r15 ::= SEQUENCE {
   carrierFreq-r15 [0] ARFCN-ValueNR-r15,
   subcarrierSpacingSSB-r15 [1] ENUMERATED { kHz15(0), kHz30(1), kHz120(2), 
      kHz240(3) },
   smtc-r15 [2] MTC-SSB-NR-r15 OPTIONAL -- Need OP
}

RedirectedCarrierInfo ::= CHOICE {
   eutra [0] ARFCN-ValueEUTRA,
   geran [1] CarrierFreqsGERAN,
   utra-FDD [2] ARFCN-ValueUTRA,
   utra-TDD [3] ARFCN-ValueUTRA,
   cdma2000-HRPD [4] CarrierFreqCDMA2000,
   cdma2000-1xRTT [5] CarrierFreqCDMA2000,
   ...,
   utra-TDD-r10 [6] CarrierFreqListUTRA-TDD-r10,
   nr-r15 [7] CarrierInfoNR-r15
}

RedirectedCarrierInfo-v9e0 ::= SEQUENCE {
   eutra-v9e0 [0] ARFCN-ValueEUTRA-v9e0
}

-- Late non critical extensions
RRCConnectionRelease-v9e0-IEs ::= SEQUENCE {
   redirectedCarrierInfo-v9e0 [0] RedirectedCarrierInfo-v9e0 OPTIONAL, -- Cond NoRedirect-r8
   idleModeMobilityControlInfo-v9e0 [1] IdleModeMobilityControlInfo-v9e0
       OPTIONAL, -- Cond IdleInfoEUTRA
   nonCriticalExtension [2] SEQUENCE {

   } OPTIONAL
}

CellInfoGERAN-r9 ::= SEQUENCE {
   physCellId-r9 [0] PhysCellIdGERAN,
   carrierFreq-r9 [1] CarrierFreqGERAN,
   systemInformation-r9 [2] SystemInfoListGERAN
}

CellInfoListGERAN-r9 ::= SEQUENCE (SIZE (1..maxCellInfoGERAN-r9)) OF CellInfoGERAN-r9

CellInfoUTRA-FDD-r9 ::= SEQUENCE {
   physCellId-r9 [0] PhysCellIdUTRA-FDD,
   utra-BCCH-Container-r9 [1] OCTET STRING
}

CellInfoListUTRA-FDD-r9 ::= SEQUENCE (SIZE (1..maxCellInfoUTRA-r9)) OF CellInfoUTRA-FDD-r9

CellInfoUTRA-TDD-r9 ::= SEQUENCE {
   physCellId-r9 [0] PhysCellIdUTRA-TDD,
   utra-BCCH-Container-r9 [1] OCTET STRING
}

CellInfoListUTRA-TDD-r9 ::= SEQUENCE (SIZE (1..maxCellInfoUTRA-r9)) OF CellInfoUTRA-TDD-r9

CellInfoUTRA-TDD-r10 ::= SEQUENCE {
   physCellId-r10 [0] PhysCellIdUTRA-TDD,
   carrierFreq-r10 [1] ARFCN-ValueUTRA,
   utra-BCCH-Container-r10 [2] OCTET STRING
}

CellInfoListUTRA-TDD-r10 ::= SEQUENCE (SIZE (1..maxCellInfoUTRA-r9)) OF CellInfoUTRA-TDD-r10

MeasIdleConfigDedicated-r15 ::= SEQUENCE {
   measIdleCarrierListEUTRA-r15 [0] EUTRA-CarrierList-r15 OPTIONAL, -- Need OR
   measIdleDuration-r15 [1] ENUMERATED { sec10(0), sec30(1), sec60(2), 
      sec120(3), sec180(4), sec240(5), sec300(6), spare(7) },
   ...
}

PLMN-RAN-AreaCell-r15 ::= SEQUENCE {
   plmn-Identity-r15 [0] PLMN-Identity OPTIONAL,
   ran-AreaCells-r15 [1] SEQUENCE (SIZE (1..32)) OF CellIdentity
}

PLMN-RAN-AreaCellList-r15 ::= SEQUENCE (SIZE (1..maxPLMN-r15)) OF PLMN-RAN-AreaCell-r15

RAN-AreaConfig-r15 ::= SEQUENCE {
   trackingAreaCode-5GC-r15 [0] TrackingAreaCode-5GC-r15,
   ran-AreaCodeList-r15 [1] SEQUENCE (SIZE (1..32)) OF RAN-AreaCode-r15 OPTIONAL --Need OR
}

PLMN-RAN-AreaConfig-r15 ::= SEQUENCE {
   plmn-Identity-r15 [0] PLMN-Identity OPTIONAL,
   ran-Area-r15 [1] SEQUENCE (SIZE (1..16)) OF RAN-AreaConfig-r15
}

PLMN-RAN-AreaConfigList-r15 ::= SEQUENCE (SIZE (1..maxPLMN-r15)) OF PLMN-RAN-AreaConfig-r15
   

RAN-NotificationAreaInfo-r15 ::= CHOICE {
   cellList-r15 [0] PLMN-RAN-AreaCellList-r15,
   ran-AreaConfigList-r15 [1] PLMN-RAN-AreaConfigList-r15
}

RRC-InactiveConfig-r15 ::= SEQUENCE {
   fullI-RNTI-r15 [0] I-RNTI-r15,
   shortI-RNTI-r15 [1] ShortI-RNTI-r15,
   ran-PagingCycle-r15 [2] ENUMERATED { rf32(0), rf64(1), rf128(2), rf256(3) }
       OPTIONAL, --Need OR
   ran-NotificationAreaInfo-r15 [3] EXPLICIT RAN-NotificationAreaInfo-r15
       OPTIONAL, --Need ON
   periodic-RNAU-timer-r15 [4] ENUMERATED { min5(0), min10(1), min20(2), 
      min30(3), min60(4), min120(5), min360(6), min720(7) } OPTIONAL, --Need OR
   nextHopChainingCount-r15 [5] NextHopChainingCount OPTIONAL, --Cond INACTIVE
   dummy [6] SEQUENCE {

   } OPTIONAL
}

RRCConnectionRelease-v1540-IEs ::= SEQUENCE {
   waitTime [0] INTEGER (1..16) OPTIONAL, -- Cond 5GC
   nonCriticalExtension [1] SEQUENCE {

   } OPTIONAL
}

RRCConnectionRelease-v1530-IEs ::= SEQUENCE {
   drb-ContinueROHC-r15 [0] ENUMERATED { true(0) } OPTIONAL, -- Cond UP-EDT
   nextHopChainingCount-r15 [1] NextHopChainingCount OPTIONAL, -- Cond UP-EDT
   measIdleConfig-r15 [2] MeasIdleConfigDedicated-r15 OPTIONAL, -- Need ON
   rrc-InactiveConfig-r15 [3] RRC-InactiveConfig-r15 OPTIONAL, -- Need OR
   cn-Type-r15 [4] ENUMERATED { epc(0), fivegc(1) } OPTIONAL, -- Need OR
   nonCriticalExtension [5] RRCConnectionRelease-v1540-IEs OPTIONAL
}

RRCConnectionRelease-v1320-IEs ::= SEQUENCE {
   resumeIdentity-r13 [0] ResumeIdentity-r13 OPTIONAL, -- Need OR	
   nonCriticalExtension [1] RRCConnectionRelease-v1530-IEs OPTIONAL
}

RRCConnectionRelease-v1020-IEs ::= SEQUENCE {
   extendedWaitTime-r10 [0] INTEGER (1..1800) OPTIONAL, -- Need ON
   nonCriticalExtension [1] RRCConnectionRelease-v1320-IEs OPTIONAL
}

-- Regular non critical extensions
RRCConnectionRelease-v920-IEs ::= SEQUENCE {
   cellInfoList-r9 [0] EXPLICIT CHOICE {
      geran-r9 [0] CellInfoListGERAN-r9,
      utra-FDD-r9 [1] CellInfoListUTRA-FDD-r9,
      utra-TDD-r9 [2] CellInfoListUTRA-TDD-r9,
      ...,
      utra-TDD-r10 [3] CellInfoListUTRA-TDD-r10
   } OPTIONAL, -- Cond Redirection
   nonCriticalExtension [1] RRCConnectionRelease-v1020-IEs OPTIONAL
}

RRCConnectionRelease-v890-IEs ::= SEQUENCE {
   lateNonCriticalExtension [0] OCTET STRING (CONTAINING 
      RRCConnectionRelease-v9e0-IEs) OPTIONAL,
   nonCriticalExtension [1] RRCConnectionRelease-v920-IEs OPTIONAL
}

RRCConnectionRelease-r8-IEs ::= SEQUENCE {
   releaseCause [0] ReleaseCause,
   redirectedCarrierInfo [1] EXPLICIT RedirectedCarrierInfo OPTIONAL, -- Need ON
   idleModeMobilityControlInfo [2] IdleModeMobilityControlInfo OPTIONAL, -- Need OP
   nonCriticalExtension [3] RRCConnectionRelease-v890-IEs OPTIONAL
}

RRCConnectionRelease ::= SEQUENCE {
   rrc-TransactionIdentifier [0] RRC-TransactionIdentifier,
   criticalExtensions [1] EXPLICIT CHOICE {
      c1 [0] EXPLICIT CHOICE {
         rrcConnectionRelease-r8 [0] RRCConnectionRelease-r8-IEs,
         spare3 [1] NULL,
         spare2 [2] NULL,
         spare1 [3] NULL
      },
      criticalExtensionsFuture [1] SEQUENCE {

      }
   }
}

SecurityConfigSMC ::= SEQUENCE {
   securityAlgorithmConfig [0] SecurityAlgorithmConfig,
   ...
}

SecurityModeCommand-v8a0-IEs ::= SEQUENCE {
   lateNonCriticalExtension [0] OCTET STRING OPTIONAL,
   nonCriticalExtension [1] SEQUENCE {

   } OPTIONAL
}

SecurityModeCommand-r8-IEs ::= SEQUENCE {
   securityConfigSMC [0] SecurityConfigSMC,
   nonCriticalExtension [1] SecurityModeCommand-v8a0-IEs OPTIONAL
}

SecurityModeCommand ::= SEQUENCE {
   rrc-TransactionIdentifier [0] RRC-TransactionIdentifier,
   criticalExtensions [1] EXPLICIT CHOICE {
      c1 [0] EXPLICIT CHOICE {
         securityModeCommand-r8 [0] SecurityModeCommand-r8-IEs,
         spare3 [1] NULL,
         spare2 [2] NULL,
         spare1 [3] NULL
      },
      criticalExtensionsFuture [1] SEQUENCE {

      }
   }
}

UE-CapabilityRequest ::= SEQUENCE (SIZE (1..maxRAT-Capabilities)) OF RAT-Type

BandIndication-r14 ::= SEQUENCE {
   bandEUTRA-r14 [0] FreqBandIndicator-r11,
   ca-BandwidthClassDL-r14 [1] CA-BandwidthClass-r10,
   ca-BandwidthClassUL-r14 [2] CA-BandwidthClass-r10 OPTIONAL
}

BandCombination-r14 ::= SEQUENCE (SIZE (1..maxSimultaneousBands-r10)) OF BandIndication-r14

BandCombinationList-r14 ::= SEQUENCE (SIZE (1..maxBandComb-r13)) OF BandCombination-r14

UECapabilityEnquiry-v1560-IEs ::= SEQUENCE {
   requestedCapabilityCommon-r15 [0] OCTET STRING OPTIONAL,
   nonCriticalExtension [1] SEQUENCE {

   } OPTIONAL
}

UECapabilityEnquiry-v1550-IEs ::= SEQUENCE {
   requestedCapabilityNR-r15 [0] OCTET STRING OPTIONAL,
   nonCriticalExtension [1] UECapabilityEnquiry-v1560-IEs OPTIONAL
}

UECapabilityEnquiry-v1530-IEs ::= SEQUENCE {
   requestSTTI-SPT-Capability-r15 [0] ENUMERATED { true(0) } OPTIONAL,
   eutra-nr-only-r15 [1] ENUMERATED { true(0) } OPTIONAL,
   nonCriticalExtension [2] UECapabilityEnquiry-v1550-IEs OPTIONAL
}

UECapabilityEnquiry-v1510-IEs ::= SEQUENCE {
   requestedFreqBandsNR-MRDC-r15 [0] OCTET STRING OPTIONAL,
   nonCriticalExtension [1] UECapabilityEnquiry-v1530-IEs OPTIONAL
}

UECapabilityEnquiry-v1430-IEs ::= SEQUENCE {
   requestDiffFallbackCombList-r14 [0] BandCombinationList-r14 OPTIONAL, -- Need ON
   nonCriticalExtension [1] UECapabilityEnquiry-v1510-IEs OPTIONAL
}

UECapabilityEnquiry-v1310-IEs ::= SEQUENCE {
   requestReducedFormat-r13 [0] ENUMERATED { true(0) } OPTIONAL, -- Need ON
   requestSkipFallbackComb-r13 [1] ENUMERATED { true(0) } OPTIONAL, -- Need ON
   requestedMaxCCsDL-r13 [2] INTEGER (2..32) OPTIONAL, -- Need ON
   requestedMaxCCsUL-r13 [3] INTEGER (2..32) OPTIONAL, -- Need ON
   requestReducedIntNonContComb-r13 [4] ENUMERATED { true(0) } OPTIONAL, -- Need ON
   nonCriticalExtension [5] UECapabilityEnquiry-v1430-IEs OPTIONAL
}

UECapabilityEnquiry-v1180-IEs ::= SEQUENCE {
   requestedFrequencyBands-r11 [0] SEQUENCE (SIZE (1..16)) OF 
      FreqBandIndicator-r11 OPTIONAL,
   nonCriticalExtension [1] UECapabilityEnquiry-v1310-IEs OPTIONAL
}

UECapabilityEnquiry-v8a0-IEs ::= SEQUENCE {
   lateNonCriticalExtension [0] OCTET STRING OPTIONAL,
   nonCriticalExtension [1] UECapabilityEnquiry-v1180-IEs OPTIONAL
}

UECapabilityEnquiry-r8-IEs ::= SEQUENCE {
   ue-CapabilityRequest [0] UE-CapabilityRequest,
   nonCriticalExtension [1] UECapabilityEnquiry-v8a0-IEs OPTIONAL
}

UECapabilityEnquiry ::= SEQUENCE {
   rrc-TransactionIdentifier [0] RRC-TransactionIdentifier,
   criticalExtensions [1] EXPLICIT CHOICE {
      c1 [0] EXPLICIT CHOICE {
         ueCapabilityEnquiry-r8 [0] UECapabilityEnquiry-r8-IEs,
         spare3 [1] NULL,
         spare2 [2] NULL,
         spare1 [3] NULL
      },
      criticalExtensionsFuture [1] SEQUENCE {

      }
   }
}

DRB-CountMSB-Info ::= SEQUENCE {
   drb-Identity [0] DRB-Identity,
   countMSB-Uplink [1] INTEGER (0..33554431),
   countMSB-Downlink [2] INTEGER (0..33554431)
}

DRB-CountMSB-InfoList ::= SEQUENCE (SIZE (1..maxDRB)) OF DRB-CountMSB-Info

DRB-CountMSB-InfoListExt-r15 ::= SEQUENCE (SIZE (1..maxDRBExt-r15)) OF DRB-CountMSB-Info

CounterCheck-v1530-IEs ::= SEQUENCE {
   drb-CountMSB-InfoListExt-r15 [0] DRB-CountMSB-InfoListExt-r15 OPTIONAL, -- Need ON
   nonCriticalExtension [1] SEQUENCE {

   } OPTIONAL
}

CounterCheck-v8a0-IEs ::= SEQUENCE {
   lateNonCriticalExtension [0] OCTET STRING OPTIONAL,
   nonCriticalExtension [1] CounterCheck-v1530-IEs OPTIONAL
}

CounterCheck-r8-IEs ::= SEQUENCE {
   drb-CountMSB-InfoList [0] DRB-CountMSB-InfoList,
   nonCriticalExtension [1] CounterCheck-v8a0-IEs OPTIONAL
}

CounterCheck ::= SEQUENCE {
   rrc-TransactionIdentifier [0] RRC-TransactionIdentifier,
   criticalExtensions [1] EXPLICIT CHOICE {
      c1 [0] EXPLICIT CHOICE {
         counterCheck-r8 [0] CounterCheck-r8-IEs,
         spare3 [1] NULL,
         spare2 [2] NULL,
         spare1 [3] NULL
      },
      criticalExtensionsFuture [1] SEQUENCE {

      }
   }
}

FlightPathInfoReportConfig-r15 ::= SEQUENCE {
   maxWayPointNumber-r15 [0] INTEGER (1..maxWayPoint-r15),
   includeTimeStamp-r15 [1] ENUMERATED { true(0) } OPTIONAL
}

UEInformationRequest-v1530-IEs ::= SEQUENCE {
   idleModeMeasurementReq-r15 [0] ENUMERATED { true(0) } OPTIONAL, -- Need ON
   flightPathInfoReq-r15 [1] FlightPathInfoReportConfig-r15 OPTIONAL, -- Need ON
   nonCriticalExtension [2] SEQUENCE {

   } OPTIONAL
}

UEInformationRequest-v1250-IEs ::= SEQUENCE {
   mobilityHistoryReportReq-r12 [0] ENUMERATED { true(0) } OPTIONAL, -- Need ON
   nonCriticalExtension [1] UEInformationRequest-v1530-IEs OPTIONAL
}

UEInformationRequest-v1130-IEs ::= SEQUENCE {
   connEstFailReportReq-r11 [0] ENUMERATED { true(0) } OPTIONAL, -- Need ON
   nonCriticalExtension [1] UEInformationRequest-v1250-IEs OPTIONAL
}

UEInformationRequest-v1020-IEs ::= SEQUENCE {
   logMeasReportReq-r10 [0] ENUMERATED { true(0) } OPTIONAL, -- Need ON
   nonCriticalExtension [1] UEInformationRequest-v1130-IEs OPTIONAL
}

UEInformationRequest-v930-IEs ::= SEQUENCE {
   lateNonCriticalExtension [0] OCTET STRING OPTIONAL,
   nonCriticalExtension [1] UEInformationRequest-v1020-IEs OPTIONAL
}

UEInformationRequest-r9-IEs ::= SEQUENCE {
   rach-ReportReq-r9 [0] BOOLEAN,
   rlf-ReportReq-r9 [1] BOOLEAN,
   nonCriticalExtension [2] UEInformationRequest-v930-IEs OPTIONAL
}

UEInformationRequest-r9 ::= SEQUENCE {
   rrc-TransactionIdentifier [0] RRC-TransactionIdentifier,
   criticalExtensions [1] EXPLICIT CHOICE {
      c1 [0] EXPLICIT CHOICE {
         ueInformationRequest-r9 [0] UEInformationRequest-r9-IEs,
         spare3 [1] NULL,
         spare2 [2] NULL,
         spare1 [3] NULL
      },
      criticalExtensionsFuture [1] SEQUENCE {

      }
   }
}

TraceReference-r10 ::= SEQUENCE {
   plmn-Identity-r10 [0] PLMN-Identity,
   traceId-r10 [1] OCTET STRING (SIZE (3))
}

CellGlobalIdList-r10 ::= SEQUENCE (SIZE (1..32)) OF CellGlobalIdEUTRA

TrackingAreaCodeList-r10 ::= SEQUENCE (SIZE (1..8)) OF TrackingAreaCode

AreaConfiguration-r10 ::= CHOICE {
   cellGlobalIdList-r10 [0] CellGlobalIdList-r10,
   trackingAreaCodeList-r10 [1] TrackingAreaCodeList-r10
}

PLMN-IdentityList3-r11 ::= SEQUENCE (SIZE (1..16)) OF PLMN-Identity

TrackingAreaCodeList-v1130 ::= SEQUENCE {
   plmn-Identity-perTAC-List-r11 [0] SEQUENCE (SIZE (1..8)) OF PLMN-Identity
}

AreaConfiguration-v1130 ::= SEQUENCE {
   trackingAreaCodeList-v1130 [0] TrackingAreaCodeList-v1130
}

TargetMBSFN-Area-r12 ::= SEQUENCE {
   mbsfn-AreaId-r12 [0] MBSFN-AreaId-r12 OPTIONAL, -- Need OR
   carrierFreq-r12 [1] ARFCN-ValueEUTRA-r9,
   ...
}

TargetMBSFN-AreaList-r12 ::= SEQUENCE (SIZE (0..maxMBSFN-Area)) OF TargetMBSFN-Area-r12

LoggedMeasurementConfiguration-v1530-IEs ::= SEQUENCE {
   bt-NameList-r15 [0] BT-NameList-r15 OPTIONAL, --Need OR
   wlan-NameList-r15 [1] WLAN-NameList-r15 OPTIONAL, --Need OR
   nonCriticalExtension [2] SEQUENCE {

   } OPTIONAL
}

LoggedMeasurementConfiguration-v1250-IEs ::= SEQUENCE {
   targetMBSFN-AreaList-r12 [0] TargetMBSFN-AreaList-r12 OPTIONAL, -- Need OP
   nonCriticalExtension [1] LoggedMeasurementConfiguration-v1530-IEs OPTIONAL
}

LoggedMeasurementConfiguration-v1130-IEs ::= SEQUENCE {
   plmn-IdentityList-r11 [0] PLMN-IdentityList3-r11 OPTIONAL, -- Need OR
   areaConfiguration-v1130 [1] AreaConfiguration-v1130 OPTIONAL, -- Need OR
   nonCriticalExtension [2] LoggedMeasurementConfiguration-v1250-IEs OPTIONAL
}

LoggedMeasurementConfiguration-v1080-IEs ::= SEQUENCE {
   lateNonCriticalExtension-r10 [0] OCTET STRING OPTIONAL,
   nonCriticalExtension [1] LoggedMeasurementConfiguration-v1130-IEs OPTIONAL
}

LoggedMeasurementConfiguration-r10-IEs ::= SEQUENCE {
   traceReference-r10 [0] TraceReference-r10,
   traceRecordingSessionRef-r10 [1] OCTET STRING (SIZE (2)),
   tce-Id-r10 [2] OCTET STRING (SIZE (1)),
   absoluteTimeInfo-r10 [3] AbsoluteTimeInfo-r10,
   areaConfiguration-r10 [4] EXPLICIT AreaConfiguration-r10 OPTIONAL, -- Need OR
   loggingDuration-r10 [5] LoggingDuration-r10,
   loggingInterval-r10 [6] LoggingInterval-r10,
   nonCriticalExtension [7] LoggedMeasurementConfiguration-v1080-IEs OPTIONAL
}

LoggedMeasurementConfiguration-r10 ::= SEQUENCE {
   criticalExtensions [0] EXPLICIT CHOICE {
      c1 [0] EXPLICIT CHOICE {
         loggedMeasurementConfiguration-r10 [0] 
            LoggedMeasurementConfiguration-r10-IEs,
         spare3 [1] NULL,
         spare2 [2] NULL,
         spare1 [3] NULL
      },
      criticalExtensionsFuture [1] SEQUENCE {

      }
   }
}

RN-SystemInfo-r10 ::= SEQUENCE {
   systemInformationBlockType1-r10 [0] OCTET STRING (CONTAINING 
      SystemInformationBlockType1) OPTIONAL, -- Need ON
   systemInformationBlockType2-r10 [1] SystemInformationBlockType2 OPTIONAL,
   ...
}

RN-SubframeConfig-r10 ::= SEQUENCE {
   subframeConfigPattern-r10 [0] EXPLICIT CHOICE {
      subframeConfigPatternFDD-r10 [0] BIT STRING  (SIZE (8)),
      subframeConfigPatternTDD-r10 [1] INTEGER (0..31)
   } OPTIONAL, -- Need ON
   rpdcch-Config-r10 [1] SEQUENCE {
      resourceAllocationType-r10 [0] ENUMERATED { type0(0), type1(1), 
         type2Localized(2), type2Distributed(3), spare4(4), spare3(5), 
         spare2(6), spare1(7) },
      resourceBlockAssignment-r10 [1] EXPLICIT CHOICE {
         type01-r10 [0] EXPLICIT CHOICE {
            nrb6-r10 [0] BIT STRING  (SIZE (6)),
            nrb15-r10 [1] BIT STRING  (SIZE (8)),
            nrb25-r10 [2] BIT STRING  (SIZE (13)),
            nrb50-r10 [3] BIT STRING  (SIZE (17)),
            nrb75-r10 [4] BIT STRING  (SIZE (19)),
            nrb100-r10 [5] BIT STRING  (SIZE (25))
         },
         type2-r10 [1] EXPLICIT CHOICE {
            nrb6-r10 [0] BIT STRING  (SIZE (5)),
            nrb15-r10 [1] BIT STRING  (SIZE (7)),
            nrb25-r10 [2] BIT STRING  (SIZE (9)),
            nrb50-r10 [3] BIT STRING  (SIZE (11)),
            nrb75-r10 [4] BIT STRING  (SIZE (12)),
            nrb100-r10 [5] BIT STRING  (SIZE (13))
         },
         ...
      },
      demodulationRS-r10 [2] EXPLICIT CHOICE {
         interleaving-r10 [0] ENUMERATED { crs(0) },
         noInterleaving-r10 [1] ENUMERATED { crs(0), dmrs(1) }
      },
      pdsch-Start-r10 [3] INTEGER (1..3),
      pucch-Config-r10 [4] EXPLICIT CHOICE {
         tdd [0] EXPLICIT CHOICE {
            channelSelectionMultiplexingBundling [0] SEQUENCE {
               n1PUCCH-AN-List-r10 [0] SEQUENCE (SIZE (1..4)) OF INTEGER (0..2047)
            },
            fallbackForFormat3 [1] SEQUENCE {
               n1PUCCH-AN-P0-r10 [0] INTEGER (0..2047),
               n1PUCCH-AN-P1-r10 [1] INTEGER (0..2047) OPTIONAL -- Need OR
            }
         },
         fdd [1] SEQUENCE {
            n1PUCCH-AN-P0-r10 [0] INTEGER (0..2047),
            n1PUCCH-AN-P1-r10 [1] INTEGER (0..2047) OPTIONAL -- Need OR
         }
      },
      ...
   } OPTIONAL,
   ...
}

RNReconfiguration-r10-IEs ::= SEQUENCE {
   rn-SystemInfo-r10 [0] RN-SystemInfo-r10 OPTIONAL, -- Need ON
   rn-SubframeConfig-r10 [1] RN-SubframeConfig-r10 OPTIONAL, -- Need ON
   lateNonCriticalExtension [2] OCTET STRING OPTIONAL,
   nonCriticalExtension [3] SEQUENCE {

   } OPTIONAL
}

RNReconfiguration-r10 ::= SEQUENCE {
   rrc-TransactionIdentifier [0] RRC-TransactionIdentifier,
   criticalExtensions [1] EXPLICIT CHOICE {
      c1 [0] EXPLICIT CHOICE {
         rnReconfiguration-r10 [0] RNReconfiguration-r10-IEs,
         spare3 [1] NULL,
         spare2 [2] NULL,
         spare1 [3] NULL
      },
      criticalExtensionsFuture [1] SEQUENCE {

      }
   }
}

RRCConnectionResume-v1530-IEs ::= SEQUENCE {
   fullConfig-r15 [0] ENUMERATED { true(0) } OPTIONAL, -- Need ON
   nonCriticalExtension [1] SEQUENCE {

   } OPTIONAL
}

RRCConnectionResume-v1510-IEs ::= SEQUENCE {
   sk-Counter-r15 [0] INTEGER (0..65535) OPTIONAL, -- Need ON
   nr-RadioBearerConfig1-r15 [1] OCTET STRING OPTIONAL, -- Need ON
   nr-RadioBearerConfig2-r15 [2] OCTET STRING OPTIONAL, -- Need ON
   nonCriticalExtension [3] RRCConnectionResume-v1530-IEs OPTIONAL
}

RRCConnectionResume-v1430-IEs ::= SEQUENCE {
   otherConfig-r14 [0] OtherConfig-r9 OPTIONAL, -- Need ON
   rrcConnectionResume-v1510-IEs [1] RRCConnectionResume-v1510-IEs OPTIONAL
}

RRCConnectionResume-r13-IEs ::= SEQUENCE {
   radioResourceConfigDedicated-r13 [0] RadioResourceConfigDedicated OPTIONAL, -- Need ON
   nextHopChainingCount-r13 [1] NextHopChainingCount,
   measConfig-r13 [2] MeasConfig OPTIONAL, -- Need ON
   antennaInfoDedicatedPCell-r13 [3] AntennaInfoDedicated-v10i0 OPTIONAL, -- Need ON
   drb-ContinueROHC-r13 [4] ENUMERATED { true(0) } OPTIONAL, -- Need OP
   lateNonCriticalExtension [5] OCTET STRING OPTIONAL,
   rrcConnectionResume-v1430-IEs [6] RRCConnectionResume-v1430-IEs OPTIONAL
}

RRCConnectionResume-r13 ::= SEQUENCE {
   rrc-TransactionIdentifier [0] RRC-TransactionIdentifier,
   criticalExtensions [1] EXPLICIT CHOICE {
      c1 [0] EXPLICIT CHOICE {
         rrcConnectionResume-r13 [0] RRCConnectionResume-r13-IEs,
         spare3 [1] NULL,
         spare2 [2] NULL,
         spare1 [3] NULL
      },
      criticalExtensionsFuture [1] SEQUENCE {

      }
   }
}

DL-DCCH-MessageType ::= CHOICE {
   c1 [0] EXPLICIT CHOICE {
      csfbParametersResponseCDMA2000 [0] CSFBParametersResponseCDMA2000,
      dlInformationTransfer [1] DLInformationTransfer,
      handoverFromEUTRAPreparationRequest [2] 
         HandoverFromEUTRAPreparationRequest,
      mobilityFromEUTRACommand [3] MobilityFromEUTRACommand,
      rrcConnectionReconfiguration [4] RRCConnectionReconfiguration,
      rrcConnectionRelease [5] RRCConnectionRelease,
      securityModeCommand [6] SecurityModeCommand,
      ueCapabilityEnquiry [7] UECapabilityEnquiry,
      counterCheck [8] CounterCheck,
      ueInformationRequest-r9 [9] UEInformationRequest-r9,
      loggedMeasurementConfiguration-r10 [10] 
         LoggedMeasurementConfiguration-r10,
      rnReconfiguration-r10 [11] RNReconfiguration-r10,
      rrcConnectionResume-r13 [12] RRCConnectionResume-r13,
      spare3 [13] NULL,
      spare2 [14] NULL,
      spare1 [15] NULL
   },
   messageClassExtension [1] SEQUENCE {

   }
}

DL-DCCH-Message ::= SEQUENCE {
   message [0] EXPLICIT DL-DCCH-MessageType
}

ReestabUE-Identity ::= SEQUENCE {
   c-RNTI [0] C-RNTI,
   physCellId [1] PhysCellId,
   shortMAC-I [2] ShortMAC-I
}

RRCConnectionReestablishmentRequest-r8-IEs ::= SEQUENCE {
   ue-Identity [0] ReestabUE-Identity,
   reestablishmentCause [1] ReestablishmentCause,
   spare [2] BIT STRING  (SIZE (2))
}

RRCConnectionReestablishmentRequest ::= SEQUENCE {
   criticalExtensions [0] EXPLICIT CHOICE {
      rrcConnectionReestablishmentRequest-r8 [0] 
         RRCConnectionReestablishmentRequest-r8-IEs,
      criticalExtensionsFuture [1] SEQUENCE {

      }
   }
}

InitialUE-Identity ::= CHOICE {
   s-TMSI [0] S-TMSI,
   randomValue [1] BIT STRING  (SIZE (40))
}

RRCConnectionRequest-r8-IEs ::= SEQUENCE {
   ue-Identity [0] EXPLICIT InitialUE-Identity,
   establishmentCause [1] EstablishmentCause,
   spare [2] BIT STRING  (SIZE (1))
}

InitialUE-Identity-5GC ::= CHOICE {
   ng-5G-S-TMSI-Part1 [0] BIT STRING  (SIZE (40)),
   randomValue [1] BIT STRING  (SIZE (40))
}

RRCConnectionRequest-5GC-r15-IEs ::= SEQUENCE {
   ue-Identity [0] EXPLICIT InitialUE-Identity-5GC,
   establishmentCause [1] EstablishmentCause-5GC,
   spare [2] BIT STRING  (SIZE (1))
}

RRCConnectionRequest ::= SEQUENCE {
   criticalExtensions [0] EXPLICIT CHOICE {
      rrcConnectionRequest-r8 [0] RRCConnectionRequest-r8-IEs,
      rrcConnectionRequest-r15 [1] RRCConnectionRequest-5GC-r15-IEs
   }
}

RRCConnectionResumeRequest-r13-IEs ::= SEQUENCE {
   resumeIdentity-r13 [0] EXPLICIT CHOICE {
      resumeID-r13 [0] ResumeIdentity-r13,
      truncatedResumeID-r13 [1] BIT STRING  (SIZE (24))
   },
   shortResumeMAC-I-r13 [1] BIT STRING  (SIZE (16)),
   resumeCause-r13 [2] ResumeCause,
   spare [3] BIT STRING  (SIZE (1))
}

RRCConnectionResumeRequest-5GC-r15-IEs ::= SEQUENCE {
   resumeIdentity-r15 [0] EXPLICIT CHOICE {
      fullI-RNTI-r15 [0] I-RNTI-r15,
      shortI-RNTI-r15 [1] ShortI-RNTI-r15
   },
   shortResumeMAC-I-r15 [1] BIT STRING  (SIZE (16)),
   resumeCause-r15 [2] ResumeCause-r15,
   spare [3] BIT STRING  (SIZE (1))
}

RRCConnectionResumeRequest-r13 ::= SEQUENCE {
   criticalExtensions [0] EXPLICIT CHOICE {
      rrcConnectionResumeRequest-r13 [0] RRCConnectionResumeRequest-r13-IEs,
      rrcConnectionResumeRequest-r15 [1] RRCConnectionResumeRequest-5GC-r15-IEs
   }
}

RRCEarlyDataRequest-r15-IEs ::= SEQUENCE {
   s-TMSI-r15 [0] S-TMSI,
   establishmentCause-r15 [1] ENUMERATED { mo-Data(0), delayTolerantAccess(1) }
      ,
   dedicatedInfoNAS-r15 [2] DedicatedInfoNAS,
   nonCriticalExtension [3] SEQUENCE {

   } OPTIONAL
}

RRCEarlyDataRequest-r15 ::= SEQUENCE {
   criticalExtensions [0] EXPLICIT CHOICE {
      rrcEarlyDataRequest-r15 [0] RRCEarlyDataRequest-r15-IEs,
      criticalExtensionsFuture [1] SEQUENCE {

      }
   }
}

UL-CCCH-MessageType ::= CHOICE {
   c1 [0] EXPLICIT CHOICE {
      rrcConnectionReestablishmentRequest [0] 
         RRCConnectionReestablishmentRequest,
      rrcConnectionRequest [1] RRCConnectionRequest
   },
   messageClassExtension [1] EXPLICIT CHOICE {
      c2 [0] EXPLICIT CHOICE {
         rrcConnectionResumeRequest-r13 [0] RRCConnectionResumeRequest-r13
      },
      messageClassExtensionFuture-r13 [1] EXPLICIT CHOICE {
         c3 [0] EXPLICIT CHOICE {
            rrcEarlyDataRequest-r15 [0] RRCEarlyDataRequest-r15,
            spare3 [1] NULL,
            spare2 [2] NULL,
            spare1 [3] NULL
         },
         messageClassExtensionFuture-r15 [1] SEQUENCE {

         }
      }
   }
}

UL-CCCH-Message ::= SEQUENCE {
   message [0] EXPLICIT UL-CCCH-MessageType
}

CSFBParametersRequestCDMA2000-v8a0-IEs ::= SEQUENCE {
   lateNonCriticalExtension [0] OCTET STRING OPTIONAL,
   nonCriticalExtension [1] SEQUENCE {

   } OPTIONAL
}

CSFBParametersRequestCDMA2000-r8-IEs ::= SEQUENCE {
   nonCriticalExtension [0] CSFBParametersRequestCDMA2000-v8a0-IEs OPTIONAL
}

CSFBParametersRequestCDMA2000 ::= SEQUENCE {
   criticalExtensions [0] EXPLICIT CHOICE {
      csfbParametersRequestCDMA2000-r8 [0] CSFBParametersRequestCDMA2000-r8-IEs
         ,
      criticalExtensionsFuture [1] SEQUENCE {

      }
   }
}

PLMN-IdentityList2 ::= SEQUENCE (SIZE (1..5)) OF PLMN-Identity

AdditionalSI-Info-r9 ::= SEQUENCE {
   csg-MemberStatus-r9 [0] ENUMERATED { member(0) } OPTIONAL,
   csg-Identity-r9 [1] CSG-Identity OPTIONAL
}

MeasResultEUTRA ::= SEQUENCE {
   physCellId [0] PhysCellId,
   cgi-Info [1] SEQUENCE {
      cellGlobalId [0] CellGlobalIdEUTRA,
      trackingAreaCode [1] TrackingAreaCode,
      plmn-IdentityList [2] PLMN-IdentityList2 OPTIONAL
   } OPTIONAL,
   measResult [2] SEQUENCE {
      rsrpResult [0] RSRP-Range OPTIONAL,
      rsrqResult [1] RSRQ-Range OPTIONAL,
      ...,
      [[
         additionalSI-Info-r9 [2] AdditionalSI-Info-r9 OPTIONAL
      ]],
      [[
         primaryPLMN-Suitable-r12 [3] ENUMERATED { true(0) } OPTIONAL,
         measResult-v1250 [4] RSRQ-Range-v1250 OPTIONAL
      ]],
      [[
         rs-sinr-Result-r13 [5] RS-SINR-Range-r13 OPTIONAL,
         cgi-Info-v1310 [6] SEQUENCE {
            freqBandIndicator-r13 [0] FreqBandIndicator-r11 OPTIONAL,
            multiBandInfoList-r13 [1] MultiBandInfoList-r11 OPTIONAL,
            freqBandIndicatorPriority-r13 [2] ENUMERATED { true(0) } OPTIONAL
         } OPTIONAL
      ]],
      [[
         measResult-v1360 [7] RSRP-Range-v1360 OPTIONAL
      ]],
      [[
         cgi-Info-5GC-r15 [8] SEQUENCE (SIZE (1..maxPLMN-r11)) OF 
            CellAccessRelatedInfo-5GC-r15 OPTIONAL
      ]]
   }
}

MeasResultListEUTRA ::= SEQUENCE (SIZE (1..maxCellReport)) OF MeasResultEUTRA

CellGlobalIdUTRA ::= SEQUENCE {
   plmn-Identity [0] PLMN-Identity,
   cellIdentity [1] BIT STRING  (SIZE (28))
}

MeasResultUTRA ::= SEQUENCE {
   physCellId [0] EXPLICIT CHOICE {
      fdd [0] PhysCellIdUTRA-FDD,
      tdd [1] PhysCellIdUTRA-TDD
   },
   cgi-Info [1] SEQUENCE {
      cellGlobalId [0] CellGlobalIdUTRA,
      locationAreaCode [1] BIT STRING  (SIZE (16)) OPTIONAL,
      routingAreaCode [2] BIT STRING  (SIZE (8)) OPTIONAL,
      plmn-IdentityList [3] PLMN-IdentityList2 OPTIONAL
   } OPTIONAL,
   measResult [2] SEQUENCE {
      utra-RSCP [0] INTEGER (-5..91) OPTIONAL,
      utra-EcN0 [1] INTEGER (0..49) OPTIONAL,
      ...,
      [[
         additionalSI-Info-r9 [2] AdditionalSI-Info-r9 OPTIONAL
      ]],
      [[
         primaryPLMN-Suitable-r12 [3] ENUMERATED { true(0) } OPTIONAL
      ]]
   }
}

MeasResultListUTRA ::= SEQUENCE (SIZE (1..maxCellReport)) OF MeasResultUTRA

CellGlobalIdGERAN ::= SEQUENCE {
   plmn-Identity [0] PLMN-Identity,
   locationAreaCode [1] BIT STRING  (SIZE (16)),
   cellIdentity [2] BIT STRING  (SIZE (16))
}

MeasResultGERAN ::= SEQUENCE {
   carrierFreq [0] CarrierFreqGERAN,
   physCellId [1] PhysCellIdGERAN,
   cgi-Info [2] SEQUENCE {
      cellGlobalId [0] CellGlobalIdGERAN,
      routingAreaCode [1] BIT STRING  (SIZE (8)) OPTIONAL
   } OPTIONAL,
   measResult [3] SEQUENCE {
      rssi [0] INTEGER (0..63),
      ...
   }
}

MeasResultListGERAN ::= SEQUENCE (SIZE (1..maxCellReport)) OF MeasResultGERAN

CellGlobalIdCDMA2000 ::= CHOICE {
   cellGlobalId1XRTT [0] BIT STRING  (SIZE (47)),
   cellGlobalIdHRPD [1] BIT STRING  (SIZE (128))
}

MeasResultCDMA2000 ::= SEQUENCE {
   physCellId [0] PhysCellIdCDMA2000,
   cgi-Info [1] EXPLICIT CellGlobalIdCDMA2000 OPTIONAL,
   measResult [2] SEQUENCE {
      pilotPnPhase [0] INTEGER (0..32767) OPTIONAL,
      pilotStrength [1] INTEGER (0..63),
      ...
   }
}

MeasResultListCDMA2000 ::= SEQUENCE (SIZE (1..maxCellReport)) OF MeasResultCDMA2000

MeasResultsCDMA2000 ::= SEQUENCE {
   preRegistrationStatusHRPD [0] BOOLEAN,
   measResultListCDMA2000 [1] MeasResultListCDMA2000
}

MeasResultNR-r15 ::= SEQUENCE {
   rsrpResult-r15 [0] RSRP-RangeNR-r15 OPTIONAL,
   rsrqResult-r15 [1] RSRQ-RangeNR-r15 OPTIONAL,
   rs-sinr-Result-r15 [2] RS-SINR-RangeNR-r15 OPTIONAL,
   ...
}

MeasResultSSB-Index-r15 ::= SEQUENCE {
   ssb-Index-r15 [0] RS-IndexNR-r15,
   measResultSSB-Index-r15 [1] MeasResultNR-r15 OPTIONAL,
   ...
}

MeasResultSSB-IndexList-r15 ::= SEQUENCE (SIZE (1..maxRS-IndexReport-r15)) OF MeasResultSSB-Index-r15
   

PLMN-IdentityListNR-r15 ::= SEQUENCE (SIZE (1..maxPLMN-NR-r15)) OF PLMN-Identity

PLMN-IdentityInfoNR-r15 ::= SEQUENCE {
   plmn-IdentityList-r15 [0] PLMN-IdentityListNR-r15,
   trackingAreaCode-r15 [1] TrackingAreaCodeNR-r15 OPTIONAL,
   ran-AreaCode-r15 [2] RAN-AreaCode-r15 OPTIONAL,
   cellIdentity-r15 [3] CellIdentityNR-r15
}

PLMN-IdentityInfoListNR-r15 ::= SEQUENCE (SIZE (1..maxPLMN-NR-r15)) OF PLMN-IdentityInfoNR-r15
   

CGI-InfoNR-r15 ::= SEQUENCE {
   plmn-IdentityInfoList-r15 [0] PLMN-IdentityInfoListNR-r15 OPTIONAL,
   frequencyBandList-15 [1] MultiFrequencyBandListNR-r15 OPTIONAL,
   noSIB1-r15 [2] SEQUENCE {
      ssb-SubcarrierOffset-r15 [0] INTEGER (0..15),
      pdcch-ConfigSIB1-r15 [1] INTEGER (0..255)
   } OPTIONAL,
   ...
}

MeasResultCellNR-r15 ::= SEQUENCE {
   pci-r15 [0] PhysCellIdNR-r15,
   measResultCell-r15 [1] MeasResultNR-r15,
   measResultRS-IndexList-r15 [2] MeasResultSSB-IndexList-r15 OPTIONAL,
   ...,
   [[
      cgi-Info-r15 [3] CGI-InfoNR-r15 OPTIONAL
   ]]
}

MeasResultCellListNR-r15 ::= SEQUENCE (SIZE (1..maxCellReport)) OF MeasResultCellNR-r15

MeasResultForECID-r9 ::= SEQUENCE {
   ue-RxTxTimeDiffResult-r9 [0] INTEGER (0..4095),
   currentSFN-r9 [1] BIT STRING  (SIZE (10))
}

LocationInfo-r10 ::= SEQUENCE {
   locationCoordinates-r10 [0] EXPLICIT CHOICE {
      ellipsoid-Point-r10 [0] OCTET STRING,
      ellipsoidPointWithAltitude-r10 [1] OCTET STRING,
      ...,
      ellipsoidPointWithUncertaintyCircle-r11 [2] OCTET STRING,
      ellipsoidPointWithUncertaintyEllipse-r11 [3] OCTET STRING,
      ellipsoidPointWithAltitudeAndUncertaintyEllipsoid-r11 [4] OCTET STRING,
      ellipsoidArc-r11 [5] OCTET STRING,
      polygon-r11 [6] OCTET STRING
   },
   horizontalVelocity-r10 [1] OCTET STRING OPTIONAL,
   gnss-TOD-msec-r10 [2] OCTET STRING OPTIONAL,
   ...,
   [[
      verticalVelocityInfo-r15 [3] EXPLICIT CHOICE {
         verticalVelocity-r15 [0] OCTET STRING,
         verticalVelocityAndUncertainty-r15 [1] OCTET STRING
      } OPTIONAL
   ]]
}

MeasResultServFreq-r10 ::= SEQUENCE {
   servFreqId-r10 [0] ServCellIndex-r10,
   measResultSCell-r10 [1] SEQUENCE {
      rsrpResultSCell-r10 [0] RSRP-Range,
      rsrqResultSCell-r10 [1] RSRQ-Range
   } OPTIONAL,
   measResultBestNeighCell-r10 [2] SEQUENCE {
      physCellId-r10 [0] PhysCellId,
      rsrpResultNCell-r10 [1] RSRP-Range,
      rsrqResultNCell-r10 [2] RSRQ-Range
   } OPTIONAL,
   ...,
   [[
      measResultSCell-v1250 [3] RSRQ-Range-v1250 OPTIONAL,
      measResultBestNeighCell-v1250 [4] RSRQ-Range-v1250 OPTIONAL
   ]],
   [[
      measResultSCell-v1310 [5] SEQUENCE {
         rs-sinr-Result-r13 [0] RS-SINR-Range-r13
      } OPTIONAL,
      measResultBestNeighCell-v1310 [6] SEQUENCE {
         rs-sinr-Result-r13 [0] RS-SINR-Range-r13
      } OPTIONAL
   ]]
}

MeasResultServFreqList-r10 ::= SEQUENCE (SIZE (1..maxServCell-r10)) OF MeasResultServFreq-r10

MeasResultCSI-RS-r12 ::= SEQUENCE {
   measCSI-RS-Id-r12 [0] MeasCSI-RS-Id-r12,
   csi-RSRP-Result-r12 [1] CSI-RSRP-Range-r12,
   ...
}

MeasResultCSI-RS-List-r12 ::= SEQUENCE (SIZE (1..maxCellReport)) OF MeasResultCSI-RS-r12

MeasResultForRSSI-r13 ::= SEQUENCE {
   rssi-Result-r13 [0] RSSI-Range-r13,
   channelOccupancy-r13 [1] INTEGER (0..100),
   ...
}

MeasResultServFreq-r13 ::= SEQUENCE {
   servFreqId-r13 [0] ServCellIndex-r13,
   measResultSCell-r13 [1] SEQUENCE {
      rsrpResultSCell-r13 [0] RSRP-Range,
      rsrqResultSCell-r13 [1] RSRQ-Range-r13,
      rs-sinr-Result-r13 [2] RS-SINR-Range-r13 OPTIONAL
   } OPTIONAL,
   measResultBestNeighCell-r13 [2] SEQUENCE {
      physCellId-r13 [0] PhysCellId,
      rsrpResultNCell-r13 [1] RSRP-Range,
      rsrqResultNCell-r13 [2] RSRQ-Range-r13,
      rs-sinr-Result-r13 [3] RS-SINR-Range-r13 OPTIONAL
   } OPTIONAL,
   ...,
   [[
      measResultBestNeighCell-v1360 [3] SEQUENCE {
         rsrpResultNCell-v1360 [0] RSRP-Range-v1360
      } OPTIONAL
   ]]
}

MeasResultServFreqListExt-r13 ::= SEQUENCE (SIZE (1..maxServCell-r13)) OF 
   MeasResultServFreq-r13

MeasResultSSTD-r13 ::= SEQUENCE {
   sfn-OffsetResult-r13 [0] INTEGER (0..1023),
   frameBoundaryOffsetResult-r13 [1] INTEGER (-5..4),
   subframeBoundaryOffsetResult-r13 [2] INTEGER (0..127)
}

UL-PDCP-DelayResult-r13 ::= SEQUENCE {
   qci-Id-r13 [0] ENUMERATED { qci1(0), qci2(1), qci3(2), qci4(3), spare4(4), 
      spare3(5), spare2(6), spare1(7) },
   excessDelay-r13 [1] INTEGER (0..31),
   ...
}

UL-PDCP-DelayResultList-r13 ::= SEQUENCE (SIZE (1..maxQCI-r13)) OF UL-PDCP-DelayResult-r13
   

MeasResultWLAN-r13 ::= SEQUENCE {
   wlan-Identifiers-r13 [0] WLAN-Identifiers-r12,
   carrierInfoWLAN-r13 [1] WLAN-CarrierInfo-r13 OPTIONAL,
   bandWLAN-r13 [2] WLAN-BandIndicator-r13 OPTIONAL,
   rssiWLAN-r13 [3] WLAN-RSSI-Range-r13,
   availableAdmissionCapacityWLAN-r13 [4] INTEGER (0..31250) OPTIONAL,
   backhaulDL-BandwidthWLAN-r13 [5] WLAN-backhaulRate-r12 OPTIONAL,
   backhaulUL-BandwidthWLAN-r13 [6] WLAN-backhaulRate-r12 OPTIONAL,
   channelUtilizationWLAN-r13 [7] INTEGER (0..255) OPTIONAL,
   stationCountWLAN-r13 [8] INTEGER (0..65535) OPTIONAL,
   connectedWLAN-r13 [9] ENUMERATED { true(0) } OPTIONAL,
   ...
}

MeasResultListWLAN-r13 ::= SEQUENCE (SIZE (1..maxCellReport)) OF MeasResultWLAN-r13

MeasResultCBR-r14 ::= SEQUENCE {
   poolIdentity-r14 [0] SL-V2X-TxPoolReportIdentity-r14,
   cbr-PSSCH-r14 [1] SL-CBR-r14,
   cbr-PSCCH-r14 [2] SL-CBR-r14 OPTIONAL
}

MeasResultListCBR-r14 ::= SEQUENCE (SIZE (1..maxCBR-Report-r14)) OF MeasResultCBR-r14

MeasResultListWLAN-r14 ::= SEQUENCE (SIZE (1..maxWLAN-Id-Report-r14)) OF MeasResultWLAN-r13

MeasResultServFreqNR-r15 ::= SEQUENCE {
   carrierFreq-r15 [0] ARFCN-ValueNR-r15,
   measResultSCell-r15 [1] MeasResultCellNR-r15 OPTIONAL,
   measResultBestNeighCell-r15 [2] MeasResultCellNR-r15 OPTIONAL,
   ...
}

MeasResultServFreqListNR-r15 ::= SEQUENCE (SIZE (1..maxServCell-r13)) OF 
   MeasResultServFreqNR-r15

MeasResultCellSFTD-r15 ::= SEQUENCE {
   physCellId-r15 [0] PhysCellIdNR-r15,
   sfn-OffsetResult-r15 [1] INTEGER (0..1023),
   frameBoundaryOffsetResult-r15 [2] INTEGER (-30720..30719),
   rsrpResult-r15 [3] RSRP-RangeNR-r15 OPTIONAL
}

MeasResultCellListSFTD-r15 ::= SEQUENCE (SIZE (1..maxCellSFTD)) OF MeasResultCellSFTD-r15

LogMeasResultBT-r15 ::= SEQUENCE {
   bt-Addr-r15 [0] BIT STRING  (SIZE (48)),
   rssi-BT-r15 [1] INTEGER (-128..127) OPTIONAL,
   ...
}

LogMeasResultListBT-r15 ::= SEQUENCE (SIZE (1..maxBT-IdReport-r15)) OF LogMeasResultBT-r15

WLAN-RTT-r15 ::= SEQUENCE {
   rttValue-r15 [0] INTEGER (0..16777215),
   rttUnits-r15 [1] ENUMERATED { microseconds(0), hundredsofnanoseconds(1), 
      tensofnanoseconds(2), nanoseconds(3), tenthsofnanoseconds(4), ... },
   rttAccuracy-r15 [2] INTEGER (0..255) OPTIONAL,
   ...
}

LogMeasResultWLAN-r15 ::= SEQUENCE {
   wlan-Identifiers-r15 [0] WLAN-Identifiers-r12,
   rssiWLAN-r15 [1] WLAN-RSSI-Range-r13 OPTIONAL,
   rtt-WLAN-r15 [2] WLAN-RTT-r15 OPTIONAL,
   ...
}

LogMeasResultListWLAN-r15 ::= SEQUENCE (SIZE (1..maxWLAN-Id-Report-r14)) OF LogMeasResultWLAN-r15

SensingResult-r15 ::= SEQUENCE {
   resourceIndex-r15 [0] INTEGER (1..2000)
}

MeasResultSensing-r15 ::= SEQUENCE {
   sl-SubframeRef-r15 [0] INTEGER (0..10239),
   sensingResult-r15 [1] SEQUENCE (SIZE (0..400)) OF SensingResult-r15
}

MeasResults ::= SEQUENCE {
   measId [0] MeasId,
   measResultPCell [1] SEQUENCE {
      rsrpResult [0] RSRP-Range,
      rsrqResult [1] RSRQ-Range
   },
   measResultNeighCells [2] EXPLICIT CHOICE {
      measResultListEUTRA [0] MeasResultListEUTRA,
      measResultListUTRA [1] MeasResultListUTRA,
      measResultListGERAN [2] MeasResultListGERAN,
      measResultsCDMA2000 [3] MeasResultsCDMA2000,
      ...,
      measResultNeighCellListNR-r15 [4] MeasResultCellListNR-r15
   } OPTIONAL,
   ...,
   [[
      measResultForECID-r9 [3] MeasResultForECID-r9 OPTIONAL
   ]],
   [[
      locationInfo-r10 [4] LocationInfo-r10 OPTIONAL,
      measResultServFreqList-r10 [5] MeasResultServFreqList-r10 OPTIONAL
   ]],
   [[
      measId-v1250 [6] MeasId-v1250 OPTIONAL,
      measResultPCell-v1250 [7] RSRQ-Range-v1250 OPTIONAL,
      measResultCSI-RS-List-r12 [8] MeasResultCSI-RS-List-r12 OPTIONAL
   ]],
   [[
      measResultForRSSI-r13 [9] MeasResultForRSSI-r13 OPTIONAL,
      measResultServFreqListExt-r13 [10] MeasResultServFreqListExt-r13 OPTIONAL
         ,
      measResultSSTD-r13 [11] MeasResultSSTD-r13 OPTIONAL,
      measResultPCell-v1310 [12] SEQUENCE {
         rs-sinr-Result-r13 [0] RS-SINR-Range-r13
      } OPTIONAL,
      ul-PDCP-DelayResultList-r13 [13] UL-PDCP-DelayResultList-r13 OPTIONAL,
      measResultListWLAN-r13 [14] MeasResultListWLAN-r13 OPTIONAL
   ]],
   [[
      measResultPCell-v1360 [15] RSRP-Range-v1360 OPTIONAL
   ]],
   [[
      measResultListCBR-r14 [16] MeasResultListCBR-r14 OPTIONAL,
      measResultListWLAN-r14 [17] MeasResultListWLAN-r14 OPTIONAL
   ]],
   [[
      measResultServFreqListNR-r15 [18] MeasResultServFreqListNR-r15 OPTIONAL,
      measResultCellListSFTD-r15 [19] MeasResultCellListSFTD-r15 OPTIONAL
   ]],
   [[
      logMeasResultListBT-r15 [20] LogMeasResultListBT-r15 OPTIONAL,
      logMeasResultListWLAN-r15 [21] LogMeasResultListWLAN-r15 OPTIONAL,
      measResultSensing-r15 [22] MeasResultSensing-r15 OPTIONAL,
      heightUE-r15 [23] INTEGER (-400..8880) OPTIONAL
   ]]
}

MeasurementReport-v8a0-IEs ::= SEQUENCE {
   lateNonCriticalExtension [0] OCTET STRING OPTIONAL,
   nonCriticalExtension [1] SEQUENCE {

   } OPTIONAL
}

MeasurementReport-r8-IEs ::= SEQUENCE {
   measResults [0] MeasResults,
   nonCriticalExtension [1] MeasurementReport-v8a0-IEs OPTIONAL
}

MeasurementReport ::= SEQUENCE {
   criticalExtensions [0] EXPLICIT CHOICE {
      c1 [0] EXPLICIT CHOICE {
         measurementReport-r8 [0] MeasurementReport-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

PerCC-GapIndication-r14 ::= SEQUENCE {
   servCellId-r14 [0] ServCellIndex-r13,
   gapIndication-r14 [1] ENUMERATED { gap(0), ncsg(1), nogap-noNcsg(2) }
}

PerCC-GapIndicationList-r14 ::= SEQUENCE (SIZE (1..maxServCell-r13)) OF PerCC-GapIndication-r14
   

RRCConnectionReconfigurationComplete-v1530-IEs ::= SEQUENCE {
   logMeasAvailableBT-r15 [0] ENUMERATED { true(0) } OPTIONAL,
   logMeasAvailableWLAN-r15 [1] ENUMERATED { true(0) } OPTIONAL,
   flightPathInfoAvailable-r15 [2] ENUMERATED { true(0) } OPTIONAL,
   nonCriticalExtension [3] SEQUENCE {

   } OPTIONAL
}

RRCConnectionReconfigurationComplete-v1510-IEs ::= SEQUENCE {
   scg-ConfigResponseNR-r15 [0] OCTET STRING OPTIONAL,
   nonCriticalExtension [1] RRCConnectionReconfigurationComplete-v1530-IEs
       OPTIONAL
}

RRCConnectionReconfigurationComplete-v1430-IEs ::= SEQUENCE {
   perCC-GapIndicationList-r14 [0] PerCC-GapIndicationList-r14 OPTIONAL,
   numFreqEffective-r14 [1] INTEGER (1..12) OPTIONAL,
   numFreqEffectiveReduced-r14 [2] INTEGER (1..12) OPTIONAL,
   nonCriticalExtension [3] RRCConnectionReconfigurationComplete-v1510-IEs
       OPTIONAL
}

RRCConnectionReconfigurationComplete-v1250-IEs ::= SEQUENCE {
   logMeasAvailableMBSFN-r12 [0] ENUMERATED { true(0) } OPTIONAL,
   nonCriticalExtension [1] RRCConnectionReconfigurationComplete-v1430-IEs
       OPTIONAL
}

RRCConnectionReconfigurationComplete-v1130-IEs ::= SEQUENCE {
   connEstFailInfoAvailable-r11 [0] ENUMERATED { true(0) } OPTIONAL,
   nonCriticalExtension [1] RRCConnectionReconfigurationComplete-v1250-IEs
       OPTIONAL
}

RRCConnectionReconfigurationComplete-v1020-IEs ::= SEQUENCE {
   rlf-InfoAvailable-r10 [0] ENUMERATED { true(0) } OPTIONAL,
   logMeasAvailable-r10 [1] ENUMERATED { true(0) } OPTIONAL,
   nonCriticalExtension [2] RRCConnectionReconfigurationComplete-v1130-IEs
       OPTIONAL
}

RRCConnectionReconfigurationComplete-v8a0-IEs ::= SEQUENCE {
   lateNonCriticalExtension [0] OCTET STRING OPTIONAL,
   nonCriticalExtension [1] RRCConnectionReconfigurationComplete-v1020-IEs
       OPTIONAL
}

RRCConnectionReconfigurationComplete-r8-IEs ::= SEQUENCE {
   nonCriticalExtension [0] RRCConnectionReconfigurationComplete-v8a0-IEs
       OPTIONAL
}

RRCConnectionReconfigurationComplete ::= SEQUENCE {
   rrc-TransactionIdentifier [0] RRC-TransactionIdentifier,
   criticalExtensions [1] EXPLICIT CHOICE {
      rrcConnectionReconfigurationComplete-r8 [0] 
         RRCConnectionReconfigurationComplete-r8-IEs,
      criticalExtensionsFuture [1] SEQUENCE {

      }
   }
}

RRCConnectionReestablishmentComplete-v1530-IEs ::= SEQUENCE {
   logMeasAvailableBT-r15 [0] ENUMERATED { true(0) } OPTIONAL,
   logMeasAvailableWLAN-r15 [1] ENUMERATED { true(0) } OPTIONAL,
   flightPathInfoAvailable-r15 [2] ENUMERATED { true(0) } OPTIONAL,
   nonCriticalExtension [3] SEQUENCE {

   } OPTIONAL
}

RRCConnectionReestablishmentComplete-v1250-IEs ::= SEQUENCE {
   logMeasAvailableMBSFN-r12 [0] ENUMERATED { true(0) } OPTIONAL,
   nonCriticalExtension [1] RRCConnectionReestablishmentComplete-v1530-IEs
       OPTIONAL
}

RRCConnectionReestablishmentComplete-v1130-IEs ::= SEQUENCE {
   connEstFailInfoAvailable-r11 [0] ENUMERATED { true(0) } OPTIONAL,
   nonCriticalExtension [1] RRCConnectionReestablishmentComplete-v1250-IEs
       OPTIONAL
}

RRCConnectionReestablishmentComplete-v1020-IEs ::= SEQUENCE {
   logMeasAvailable-r10 [0] ENUMERATED { true(0) } OPTIONAL,
   nonCriticalExtension [1] RRCConnectionReestablishmentComplete-v1130-IEs
       OPTIONAL
}

RRCConnectionReestablishmentComplete-v8a0-IEs ::= SEQUENCE {
   lateNonCriticalExtension [0] OCTET STRING OPTIONAL,
   nonCriticalExtension [1] RRCConnectionReestablishmentComplete-v1020-IEs
       OPTIONAL
}

RRCConnectionReestablishmentComplete-v920-IEs ::= SEQUENCE {
   rlf-InfoAvailable-r9 [0] ENUMERATED { true(0) } OPTIONAL,
   nonCriticalExtension [1] RRCConnectionReestablishmentComplete-v8a0-IEs
       OPTIONAL
}

RRCConnectionReestablishmentComplete-r8-IEs ::= SEQUENCE {
   nonCriticalExtension [0] RRCConnectionReestablishmentComplete-v920-IEs
       OPTIONAL
}

RRCConnectionReestablishmentComplete ::= SEQUENCE {
   rrc-TransactionIdentifier [0] RRC-TransactionIdentifier,
   criticalExtensions [1] EXPLICIT CHOICE {
      rrcConnectionReestablishmentComplete-r8 [0] 
         RRCConnectionReestablishmentComplete-r8-IEs,
      criticalExtensionsFuture [1] SEQUENCE {

      }
   }
}

RegisteredMME ::= SEQUENCE {
   plmn-Identity [0] PLMN-Identity OPTIONAL,
   mmegi [1] BIT STRING  (SIZE (16)),
   mmec [2] MMEC
}

RegisteredAMF-r15 ::= SEQUENCE {
   plmn-Identity-r15 [0] PLMN-Identity OPTIONAL,
   amf-Identifier-r15 [1] AMF-Identifier-r15
}

S-NSSAI-r15 ::= CHOICE {
   sst [0] BIT STRING  (SIZE (8)),
   sst-SD [1] BIT STRING  (SIZE (32))
}

RRCConnectionSetupComplete-v1540-IEs ::= SEQUENCE {
   gummei-Type-v1540 [0] ENUMERATED { mappedFrom5G-v1540(0) } OPTIONAL,
   guami-Type-r15 [1] ENUMERATED { native(0), mapped(1) } OPTIONAL,
   nonCriticalExtension [2] SEQUENCE {

   } OPTIONAL
}

RRCConnectionSetupComplete-v1530-IEs ::= SEQUENCE {
   logMeasAvailableBT-r15 [0] ENUMERATED { true(0) } OPTIONAL,
   logMeasAvailableWLAN-r15 [1] ENUMERATED { true(0) } OPTIONAL,
   idleMeasAvailable-r15 [2] ENUMERATED { true(0) } OPTIONAL,
   flightPathInfoAvailable-r15 [3] ENUMERATED { true(0) } OPTIONAL,
   connectTo5GC-r15 [4] ENUMERATED { true(0) } OPTIONAL,
   registeredAMF-r15 [5] RegisteredAMF-r15 OPTIONAL,
   s-NSSAI-list-r15 [6] SEQUENCE (SIZE (1..maxNrofS-NSSAI-r15)) OF S-NSSAI-r15 OPTIONAL,
   ng-5G-S-TMSI-Bits-r15 [7] EXPLICIT CHOICE {
      ng-5G-S-TMSI-r15 [0] NG-5G-S-TMSI-r15,
      ng-5G-S-TMSI-Part2-r15 [1] BIT STRING  (SIZE (8))
   } OPTIONAL,
   nonCriticalExtension [8] RRCConnectionSetupComplete-v1540-IEs OPTIONAL
}

RRCConnectionSetupComplete-v1430-IEs ::= SEQUENCE {
   dcn-ID-r14 [0] INTEGER (0..65535) OPTIONAL,
   nonCriticalExtension [1] RRCConnectionSetupComplete-v1530-IEs OPTIONAL
}

RRCConnectionSetupComplete-v1330-IEs ::= SEQUENCE {
   ue-CE-NeedULGaps-r13 [0] ENUMERATED { true(0) } OPTIONAL,
   nonCriticalExtension [1] RRCConnectionSetupComplete-v1430-IEs OPTIONAL
}

RRCConnectionSetupComplete-v1320-IEs ::= SEQUENCE {
   ce-ModeB-r13 [0] ENUMERATED { supported(0) } OPTIONAL,
   s-TMSI-r13 [1] S-TMSI OPTIONAL,
   attachWithoutPDN-Connectivity-r13 [2] ENUMERATED { true(0) } OPTIONAL,
   up-CIoT-EPS-Optimisation-r13 [3] ENUMERATED { true(0) } OPTIONAL,
   cp-CIoT-EPS-Optimisation-r13 [4] ENUMERATED { true(0) } OPTIONAL,
   nonCriticalExtension [5] RRCConnectionSetupComplete-v1330-IEs OPTIONAL
}

RRCConnectionSetupComplete-v1250-IEs ::= SEQUENCE {
   mobilityState-r12 [0] ENUMERATED { normal(0), medium(1), high(2), spare(3) }
       OPTIONAL,
   mobilityHistoryAvail-r12 [1] ENUMERATED { true(0) } OPTIONAL,
   logMeasAvailableMBSFN-r12 [2] ENUMERATED { true(0) } OPTIONAL,
   nonCriticalExtension [3] RRCConnectionSetupComplete-v1320-IEs OPTIONAL
}

RRCConnectionSetupComplete-v1130-IEs ::= SEQUENCE {
   connEstFailInfoAvailable-r11 [0] ENUMERATED { true(0) } OPTIONAL,
   nonCriticalExtension [1] RRCConnectionSetupComplete-v1250-IEs OPTIONAL
}

RRCConnectionSetupComplete-v1020-IEs ::= SEQUENCE {
   gummei-Type-r10 [0] ENUMERATED { native(0), mapped(1) } OPTIONAL,
   rlf-InfoAvailable-r10 [1] ENUMERATED { true(0) } OPTIONAL,
   logMeasAvailable-r10 [2] ENUMERATED { true(0) } OPTIONAL,
   rn-SubframeConfigReq-r10 [3] ENUMERATED { required(0), notRequired(1) }
       OPTIONAL,
   nonCriticalExtension [4] RRCConnectionSetupComplete-v1130-IEs OPTIONAL
}

RRCConnectionSetupComplete-v8a0-IEs ::= SEQUENCE {
   lateNonCriticalExtension [0] OCTET STRING OPTIONAL,
   nonCriticalExtension [1] RRCConnectionSetupComplete-v1020-IEs OPTIONAL
}

RRCConnectionSetupComplete-r8-IEs ::= SEQUENCE {
   selectedPLMN-Identity [0] INTEGER (1..maxPLMN-r11),
   registeredMME [1] RegisteredMME OPTIONAL,
   dedicatedInfoNAS [2] DedicatedInfoNAS,
   nonCriticalExtension [3] RRCConnectionSetupComplete-v8a0-IEs OPTIONAL
}

RRCConnectionSetupComplete ::= SEQUENCE {
   rrc-TransactionIdentifier [0] RRC-TransactionIdentifier,
   criticalExtensions [1] EXPLICIT CHOICE {
      c1 [0] EXPLICIT CHOICE {
         rrcConnectionSetupComplete-r8 [0] RRCConnectionSetupComplete-r8-IEs,
         spare3 [1] NULL,
         spare2 [2] NULL,
         spare1 [3] NULL
      },
      criticalExtensionsFuture [1] SEQUENCE {

      }
   }
}

SecurityModeComplete-v8a0-IEs ::= SEQUENCE {
   lateNonCriticalExtension [0] OCTET STRING OPTIONAL,
   nonCriticalExtension [1] SEQUENCE {

   } OPTIONAL
}

SecurityModeComplete-r8-IEs ::= SEQUENCE {
   nonCriticalExtension [0] SecurityModeComplete-v8a0-IEs OPTIONAL
}

SecurityModeComplete ::= SEQUENCE {
   rrc-TransactionIdentifier [0] RRC-TransactionIdentifier,
   criticalExtensions [1] EXPLICIT CHOICE {
      securityModeComplete-r8 [0] SecurityModeComplete-r8-IEs,
      criticalExtensionsFuture [1] SEQUENCE {

      }
   }
}

SecurityModeFailure-v8a0-IEs ::= SEQUENCE {
   lateNonCriticalExtension [0] OCTET STRING OPTIONAL,
   nonCriticalExtension [1] SEQUENCE {

   } OPTIONAL
}

SecurityModeFailure-r8-IEs ::= SEQUENCE {
   nonCriticalExtension [0] SecurityModeFailure-v8a0-IEs OPTIONAL
}

SecurityModeFailure ::= SEQUENCE {
   rrc-TransactionIdentifier [0] RRC-TransactionIdentifier,
   criticalExtensions [1] EXPLICIT CHOICE {
      securityModeFailure-r8 [0] SecurityModeFailure-r8-IEs,
      criticalExtensionsFuture [1] SEQUENCE {

      }
   }
}

UE-CapabilityRAT-Container ::= SEQUENCE {
   rat-Type [0] RAT-Type,
   ueCapabilityRAT-Container [1] OCTET STRING
}

UE-CapabilityRAT-ContainerList ::= SEQUENCE (SIZE (0..maxRAT-Capabilities)) OF 
   UE-CapabilityRAT-Container

UE-RadioPagingInfo-r12 ::= SEQUENCE {
   ue-Category-v1250 [0] INTEGER (0) OPTIONAL,
   ...,
   [[
      ue-CategoryDL-v1310 [1] ENUMERATED { m1(0) } OPTIONAL,
      ce-ModeA-r13 [2] ENUMERATED { true(0) } OPTIONAL,
      ce-ModeB-r13 [3] ENUMERATED { true(0) } OPTIONAL
   ]],
   [[
      wakeUpSignal-r15 [4] ENUMERATED { true(0) } OPTIONAL,
      wakeUpSignal-TDD-r15 [5] ENUMERATED { true(0) } OPTIONAL,
      wakeUpSignalMinGap-eDRX-r15 [6] ENUMERATED { ms40(0), ms240(1), ms1000(2)
         , ms2000(3) } OPTIONAL,
      wakeUpSignalMinGap-eDRX-TDD-r15 [7] ENUMERATED { ms40(0), ms240(1), 
         ms1000(2), ms2000(3) } OPTIONAL
   ]]
}

UECapabilityInformation-v1250-IEs ::= SEQUENCE {
   ue-RadioPagingInfo-r12 [0] UE-RadioPagingInfo-r12 OPTIONAL,
   nonCriticalExtension [1] SEQUENCE {

   } OPTIONAL
}

UECapabilityInformation-v8a0-IEs ::= SEQUENCE {
   lateNonCriticalExtension [0] OCTET STRING OPTIONAL,
   nonCriticalExtension [1] UECapabilityInformation-v1250-IEs OPTIONAL
}

UECapabilityInformation-r8-IEs ::= SEQUENCE {
   ue-CapabilityRAT-ContainerList [0] UE-CapabilityRAT-ContainerList,
   nonCriticalExtension [1] UECapabilityInformation-v8a0-IEs OPTIONAL
}

UECapabilityInformation ::= SEQUENCE {
   rrc-TransactionIdentifier [0] RRC-TransactionIdentifier,
   criticalExtensions [1] EXPLICIT CHOICE {
      c1 [0] EXPLICIT CHOICE {
         ueCapabilityInformation-r8 [0] UECapabilityInformation-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

ULHandoverPreparationTransfer-v8a0-IEs ::= SEQUENCE {
   lateNonCriticalExtension [0] OCTET STRING OPTIONAL,
   nonCriticalExtension [1] SEQUENCE {

   } OPTIONAL
}

ULHandoverPreparationTransfer-r8-IEs ::= SEQUENCE {
   cdma2000-Type [0] CDMA2000-Type,
   meid [1] BIT STRING  (SIZE (56)) OPTIONAL,
   dedicatedInfo [2] DedicatedInfoCDMA2000,
   nonCriticalExtension [3] ULHandoverPreparationTransfer-v8a0-IEs OPTIONAL
}

ULHandoverPreparationTransfer ::= SEQUENCE {
   criticalExtensions [0] EXPLICIT CHOICE {
      c1 [0] EXPLICIT CHOICE {
         ulHandoverPreparationTransfer-r8 [0] 
            ULHandoverPreparationTransfer-r8-IEs,
         spare3 [1] NULL,
         spare2 [2] NULL,
         spare1 [3] NULL
      },
      criticalExtensionsFuture [1] SEQUENCE {

      }
   }
}

ULInformationTransfer-v8a0-IEs ::= SEQUENCE {
   lateNonCriticalExtension [0] OCTET STRING OPTIONAL,
   nonCriticalExtension [1] SEQUENCE {

   } OPTIONAL
}

ULInformationTransfer-r8-IEs ::= SEQUENCE {
   dedicatedInfoType [0] EXPLICIT CHOICE {
      dedicatedInfoNAS [0] DedicatedInfoNAS,
      dedicatedInfoCDMA2000-1XRTT [1] DedicatedInfoCDMA2000,
      dedicatedInfoCDMA2000-HRPD [2] DedicatedInfoCDMA2000
   },
   nonCriticalExtension [1] ULInformationTransfer-v8a0-IEs OPTIONAL
}

ULInformationTransfer ::= SEQUENCE {
   criticalExtensions [0] EXPLICIT CHOICE {
      c1 [0] EXPLICIT CHOICE {
         ulInformationTransfer-r8 [0] ULInformationTransfer-r8-IEs,
         spare3 [1] NULL,
         spare2 [2] NULL,
         spare1 [3] NULL
      },
      criticalExtensionsFuture [1] SEQUENCE {

      }
   }
}

DRB-CountInfo ::= SEQUENCE {
   drb-Identity [0] DRB-Identity,
   count-Uplink [1] INTEGER (0..4294967295),
   count-Downlink [2] INTEGER (0..4294967295)
}

DRB-CountInfoList ::= SEQUENCE (SIZE (0..maxDRB)) OF DRB-CountInfo

DRB-CountInfoListExt-r15 ::= SEQUENCE (SIZE (1..maxDRBExt-r15)) OF DRB-CountInfo

CounterCheckResponse-v1530-IEs ::= SEQUENCE {
   drb-CountInfoListExt-r15 [0] DRB-CountInfoListExt-r15 OPTIONAL,
   nonCriticalExtension [1] SEQUENCE {

   } OPTIONAL
}

CounterCheckResponse-v8a0-IEs ::= SEQUENCE {
   lateNonCriticalExtension [0] OCTET STRING OPTIONAL,
   nonCriticalExtension [1] CounterCheckResponse-v1530-IEs OPTIONAL
}

CounterCheckResponse-r8-IEs ::= SEQUENCE {
   drb-CountInfoList [0] DRB-CountInfoList,
   nonCriticalExtension [1] CounterCheckResponse-v8a0-IEs OPTIONAL
}

CounterCheckResponse ::= SEQUENCE {
   rrc-TransactionIdentifier [0] RRC-TransactionIdentifier,
   criticalExtensions [1] EXPLICIT CHOICE {
      counterCheckResponse-r8 [0] CounterCheckResponse-r8-IEs,
      criticalExtensionsFuture [1] SEQUENCE {

      }
   }
}

MeasResult2EUTRA-r9 ::= SEQUENCE {
   carrierFreq-r9 [0] ARFCN-ValueEUTRA,
   measResultList-r9 [1] MeasResultListEUTRA
}

MeasResultList2EUTRA-r9 ::= SEQUENCE (SIZE (1..maxFreq)) OF MeasResult2EUTRA-r9

MeasResult2UTRA-r9 ::= SEQUENCE {
   carrierFreq-r9 [0] ARFCN-ValueUTRA,
   measResultList-r9 [1] MeasResultListUTRA
}

MeasResultList2UTRA-r9 ::= SEQUENCE (SIZE (1..maxFreq)) OF MeasResult2UTRA-r9

MeasResult2CDMA2000-r9 ::= SEQUENCE {
   carrierFreq-r9 [0] CarrierFreqCDMA2000,
   measResultList-r9 [1] MeasResultsCDMA2000
}

MeasResultList2CDMA2000-r9 ::= SEQUENCE (SIZE (1..maxFreq)) OF MeasResult2CDMA2000-r9

RSRQ-Type-r12 ::= SEQUENCE {
   allSymbols-r12 [0] BOOLEAN,
   wideBand-r12 [1] BOOLEAN
}

MeasResult2EUTRA-v1250 ::= SEQUENCE {
   rsrq-Type-r12 [0] RSRQ-Type-r12 OPTIONAL
}

MeasResultList2EUTRA-v1250 ::= SEQUENCE (SIZE (1..maxFreq)) OF MeasResult2EUTRA-v1250

RLF-Report-r9 ::= SEQUENCE {
   measResultLastServCell-r9 [0] SEQUENCE {
      rsrpResult-r9 [0] RSRP-Range,
      rsrqResult-r9 [1] RSRQ-Range OPTIONAL
   },
   measResultNeighCells-r9 [1] SEQUENCE {
      measResultListEUTRA-r9 [0] MeasResultList2EUTRA-r9 OPTIONAL,
      measResultListUTRA-r9 [1] MeasResultList2UTRA-r9 OPTIONAL,
      measResultListGERAN-r9 [2] MeasResultListGERAN OPTIONAL,
      measResultsCDMA2000-r9 [3] MeasResultList2CDMA2000-r9 OPTIONAL
   } OPTIONAL,
   ...,
   [[
      locationInfo-r10 [2] LocationInfo-r10 OPTIONAL,
      failedPCellId-r10 [3] EXPLICIT CHOICE {
         cellGlobalId-r10 [0] CellGlobalIdEUTRA,
         pci-arfcn-r10 [1] SEQUENCE {
            physCellId-r10 [0] PhysCellId,
            carrierFreq-r10 [1] ARFCN-ValueEUTRA
         }
      } OPTIONAL,
      reestablishmentCellId-r10 [4] CellGlobalIdEUTRA OPTIONAL,
      timeConnFailure-r10 [5] INTEGER (0..1023) OPTIONAL,
      connectionFailureType-r10 [6] ENUMERATED { rlf(0), hof(1) } OPTIONAL,
      previousPCellId-r10 [7] CellGlobalIdEUTRA OPTIONAL
   ]],
   [[
      failedPCellId-v1090 [8] SEQUENCE {
         carrierFreq-v1090 [0] ARFCN-ValueEUTRA-v9e0
      } OPTIONAL
   ]],
   [[
      basicFields-r11 [9] SEQUENCE {
         c-RNTI-r11 [0] C-RNTI,
         rlf-Cause-r11 [1] ENUMERATED { t310-Expiry(0), randomAccessProblem(1)
            , rlc-MaxNumRetx(2), t312-Expiry-r12(3) },
         timeSinceFailure-r11 [2] TimeSinceFailure-r11
      } OPTIONAL,
      previousUTRA-CellId-r11 [10] SEQUENCE {
         carrierFreq-r11 [0] ARFCN-ValueUTRA,
         physCellId-r11 [1] EXPLICIT CHOICE {
            fdd-r11 [0] PhysCellIdUTRA-FDD,
            tdd-r11 [1] PhysCellIdUTRA-TDD
         },
         cellGlobalId-r11 [2] CellGlobalIdUTRA OPTIONAL
      } OPTIONAL,
      selectedUTRA-CellId-r11 [11] SEQUENCE {
         carrierFreq-r11 [0] ARFCN-ValueUTRA,
         physCellId-r11 [1] EXPLICIT CHOICE {
            fdd-r11 [0] PhysCellIdUTRA-FDD,
            tdd-r11 [1] PhysCellIdUTRA-TDD
         }
      } OPTIONAL
   ]],
   [[
      failedPCellId-v1250 [12] SEQUENCE {
         tac-FailedPCell-r12 [0] TrackingAreaCode
      } OPTIONAL,
      measResultLastServCell-v1250 [13] RSRQ-Range-v1250 OPTIONAL,
      lastServCellRSRQ-Type-r12 [14] RSRQ-Type-r12 OPTIONAL,
      measResultListEUTRA-v1250 [15] MeasResultList2EUTRA-v1250 OPTIONAL
   ]],
   [[
      drb-EstablishedWithQCI-1-r13 [16] ENUMERATED { qci1(0) } OPTIONAL
   ]],
   [[
      measResultLastServCell-v1360 [17] RSRP-Range-v1360 OPTIONAL
   ]],
   [[
      logMeasResultListBT-r15 [18] LogMeasResultListBT-r15 OPTIONAL,
      logMeasResultListWLAN-r15 [19] LogMeasResultListWLAN-r15 OPTIONAL
   ]]
}

MeasResult2EUTRA-v9e0 ::= SEQUENCE {
   carrierFreq-v9e0 [0] ARFCN-ValueEUTRA-v9e0 OPTIONAL
}

MeasResultList2EUTRA-v9e0 ::= SEQUENCE (SIZE (1..maxFreq)) OF MeasResult2EUTRA-v9e0

RLF-Report-v9e0 ::= SEQUENCE {
   measResultListEUTRA-v9e0 [0] MeasResultList2EUTRA-v9e0
}

-- Late non critical extensions
UEInformationResponse-v9e0-IEs ::= SEQUENCE {
   rlf-Report-v9e0 [0] RLF-Report-v9e0 OPTIONAL,
   nonCriticalExtension [1] SEQUENCE {

   } OPTIONAL
}

MeasResultList2GERAN-r10 ::= SEQUENCE (SIZE (1..maxCellListGERAN)) OF MeasResultListGERAN

BLER-Result-r12 ::= SEQUENCE {
   bler-r12 [0] BLER-Range-r12,
   blocksReceived-r12 [1] SEQUENCE {
      n-r12 [0] BIT STRING  (SIZE (3)),
      m-r12 [1] BIT STRING  (SIZE (8))
   }
}

DataBLER-MCH-Result-r12 ::= SEQUENCE {
   mch-Index-r12 [0] INTEGER (1..maxPMCH-PerMBSFN),
   dataBLER-Result-r12 [1] BLER-Result-r12
}

DataBLER-MCH-ResultList-r12 ::= SEQUENCE (SIZE (1..maxPMCH-PerMBSFN)) OF DataBLER-MCH-Result-r12
   

MeasResultMBSFN-r12 ::= SEQUENCE {
   mbsfn-Area-r12 [0] SEQUENCE {
      mbsfn-AreaId-r12 [0] MBSFN-AreaId-r12,
      carrierFreq-r12 [1] ARFCN-ValueEUTRA-r9
   },
   rsrpResultMBSFN-r12 [1] RSRP-Range,
   rsrqResultMBSFN-r12 [2] MBSFN-RSRQ-Range-r12,
   signallingBLER-Result-r12 [3] BLER-Result-r12 OPTIONAL,
   dataBLER-MCH-ResultList-r12 [4] DataBLER-MCH-ResultList-r12 OPTIONAL,
   ...
}

MeasResultListMBSFN-r12 ::= SEQUENCE (SIZE (1..maxMBSFN-Area)) OF MeasResultMBSFN-r12

LogMeasInfo-r10 ::= SEQUENCE {
   locationInfo-r10 [0] LocationInfo-r10 OPTIONAL,
   relativeTimeStamp-r10 [1] INTEGER (0..7200),
   servCellIdentity-r10 [2] CellGlobalIdEUTRA,
   measResultServCell-r10 [3] SEQUENCE {
      rsrpResult-r10 [0] RSRP-Range,
      rsrqResult-r10 [1] RSRQ-Range
   },
   measResultNeighCells-r10 [4] SEQUENCE {
      measResultListEUTRA-r10 [0] MeasResultList2EUTRA-r9 OPTIONAL,
      measResultListUTRA-r10 [1] MeasResultList2UTRA-r9 OPTIONAL,
      measResultListGERAN-r10 [2] MeasResultList2GERAN-r10 OPTIONAL,
      measResultListCDMA2000-r10 [3] MeasResultList2CDMA2000-r9 OPTIONAL
   } OPTIONAL,
   ...,
   [[
      measResultListEUTRA-v1090 [5] MeasResultList2EUTRA-v9e0 OPTIONAL
   ]],
   [[
      measResultListMBSFN-r12 [6] MeasResultListMBSFN-r12 OPTIONAL,
      measResultServCell-v1250 [7] RSRQ-Range-v1250 OPTIONAL,
      servCellRSRQ-Type-r12 [8] RSRQ-Type-r12 OPTIONAL,
      measResultListEUTRA-v1250 [9] MeasResultList2EUTRA-v1250 OPTIONAL
   ]],
   [[
      inDeviceCoexDetected-r13 [10] ENUMERATED { true(0) } OPTIONAL
   ]],
   [[
      measResultServCell-v1360 [11] RSRP-Range-v1360 OPTIONAL
   ]],
   [[
      logMeasResultListBT-r15 [12] LogMeasResultListBT-r15 OPTIONAL,
      logMeasResultListWLAN-r15 [13] LogMeasResultListWLAN-r15 OPTIONAL
   ]],
   [[
      anyCellSelectionDetected-r15 [14] ENUMERATED { true(0) } OPTIONAL
   ]]
}

LogMeasInfoList-r10 ::= SEQUENCE (SIZE (1..maxLogMeasReport-r10)) OF LogMeasInfo-r10

LogMeasReport-r10 ::= SEQUENCE {
   absoluteTimeStamp-r10 [0] AbsoluteTimeInfo-r10,
   traceReference-r10 [1] TraceReference-r10,
   traceRecordingSessionRef-r10 [2] OCTET STRING (SIZE (2)),
   tce-Id-r10 [3] OCTET STRING (SIZE (1)),
   logMeasInfoList-r10 [4] LogMeasInfoList-r10,
   logMeasAvailable-r10 [5] ENUMERATED { true(0) } OPTIONAL,
   ...,
   [[
      logMeasAvailableBT-r15 [6] ENUMERATED { true(0) } OPTIONAL,
      logMeasAvailableWLAN-r15 [7] ENUMERATED { true(0) } OPTIONAL
   ]]
}

ConnEstFailReport-r11 ::= SEQUENCE {
   failedCellId-r11 [0] CellGlobalIdEUTRA,
   locationInfo-r11 [1] LocationInfo-r10 OPTIONAL,
   measResultFailedCell-r11 [2] SEQUENCE {
      rsrpResult-r11 [0] RSRP-Range,
      rsrqResult-r11 [1] RSRQ-Range OPTIONAL
   },
   measResultNeighCells-r11 [3] SEQUENCE {
      measResultListEUTRA-r11 [0] MeasResultList2EUTRA-r9 OPTIONAL,
      measResultListUTRA-r11 [1] MeasResultList2UTRA-r9 OPTIONAL,
      measResultListGERAN-r11 [2] MeasResultListGERAN OPTIONAL,
      measResultsCDMA2000-r11 [3] MeasResultList2CDMA2000-r9 OPTIONAL
   } OPTIONAL,
   numberOfPreamblesSent-r11 [4] NumberOfPreamblesSent-r11,
   contentionDetected-r11 [5] BOOLEAN,
   maxTxPowerReached-r11 [6] BOOLEAN,
   timeSinceFailure-r11 [7] TimeSinceFailure-r11,
   measResultListEUTRA-v1130 [8] MeasResultList2EUTRA-v9e0 OPTIONAL,
   ...,
   [[
      measResultFailedCell-v1250 [9] RSRQ-Range-v1250 OPTIONAL,
      failedCellRSRQ-Type-r12 [10] RSRQ-Type-r12 OPTIONAL,
      measResultListEUTRA-v1250 [11] MeasResultList2EUTRA-v1250 OPTIONAL
   ]],
   [[
      measResultFailedCell-v1360 [12] RSRP-Range-v1360 OPTIONAL
   ]],
   [[
      logMeasResultListBT-r15 [13] LogMeasResultListBT-r15 OPTIONAL,
      logMeasResultListWLAN-r15 [14] LogMeasResultListWLAN-r15 OPTIONAL
   ]]
}

MeasResultIdleEUTRA-r15 ::= SEQUENCE {
   carrierFreq-r15 [0] ARFCN-ValueEUTRA-r9,
   physCellId-r15 [1] PhysCellId,
   measResult-r15 [2] SEQUENCE {
      rsrpResult-r15 [0] RSRP-Range,
      rsrqResult-r15 [1] RSRQ-Range-r13
   },
   ...
}

MeasResultIdleListEUTRA-r15 ::= SEQUENCE (SIZE (1..maxCellMeasIdle-r15)) OF MeasResultIdleEUTRA-r15
   

MeasResultIdle-r15 ::= SEQUENCE {
   measResultServingCell-r15 [0] SEQUENCE {
      rsrpResult-r15 [0] RSRP-Range,
      rsrqResult-r15 [1] RSRQ-Range-r13
   },
   measResultNeighCells-r15 [1] EXPLICIT CHOICE {
      measResultIdleListEUTRA-r15 [0] MeasResultIdleListEUTRA-r15,
      ...
   } OPTIONAL,
   ...
}

MeasResultListIdle-r15 ::= SEQUENCE (SIZE (1..maxIdleMeasCarriers-r15)) OF MeasResultIdle-r15

WayPointLocation-r15 ::= SEQUENCE {
   wayPointLocation-r15 [0] LocationInfo-r10,
   timeStamp-r15 [1] AbsoluteTimeInfo-r10 OPTIONAL
}

FlightPathInfoReport-r15 ::= SEQUENCE {
   flightPath-r15 [0] SEQUENCE (SIZE (1..maxWayPoint-r15)) OF WayPointLocation-r15 OPTIONAL,
   nonCriticalExtension [1] SEQUENCE {

   } OPTIONAL
}

UEInformationResponse-v1530-IEs ::= SEQUENCE {
   measResultListIdle-r15 [0] MeasResultListIdle-r15 OPTIONAL,
   flightPathInfoReport-r15 [1] FlightPathInfoReport-r15 OPTIONAL,
   nonCriticalExtension [2] SEQUENCE {

   } OPTIONAL
}

UEInformationResponse-v1250-IEs ::= SEQUENCE {
   mobilityHistoryReport-r12 [0] MobilityHistoryReport-r12 OPTIONAL,
   nonCriticalExtension [1] UEInformationResponse-v1530-IEs OPTIONAL
}

UEInformationResponse-v1130-IEs ::= SEQUENCE {
   connEstFailReport-r11 [0] ConnEstFailReport-r11 OPTIONAL,
   nonCriticalExtension [1] UEInformationResponse-v1250-IEs OPTIONAL
}

UEInformationResponse-v1020-IEs ::= SEQUENCE {
   logMeasReport-r10 [0] LogMeasReport-r10 OPTIONAL,
   nonCriticalExtension [1] UEInformationResponse-v1130-IEs OPTIONAL
}

-- Regular non critical extensions
UEInformationResponse-v930-IEs ::= SEQUENCE {
   lateNonCriticalExtension [0] OCTET STRING (CONTAINING 
      UEInformationResponse-v9e0-IEs) OPTIONAL,
   nonCriticalExtension [1] UEInformationResponse-v1020-IEs OPTIONAL
}

UEInformationResponse-r9-IEs ::= SEQUENCE {
   rach-Report-r9 [0] SEQUENCE {
      numberOfPreamblesSent-r9 [0] NumberOfPreamblesSent-r11,
      contentionDetected-r9 [1] BOOLEAN
   } OPTIONAL,
   rlf-Report-r9 [1] RLF-Report-r9 OPTIONAL,
   nonCriticalExtension [2] UEInformationResponse-v930-IEs OPTIONAL
}

UEInformationResponse-r9 ::= SEQUENCE {
   rrc-TransactionIdentifier [0] RRC-TransactionIdentifier,
   criticalExtensions [1] EXPLICIT CHOICE {
      c1 [0] EXPLICIT CHOICE {
         ueInformationResponse-r9 [0] UEInformationResponse-r9-IEs,
         spare3 [1] NULL,
         spare2 [2] NULL,
         spare1 [3] NULL
      },
      criticalExtensionsFuture [1] SEQUENCE {

      }
   }
}

ProximityIndication-v930-IEs ::= SEQUENCE {
   lateNonCriticalExtension [0] OCTET STRING OPTIONAL,
   nonCriticalExtension [1] SEQUENCE {

   } OPTIONAL
}

ProximityIndication-r9-IEs ::= SEQUENCE {
   type-r9 [0] ENUMERATED { entering(0), leaving(1) },
   carrierFreq-r9 [1] EXPLICIT CHOICE {
      eutra-r9 [0] ARFCN-ValueEUTRA,
      utra-r9 [1] ARFCN-ValueUTRA,
      ...,
      eutra2-v9e0 [2] ARFCN-ValueEUTRA-v9e0
   },
   nonCriticalExtension [2] ProximityIndication-v930-IEs OPTIONAL
}

ProximityIndication-r9 ::= SEQUENCE {
   criticalExtensions [0] EXPLICIT CHOICE {
      c1 [0] EXPLICIT CHOICE {
         proximityIndication-r9 [0] ProximityIndication-r9-IEs,
         spare3 [1] NULL,
         spare2 [2] NULL,
         spare1 [3] NULL
      },
      criticalExtensionsFuture [1] SEQUENCE {

      }
   }
}

RNReconfigurationComplete-r10-IEs ::= SEQUENCE {
   lateNonCriticalExtension [0] OCTET STRING OPTIONAL,
   nonCriticalExtension [1] SEQUENCE {

   } OPTIONAL
}

RNReconfigurationComplete-r10 ::= SEQUENCE {
   rrc-TransactionIdentifier [0] RRC-TransactionIdentifier,
   criticalExtensions [1] EXPLICIT CHOICE {
      c1 [0] EXPLICIT CHOICE {
         rnReconfigurationComplete-r10 [0] RNReconfigurationComplete-r10-IEs,
         spare3 [1] NULL,
         spare2 [2] NULL,
         spare1 [3] NULL
      },
      criticalExtensionsFuture [1] SEQUENCE {

      }
   }
}

CountingResponseInfo-r10 ::= SEQUENCE {
   countingResponseService-r10 [0] INTEGER (0..maxServiceCount-1),
   ...
}

CountingResponseList-r10 ::= SEQUENCE (SIZE (1..maxServiceCount)) OF CountingResponseInfo-r10

MBMSCountingResponse-r10-IEs ::= SEQUENCE {
   mbsfn-AreaIndex-r10 [0] INTEGER (0..maxMBSFN-Area-1) OPTIONAL,
   countingResponseList-r10 [1] CountingResponseList-r10 OPTIONAL,
   lateNonCriticalExtension [2] OCTET STRING OPTIONAL,
   nonCriticalExtension [3] SEQUENCE {

   } OPTIONAL
}

MBMSCountingResponse-r10 ::= SEQUENCE {
   criticalExtensions [0] EXPLICIT CHOICE {
      c1 [0] EXPLICIT CHOICE {
         countingResponse-r10 [0] MBMSCountingResponse-r10-IEs,
         spare3 [1] NULL,
         spare2 [2] NULL,
         spare1 [3] NULL
      },
      criticalExtensionsFuture [1] SEQUENCE {

      }
   }
}

RSTD-InterFreqInfo-r10 ::= SEQUENCE {
   carrierFreq-r10 [0] ARFCN-ValueEUTRA,
   measPRS-Offset-r10 [1] INTEGER (0..39),
   ...,
   [[
      carrierFreq-v1090 [2] ARFCN-ValueEUTRA-v9e0 OPTIONAL
   ]],
   [[
      measPRS-Offset-r15 [3] EXPLICIT CHOICE {
         rstd0-r15 [0] INTEGER (0..79),
         rstd1-r15 [1] INTEGER (0..159),
         rstd2-r15 [2] INTEGER (0..319),
         rstd3-r15 [3] INTEGER (0..639),
         rstd4-r15 [4] INTEGER (0..1279),
         rstd5-r15 [5] INTEGER (0..159),
         rstd6-r15 [6] INTEGER (0..319),
         rstd7-r15 [7] INTEGER (0..639),
         rstd8-r15 [8] INTEGER (0..1279),
         rstd9-r15 [9] INTEGER (0..319),
         rstd10-r15 [10] INTEGER (0..639),
         rstd11-r15 [11] INTEGER (0..1279),
         rstd12-r15 [12] INTEGER (0..319),
         rstd13-r15 [13] INTEGER (0..639),
         rstd14-r15 [14] INTEGER (0..1279),
         rstd15-r15 [15] INTEGER (0..639),
         rstd16-r15 [16] INTEGER (0..1279),
         rstd17-r15 [17] INTEGER (0..639),
         rstd18-r15 [18] INTEGER (0..1279),
         rstd19-r15 [19] INTEGER (0..639),
         rstd20-r15 [20] INTEGER (0..1279)
      } OPTIONAL
   ]]
}

RSTD-InterFreqInfoList-r10 ::= SEQUENCE (SIZE (1..maxRSTD-Freq-r10)) OF RSTD-InterFreqInfo-r10

InterFreqRSTDMeasurementIndication-r10-IEs ::= SEQUENCE {
   rstd-InterFreqIndication-r10 [0] EXPLICIT CHOICE {
      start [0] SEQUENCE {
         rstd-InterFreqInfoList-r10 [0] RSTD-InterFreqInfoList-r10
      },
      stop [1] NULL
   },
   lateNonCriticalExtension [1] OCTET STRING OPTIONAL,
   nonCriticalExtension [2] SEQUENCE {

   } OPTIONAL
}

InterFreqRSTDMeasurementIndication-r10 ::= SEQUENCE {
   criticalExtensions [0] EXPLICIT CHOICE {
      c1 [0] EXPLICIT CHOICE {
         interFreqRSTDMeasurementIndication-r10 [0] 
            InterFreqRSTDMeasurementIndication-r10-IEs,
         spare3 [1] NULL,
         spare2 [2] NULL,
         spare1 [3] NULL
      },
      criticalExtensionsFuture [1] SEQUENCE {

      }
   }
}

BW-Preference-r14 ::= SEQUENCE {
   dl-Preference-r14 [0] ENUMERATED { mhz1dot4(0), mhz5(1), mhz20(2) } OPTIONAL
      ,
   ul-Preference-r14 [1] ENUMERATED { mhz1dot4(0), mhz5(1) } OPTIONAL
}

TrafficPatternInfo-r14 ::= SEQUENCE {
   trafficPeriodicity-r14 [0] ENUMERATED { sf20(0), sf50(1), sf100(2), sf200(3)
      , sf300(4), sf400(5), sf500(6), sf600(7), sf700(8), sf800(9), sf900(10), 
      sf1000(11) },
   timingOffset-r14 [1] INTEGER (0..10239),
   priorityInfoSL-r14 [2] SL-Priority-r13 OPTIONAL,
   logicalChannelIdentityUL-r14 [3] INTEGER (3..10) OPTIONAL,
   messageSize-r14 [4] BIT STRING  (SIZE (6))
}

TrafficPatternInfoList-r14 ::= SEQUENCE (SIZE (1..maxTrafficPattern-r14)) OF TrafficPatternInfo-r14

DelayBudgetReport-r14 ::= CHOICE {
   type1 [0] ENUMERATED { msMinus1280(0), msMinus640(1), msMinus320(2), 
      msMinus160(3), msMinus80(4), msMinus60(5), msMinus40(6), msMinus20(7), 
      ms0(8), ms20(9), ms40(10), ms60(11), ms80(12), ms160(13), ms320(14), 
      ms640(15), ms1280(16) },
   type2 [1] ENUMERATED { msMinus192(0), msMinus168(1), msMinus144(2), 
      msMinus120(3), msMinus96(4), msMinus72(5), msMinus48(6), msMinus24(7), 
      ms0(8), ms24(9), ms48(10), ms72(11), ms96(12), ms120(13), ms144(14), 
      ms168(15), ms192(16) }
}

OverheatingAssistance-r14 ::= SEQUENCE {
   reducedUE-Category [0] SEQUENCE {
      reducedUE-CategoryDL [0] INTEGER (0..19),
      reducedUE-CategoryUL [1] INTEGER (0..21)
   } OPTIONAL,
   reducedMaxCCs [1] SEQUENCE {
      reducedCCsDL [0] INTEGER (0..31),
      reducedCCsUL [1] INTEGER (0..31)
   } OPTIONAL
}

TrafficPatternInfo-v1530 ::= SEQUENCE {
   trafficDestination-r15 [0] SL-DestinationIdentity-r12 OPTIONAL,
   reliabilityInfoSL-r15 [1] SL-Reliability-r15 OPTIONAL
}

TrafficPatternInfoList-v1530 ::= SEQUENCE (SIZE (1..maxTrafficPattern-r14)) OF 
   TrafficPatternInfo-v1530

UEAssistanceInformation-v1530-IEs ::= SEQUENCE {
   sps-AssistanceInformation-v1530 [0] SEQUENCE {
      trafficPatternInfoListSL-v1530 [0] TrafficPatternInfoList-v1530
   } OPTIONAL,
   nonCriticalExtension [1] SEQUENCE {

   } OPTIONAL
}

UEAssistanceInformation-v1450-IEs ::= SEQUENCE {
   overheatingAssistance-r14 [0] OverheatingAssistance-r14 OPTIONAL,
   nonCriticalExtension [1] UEAssistanceInformation-v1530-IEs OPTIONAL
}

UEAssistanceInformation-v1430-IEs ::= SEQUENCE {
   bw-Preference-r14 [0] BW-Preference-r14 OPTIONAL,
   sps-AssistanceInformation-r14 [1] SEQUENCE {
      trafficPatternInfoListSL-r14 [0] TrafficPatternInfoList-r14 OPTIONAL,
      trafficPatternInfoListUL-r14 [1] TrafficPatternInfoList-r14 OPTIONAL
   } OPTIONAL,
   rlm-Report-r14 [2] SEQUENCE {
      rlm-Event-r14 [0] ENUMERATED { earlyOutOfSync(0), earlyInSync(1) },
      excessRep-MPDCCH-r14 [1] ENUMERATED { excessRep1(0), excessRep2(1) }
          OPTIONAL
   } OPTIONAL,
   delayBudgetReport-r14 [3] EXPLICIT DelayBudgetReport-r14 OPTIONAL,
   nonCriticalExtension [4] UEAssistanceInformation-v1450-IEs OPTIONAL
}

UEAssistanceInformation-r11-IEs ::= SEQUENCE {
   powerPrefIndication-r11 [0] ENUMERATED { normal(0), lowPowerConsumption(1) }
       OPTIONAL,
   lateNonCriticalExtension [1] OCTET STRING OPTIONAL,
   nonCriticalExtension [2] UEAssistanceInformation-v1430-IEs OPTIONAL
}

UEAssistanceInformation-r11 ::= SEQUENCE {
   criticalExtensions [0] EXPLICIT CHOICE {
      c1 [0] EXPLICIT CHOICE {
         ueAssistanceInformation-r11 [0] UEAssistanceInformation-r11-IEs,
         spare3 [1] NULL,
         spare2 [2] NULL,
         spare1 [3] NULL
      },
      criticalExtensionsFuture [1] SEQUENCE {

      }
   }
}

AffectedCarrierFreq-r11 ::= SEQUENCE {
   carrierFreq-r11 [0] MeasObjectId,
   interferenceDirection-r11 [1] ENUMERATED { eutra(0), other(1), both(2), 
      spare(3) }
}

AffectedCarrierFreqList-r11 ::= SEQUENCE (SIZE (1..maxFreqIDC-r11)) OF AffectedCarrierFreq-r11
   

IDC-SubframePattern-r11 ::= CHOICE {
   subframePatternFDD-r11 [0] BIT STRING  (SIZE (4)),
   subframePatternTDD-r11 [1] EXPLICIT CHOICE {
      subframeConfig0-r11 [0] BIT STRING  (SIZE (70)),
      subframeConfig1-5-r11 [1] BIT STRING  (SIZE (10)),
      subframeConfig6-r11 [2] BIT STRING  (SIZE (60))
   },
   ...
}

IDC-SubframePatternList-r11 ::= SEQUENCE (SIZE (1..maxSubframePatternIDC-r11)) OF IDC-SubframePattern-r11
   

TDM-AssistanceInfo-r11 ::= CHOICE {
   drx-AssistanceInfo-r11 [0] SEQUENCE {
      drx-CycleLength-r11 [0] ENUMERATED { sf40(0), sf64(1), sf80(2), sf128(3)
         , sf160(4), sf256(5), spare2(6), spare1(7) },
      drx-Offset-r11 [1] INTEGER (0..255) OPTIONAL,
      drx-ActiveTime-r11 [2] ENUMERATED { sf20(0), sf30(1), sf40(2), sf60(3), 
         sf80(4), sf100(5), spare2(6), spare1(7) }
   },
   idc-SubframePatternList-r11 [1] IDC-SubframePatternList-r11,
   ...
}

AffectedCarrierFreqComb-r11 ::= SEQUENCE (SIZE (2..maxServCell-r10)) OF MeasObjectId

AffectedCarrierFreqCombList-r11 ::= SEQUENCE (SIZE (1..maxCombIDC-r11)) OF 
   AffectedCarrierFreqComb-r11

VictimSystemType-r11 ::= SEQUENCE {
   gps-r11 [0] ENUMERATED { true(0) } OPTIONAL,
   glonass-r11 [1] ENUMERATED { true(0) } OPTIONAL,
   bds-r11 [2] ENUMERATED { true(0) } OPTIONAL,
   galileo-r11 [3] ENUMERATED { true(0) } OPTIONAL,
   wlan-r11 [4] ENUMERATED { true(0) } OPTIONAL,
   bluetooth-r11 [5] ENUMERATED { true(0) } OPTIONAL
}

AffectedCarrierFreq-v1310 ::= SEQUENCE {
   carrierFreq-v1310 [0] MeasObjectId-v1310 OPTIONAL
}

AffectedCarrierFreqList-v1310 ::= SEQUENCE (SIZE (1..maxFreqIDC-r11)) OF 
   AffectedCarrierFreq-v1310

AffectedCarrierFreqComb-r13 ::= SEQUENCE (SIZE (2..maxServCell-r13)) OF MeasObjectId-r13

AffectedCarrierFreqCombList-r13 ::= SEQUENCE (SIZE (1..maxCombIDC-r11)) OF 
   AffectedCarrierFreqComb-r13

AffectedCarrierFreqComb-r15 ::= SEQUENCE (SIZE (1..maxServCell-r13)) OF MeasObjectId-r13

AffectedCarrierFreqCombNR-r15 ::= SEQUENCE (SIZE (1..maxServCellNR-r15)) OF ARFCN-ValueNR-r15

AffectedCarrierFreqCombInfoMRDC-r15 ::= SEQUENCE {
   victimSystemType-r15 [0] VictimSystemType-r11,
   interferenceDirectionMRDC-r15 [1] ENUMERATED { eutra-nr(0), nr(1), other(2)
      , eutra-nr-other(3), nr-other(4), spare3(5), spare2(6), spare1(7) },
   affectedCarrierFreqCombMRDC-r15 [2] SEQUENCE {
      affectedCarrierFreqCombEUTRA-r15 [0] AffectedCarrierFreqComb-r15 OPTIONAL
         ,
      affectedCarrierFreqCombNR-r15 [1] AffectedCarrierFreqCombNR-r15
   } OPTIONAL
}

MRDC-AssistanceInfo-r15 ::= SEQUENCE {
   affectedCarrierFreqCombInfoListMRDC-r15 [0] SEQUENCE (SIZE (1..maxCombIDC-r11)) OF 
      AffectedCarrierFreqCombInfoMRDC-r15,
   ...
}

InDeviceCoexIndication-v1530-IEs ::= SEQUENCE {
   mrdc-AssistanceInfo-r15 [0] MRDC-AssistanceInfo-r15 OPTIONAL,
   nonCriticalExtension [1] SEQUENCE {

   } OPTIONAL
}

InDeviceCoexIndication-v1360-IEs ::= SEQUENCE {
   hardwareSharingProblem-r13 [0] ENUMERATED { true(0) } OPTIONAL,
   nonCriticalExtension [1] InDeviceCoexIndication-v1530-IEs OPTIONAL
}

InDeviceCoexIndication-v1310-IEs ::= SEQUENCE {
   affectedCarrierFreqList-v1310 [0] AffectedCarrierFreqList-v1310 OPTIONAL,
   affectedCarrierFreqCombList-r13 [1] AffectedCarrierFreqCombList-r13 OPTIONAL
      ,
   nonCriticalExtension [2] InDeviceCoexIndication-v1360-IEs OPTIONAL
}

InDeviceCoexIndication-v11d0-IEs ::= SEQUENCE {
   ul-CA-AssistanceInfo-r11 [0] SEQUENCE {
      affectedCarrierFreqCombList-r11 [0] AffectedCarrierFreqCombList-r11
          OPTIONAL,
      victimSystemType-r11 [1] VictimSystemType-r11
   } OPTIONAL,
   nonCriticalExtension [1] InDeviceCoexIndication-v1310-IEs OPTIONAL
}

InDeviceCoexIndication-r11-IEs ::= SEQUENCE {
   affectedCarrierFreqList-r11 [0] AffectedCarrierFreqList-r11 OPTIONAL,
   tdm-AssistanceInfo-r11 [1] EXPLICIT TDM-AssistanceInfo-r11 OPTIONAL,
   lateNonCriticalExtension [2] OCTET STRING OPTIONAL,
   nonCriticalExtension [3] InDeviceCoexIndication-v11d0-IEs OPTIONAL
}

InDeviceCoexIndication-r11 ::= SEQUENCE {
   criticalExtensions [0] EXPLICIT CHOICE {
      c1 [0] EXPLICIT CHOICE {
         inDeviceCoexIndication-r11 [0] InDeviceCoexIndication-r11-IEs,
         spare3 [1] NULL,
         spare2 [2] NULL,
         spare1 [3] NULL
      },
      criticalExtensionsFuture [1] SEQUENCE {

      }
   }
}

CarrierFreqListMBMS-r11 ::= SEQUENCE (SIZE (1..maxFreqMBMS-r11)) OF ARFCN-ValueEUTRA-r9

MBMS-ServiceInfo-r13 ::= SEQUENCE {
   tmgi-r13 [0] TMGI-r9
}

MBMS-ServiceList-r13 ::= SEQUENCE (SIZE (0..maxMBMS-ServiceListPerUE-r13)) OF MBMS-ServiceInfo-r13

MBMS-ROM-Info-r15 ::= SEQUENCE {
   mbms-ROM-Freq-r15 [0] ARFCN-ValueEUTRA-r9,
   mbms-ROM-SubcarrierSpacing-r15 [1] ENUMERATED { kHz15(0), kHz7dot5(1), 
      kHz1dot25(2) },
   mbms-Bandwidth-r15 [2] ENUMERATED { n6(0), n15(1), n25(2), n50(3), n75(4), 
      n100(5) }
}

MBMSInterestIndication-v1540-IEs ::= SEQUENCE {
   mbms-ROM-InfoList-r15 [0] SEQUENCE (SIZE (1..maxMBMS-ServiceListPerUE-r13)) OF MBMS-ROM-Info-r15 OPTIONAL
      ,
   nonCriticalExtension [1] SEQUENCE {

   } OPTIONAL
}

MBMSInterestIndication-v1310-IEs ::= SEQUENCE {
   mbms-Services-r13 [0] MBMS-ServiceList-r13 OPTIONAL,
   nonCriticalExtension [1] MBMSInterestIndication-v1540-IEs OPTIONAL
}

MBMSInterestIndication-r11-IEs ::= SEQUENCE {
   mbms-FreqList-r11 [0] CarrierFreqListMBMS-r11 OPTIONAL,
   mbms-Priority-r11 [1] ENUMERATED { true(0) } OPTIONAL,
   lateNonCriticalExtension [2] OCTET STRING OPTIONAL,
   nonCriticalExtension [3] MBMSInterestIndication-v1310-IEs OPTIONAL
}

MBMSInterestIndication-r11 ::= SEQUENCE {
   criticalExtensions [0] EXPLICIT CHOICE {
      c1 [0] EXPLICIT CHOICE {
         interestIndication-r11 [0] MBMSInterestIndication-r11-IEs,
         spare3 [1] NULL,
         spare2 [2] NULL,
         spare1 [3] NULL
      },
      criticalExtensionsFuture [1] SEQUENCE {

      }
   }
}

-- Regular non-critical extensions:
FailureReportSCG-r12 ::= SEQUENCE {
   failureType-r12 [0] ENUMERATED { t313-Expiry(0), randomAccessProblem(1), 
      rlc-MaxNumRetx(2), scg-ChangeFailure(3) },
   measResultServFreqList-r12 [1] MeasResultServFreqList-r10 OPTIONAL,
   measResultNeighCells-r12 [2] MeasResultList2EUTRA-r9 OPTIONAL,
   ...,
   [[
      failureType-v1290 [3] ENUMERATED { maxUL-TimingDiff-v1290(0) } OPTIONAL
   ]],
   [[
      measResultServFreqListExt-r13 [4] MeasResultServFreqListExt-r13 OPTIONAL
   ]]
}

FailureReportSCG-v12d0 ::= SEQUENCE {
   measResultNeighCells-v12d0 [0] MeasResultList2EUTRA-v9e0 OPTIONAL
}

-- Late non-critical extensions:
SCGFailureInformation-v12d0b-IEs ::= SEQUENCE {
   failureReportSCG-v12d0 [0] FailureReportSCG-v12d0 OPTIONAL,
   nonCriticalExtension [1] SEQUENCE {

   } OPTIONAL
}

SCGFailureInformation-v12d0a-IEs ::= SEQUENCE {
   lateNonCriticalExtension [0] OCTET STRING (CONTAINING 
      SCGFailureInformation-v12d0b-IEs) OPTIONAL,
   nonCriticalExtension [1] SEQUENCE {

   } OPTIONAL
}

SCGFailureInformation-r12-IEs ::= SEQUENCE {
   failureReportSCG-r12 [0] FailureReportSCG-r12 OPTIONAL,
   nonCriticalExtension [1] SCGFailureInformation-v12d0a-IEs OPTIONAL
}

SCGFailureInformation-r12 ::= SEQUENCE {
   criticalExtensions [0] EXPLICIT CHOICE {
      c1 [0] EXPLICIT CHOICE {
         scgFailureInformation-r12 [0] SCGFailureInformation-r12-IEs,
         spare3 [1] NULL,
         spare2 [2] NULL,
         spare1 [3] NULL
      },
      criticalExtensionsFuture [1] SEQUENCE {

      }
   }
}

SL-CommTxResourceReq-r12 ::= SEQUENCE {
   carrierFreq-r12 [0] ARFCN-ValueEUTRA-r9 OPTIONAL,
   destinationInfoList-r12 [1] SL-DestinationInfoList-r12
}

SL-DiscTxResourceReq-r13 ::= SEQUENCE {
   carrierFreqDiscTx-r13 [0] INTEGER (1..maxFreq) OPTIONAL,
   discTxResourceReq-r13 [1] INTEGER (1..63)
}

SL-DiscTxResourceReqPerFreqList-r13 ::= SEQUENCE (SIZE (1..maxFreq)) OF 
   SL-DiscTxResourceReq-r13

SL-GapFreqInfo-r13 ::= SEQUENCE {
   carrierFreq-r13 [0] ARFCN-ValueEUTRA-r9 OPTIONAL,
   gapPatternList-r13 [1] SL-GapPatternList-r13
}

SL-GapRequest-r13 ::= SEQUENCE (SIZE (1..maxFreq)) OF SL-GapFreqInfo-r13

SL-DiscSysInfoReport-r13 ::= SEQUENCE {
   plmn-IdentityList-r13 [0] PLMN-IdentityList OPTIONAL,
   cellIdentity-13 [1] CellIdentity OPTIONAL,
   carrierFreqInfo-13 [2] ARFCN-ValueEUTRA-r9 OPTIONAL,
   discRxResources-r13 [3] SL-DiscRxPoolList-r12 OPTIONAL,
   discTxPoolCommon-r13 [4] SL-DiscTxPoolList-r12 OPTIONAL,
   discTxPowerInfo-r13 [5] SL-DiscTxPowerInfoList-r12 OPTIONAL,
   discSyncConfig-r13 [6] SL-SyncConfigNFreq-r13 OPTIONAL,
   discCellSelectionInfo-r13 [7] SEQUENCE {
      q-RxLevMin-r13 [0] Q-RxLevMin,
      q-RxLevMinOffset-r13 [1] INTEGER (1..8) OPTIONAL
   } OPTIONAL,
   cellReselectionInfo-r13 [8] SEQUENCE {
      q-Hyst-r13 [0] ENUMERATED { dB0(0), dB1(1), dB2(2), dB3(3), dB4(4), 
         dB5(5), dB6(6), dB8(7), dB10(8), dB12(9), dB14(10), dB16(11), dB18(12)
         , dB20(13), dB22(14), dB24(15) },
      q-RxLevMin-r13 [1] Q-RxLevMin,
      t-ReselectionEUTRA-r13 [2] T-Reselection
   } OPTIONAL,
   tdd-Config-r13 [9] TDD-Config OPTIONAL,
   freqInfo-r13 [10] SEQUENCE {
      ul-CarrierFreq-r13 [0] ARFCN-ValueEUTRA OPTIONAL,
      ul-Bandwidth-r13 [1] ENUMERATED { n6(0), n15(1), n25(2), n50(3), n75(4), 
         n100(5) } OPTIONAL,
      additionalSpectrumEmission-r13 [2] AdditionalSpectrumEmission OPTIONAL
   } OPTIONAL,
   p-Max-r13 [11] P-Max OPTIONAL,
   referenceSignalPower-r13 [12] INTEGER (-60..50) OPTIONAL,
   ...,
   [[
      freqInfo-v1370 [13] SEQUENCE {
         additionalSpectrumEmission-v1370 [0] AdditionalSpectrumEmission-v10l0
      } OPTIONAL
   ]]
}

SL-DiscSysInfoReportFreqList-r13 ::= SEQUENCE (SIZE (1..maxSL-DiscSysInfoReportFreq-r13)) OF 
   SL-DiscSysInfoReport-r13

SL-V2X-CommFreqList-r14 ::= SEQUENCE (SIZE (1..maxFreqV2X-r14)) OF INTEGER (0..maxFreqV2X-1-r14)

SL-V2X-CommTxResourceReq-r14 ::= SEQUENCE {
   carrierFreqCommTx-r14 [0] INTEGER (0..maxFreqV2X-1-r14) OPTIONAL,
   v2x-TypeTxSync-r14 [1] SL-TypeTxSync-r14 OPTIONAL,
   v2x-DestinationInfoList-r14 [2] SL-DestinationInfoList-r12 OPTIONAL
}

SL-V2X-CommTxFreqList-r14 ::= SEQUENCE (SIZE (1..maxFreqV2X-r14)) OF 
   SL-V2X-CommTxResourceReq-r14

SidelinkUEInformation-v1530-IEs ::= SEQUENCE {
   reliabilityInfoListSL-r15 [0] SL-ReliabilityList-r15 OPTIONAL,
   nonCriticalExtension [1] SEQUENCE {

   } OPTIONAL
}

SidelinkUEInformation-v1430-IEs ::= SEQUENCE {
   v2x-CommRxInterestedFreqList-r14 [0] SL-V2X-CommFreqList-r14 OPTIONAL,
   p2x-CommTxType-r14 [1] ENUMERATED { true(0) } OPTIONAL,
   v2x-CommTxResourceReq-r14 [2] SL-V2X-CommTxFreqList-r14 OPTIONAL,
   nonCriticalExtension [3] SidelinkUEInformation-v1530-IEs OPTIONAL
}

SidelinkUEInformation-v1310-IEs ::= SEQUENCE {
   commTxResourceReqUC-r13 [0] SL-CommTxResourceReq-r12 OPTIONAL,
   commTxResourceInfoReqRelay-r13 [1] SEQUENCE {
      commTxResourceReqRelay-r13 [0] SL-CommTxResourceReq-r12 OPTIONAL,
      commTxResourceReqRelayUC-r13 [1] SL-CommTxResourceReq-r12 OPTIONAL,
      ue-Type-r13 [2] ENUMERATED { relayUE(0), remoteUE(1) }
   } OPTIONAL,
   discTxResourceReq-v1310 [2] SEQUENCE {
      carrierFreqDiscTx-r13 [0] INTEGER (1..maxFreq) OPTIONAL,
      discTxResourceReqAddFreq-r13 [1] SL-DiscTxResourceReqPerFreqList-r13
          OPTIONAL
   } OPTIONAL,
   discTxResourceReqPS-r13 [3] SL-DiscTxResourceReq-r13 OPTIONAL,
   discRxGapReq-r13 [4] SL-GapRequest-r13 OPTIONAL,
   discTxGapReq-r13 [5] SL-GapRequest-r13 OPTIONAL,
   discSysInfoReportFreqList-r13 [6] SL-DiscSysInfoReportFreqList-r13 OPTIONAL,
   nonCriticalExtension [7] SidelinkUEInformation-v1430-IEs OPTIONAL
}

SidelinkUEInformation-r12-IEs ::= SEQUENCE {
   commRxInterestedFreq-r12 [0] ARFCN-ValueEUTRA-r9 OPTIONAL,
   commTxResourceReq-r12 [1] SL-CommTxResourceReq-r12 OPTIONAL,
   discRxInterest-r12 [2] ENUMERATED { true(0) } OPTIONAL,
   discTxResourceReq-r12 [3] INTEGER (1..63) OPTIONAL,
   lateNonCriticalExtension [4] OCTET STRING OPTIONAL,
   nonCriticalExtension [5] SidelinkUEInformation-v1310-IEs OPTIONAL
}

SidelinkUEInformation-r12 ::= SEQUENCE {
   criticalExtensions [0] EXPLICIT CHOICE {
      c1 [0] EXPLICIT CHOICE {
         sidelinkUEInformation-r12 [0] SidelinkUEInformation-r12-IEs,
         spare3 [1] NULL,
         spare2 [2] NULL,
         spare1 [3] NULL
      },
      criticalExtensionsFuture [1] SEQUENCE {

      }
   }
}

WLANConnectionStatusReport-v1430-IEs ::= SEQUENCE {
   wlan-Status-v1430 [0] WLAN-Status-v1430,
   nonCriticalExtension [1] SEQUENCE {

   } OPTIONAL
}

WLANConnectionStatusReport-r13-IEs ::= SEQUENCE {
   wlan-Status-r13 [0] WLAN-Status-r13,
   lateNonCriticalExtension [1] OCTET STRING OPTIONAL,
   nonCriticalExtension [2] WLANConnectionStatusReport-v1430-IEs OPTIONAL
}

WLANConnectionStatusReport-r13 ::= SEQUENCE {
   criticalExtensions [0] EXPLICIT CHOICE {
      c1 [0] EXPLICIT CHOICE {
         wlanConnectionStatusReport-r13 [0] WLANConnectionStatusReport-r13-IEs,
         spare3 [1] NULL,
         spare2 [2] NULL,
         spare1 [3] NULL
      },
      criticalExtensionsFuture [1] SEQUENCE {

      }
   }
}

RRCConnectionResumeComplete-v1530-IEs ::= SEQUENCE {
   logMeasAvailableBT-r15 [0] ENUMERATED { true(0) } OPTIONAL,
   logMeasAvailableWLAN-r15 [1] ENUMERATED { true(0) } OPTIONAL,
   idleMeasAvailable-r15 [2] ENUMERATED { true(0) } OPTIONAL,
   flightPathInfoAvailable-r15 [3] ENUMERATED { true(0) } OPTIONAL,
   nonCriticalExtension [4] SEQUENCE {

   } OPTIONAL
}

RRCConnectionResumeComplete-r13-IEs ::= SEQUENCE {
   selectedPLMN-Identity-r13 [0] INTEGER (1..maxPLMN-r11) OPTIONAL,
   dedicatedInfoNAS-r13 [1] DedicatedInfoNAS OPTIONAL,
   rlf-InfoAvailable-r13 [2] ENUMERATED { true(0) } OPTIONAL,
   logMeasAvailable-r13 [3] ENUMERATED { true(0) } OPTIONAL,
   connEstFailInfoAvailable-r13 [4] ENUMERATED { true(0) } OPTIONAL,
   mobilityState-r13 [5] ENUMERATED { normal(0), medium(1), high(2), spare(3) }
       OPTIONAL,
   mobilityHistoryAvail-r13 [6] ENUMERATED { true(0) } OPTIONAL,
   logMeasAvailableMBSFN-r13 [7] ENUMERATED { true(0) } OPTIONAL,
   lateNonCriticalExtension [8] OCTET STRING OPTIONAL,
   nonCriticalExtension [9] RRCConnectionResumeComplete-v1530-IEs OPTIONAL
}

RRCConnectionResumeComplete-r13 ::= SEQUENCE {
   rrc-TransactionIdentifier [0] RRC-TransactionIdentifier,
   criticalExtensions [1] EXPLICIT CHOICE {
      rrcConnectionResumeComplete-r13 [0] RRCConnectionResumeComplete-r13-IEs,
      criticalExtensionsFuture [1] SEQUENCE {

      }
   }
}

ULInformationTransferMRDC-r15-IEs ::= SEQUENCE {
   ul-DCCH-MessageNR-r15 [0] OCTET STRING OPTIONAL,
   lateNonCriticalExtension [1] OCTET STRING OPTIONAL,
   nonCriticalExtension [2] SEQUENCE {

   } OPTIONAL
}

ULInformationTransferMRDC-r15 ::= SEQUENCE {
   criticalExtensions [0] EXPLICIT CHOICE {
      c1 [0] EXPLICIT CHOICE {
         ulInformationTransferMRDC-r15 [0] ULInformationTransferMRDC-r15-IEs,
         spare3 [1] NULL,
         spare2 [2] NULL,
         spare1 [3] NULL
      },
      criticalExtensionsFuture [1] SEQUENCE {

      }
   }
}

MeasResultFreqFailNR-r15 ::= SEQUENCE {
   carrierFreq-r15 [0] ARFCN-ValueNR-r15,
   measResultCellList-r15 [1] MeasResultCellListNR-r15 OPTIONAL,
   ...
}

MeasResultFreqListFailNR-r15 ::= SEQUENCE (SIZE (1..maxFreqNR-r15)) OF 
   MeasResultFreqFailNR-r15

FailureReportSCG-NR-r15 ::= SEQUENCE {
   failureType-r15 [0] ENUMERATED { t310-Expiry(0), randomAccessProblem(1), 
      rlc-MaxNumRetx(2), synchReconfigFailureSCG(3), scg-reconfigFailure(4), 
      srb3-IntegrityFailure(5) },
   measResultFreqListNR-r15 [1] MeasResultFreqListFailNR-r15 OPTIONAL,
   measResultSCG-r15 [2] OCTET STRING OPTIONAL,
   ...
}

SCGFailureInformationNR-r15-IEs ::= SEQUENCE {
   failureReportSCG-NR-r15 [0] FailureReportSCG-NR-r15 OPTIONAL,
   nonCriticalExtension [1] SEQUENCE {

   } OPTIONAL
}

SCGFailureInformationNR-r15 ::= SEQUENCE {
   criticalExtensions [0] EXPLICIT CHOICE {
      c1 [0] EXPLICIT CHOICE {
         scgFailureInformationNR-r15 [0] SCGFailureInformationNR-r15-IEs,
         spare3 [1] NULL,
         spare2 [2] NULL,
         spare1 [3] NULL
      },
      criticalExtensionsFuture [1] SEQUENCE {

      }
   }
}

MeasReportAppLayer-r15-IEs ::= SEQUENCE {
   measReportAppLayerContainer-r15 [0] OCTET STRING (SIZE (1..8000)) OPTIONAL,
   serviceType-r15 [1] ENUMERATED { qoe(0), qoemtsi(1), spare6(2), spare5(3), 
      spare4(4), spare3(5), spare2(6), spare1(7) } OPTIONAL,
   nonCriticalExtension [2] SEQUENCE {

   } OPTIONAL
}

MeasReportAppLayer-r15 ::= SEQUENCE {
   criticalExtensions [0] EXPLICIT CHOICE {
      measReportAppLayer-r15 [0] MeasReportAppLayer-r15-IEs,
      criticalExtensionsFuture [1] SEQUENCE {

      }
   }
}

FailedLogicalChannelInfo-r15 ::= SEQUENCE {
   failedLogicalChannelIdentity-r15 [0] SEQUENCE {
      cellGroupIndication-r15 [0] ENUMERATED { mn(0), sn(1) },
      logicalChannelIdentity-r15 [1] INTEGER (1..10) OPTIONAL,
      logicalChannelIdentityExt-r15 [2] INTEGER (32..38) OPTIONAL
   },
   failureType [1] ENUMERATED { duplication(0), spare3(1), spare2(2), spare1(3)
       }
}

FailureInformation-r15 ::= SEQUENCE {
   failedLogicalChannelInfo-r15 [0] FailedLogicalChannelInfo-r15 OPTIONAL
--nonCriticalExtension is removed in this version as OPTIONAL was missing
}

UL-DCCH-MessageType ::= CHOICE {
   c1 [0] EXPLICIT CHOICE {
      csfbParametersRequestCDMA2000 [0] CSFBParametersRequestCDMA2000,
      measurementReport [1] MeasurementReport,
      rrcConnectionReconfigurationComplete [2] 
         RRCConnectionReconfigurationComplete,
      rrcConnectionReestablishmentComplete [3] 
         RRCConnectionReestablishmentComplete,
      rrcConnectionSetupComplete [4] RRCConnectionSetupComplete,
      securityModeComplete [5] SecurityModeComplete,
      securityModeFailure [6] SecurityModeFailure,
      ueCapabilityInformation [7] UECapabilityInformation,
      ulHandoverPreparationTransfer [8] ULHandoverPreparationTransfer,
      ulInformationTransfer [9] ULInformationTransfer,
      counterCheckResponse [10] CounterCheckResponse,
      ueInformationResponse-r9 [11] UEInformationResponse-r9,
      proximityIndication-r9 [12] ProximityIndication-r9,
      rnReconfigurationComplete-r10 [13] RNReconfigurationComplete-r10,
      mbmsCountingResponse-r10 [14] MBMSCountingResponse-r10,
      interFreqRSTDMeasurementIndication-r10 [15] 
         InterFreqRSTDMeasurementIndication-r10
   },
   messageClassExtension [1] EXPLICIT CHOICE {
      c2 [0] EXPLICIT CHOICE {
         ueAssistanceInformation-r11 [0] UEAssistanceInformation-r11,
         inDeviceCoexIndication-r11 [1] InDeviceCoexIndication-r11,
         mbmsInterestIndication-r11 [2] MBMSInterestIndication-r11,
         scgFailureInformation-r12 [3] SCGFailureInformation-r12,
         sidelinkUEInformation-r12 [4] SidelinkUEInformation-r12,
         wlanConnectionStatusReport-r13 [5] WLANConnectionStatusReport-r13,
         rrcConnectionResumeComplete-r13 [6] RRCConnectionResumeComplete-r13,
         ulInformationTransferMRDC-r15 [7] ULInformationTransferMRDC-r15,
         scgFailureInformationNR-r15 [8] SCGFailureInformationNR-r15,
         measReportAppLayer-r15 [9] MeasReportAppLayer-r15,
         failureInformation-r15 [10] FailureInformation-r15,
         spare5 [11] NULL,
         spare4 [12] NULL,
         spare3 [13] NULL,
         spare2 [14] NULL,
         spare1 [15] NULL
      },
      messageClassExtensionFuture-r11 [1] SEQUENCE {

      }
   }
}

UL-DCCH-Message ::= SEQUENCE {
   message [0] EXPLICIT UL-DCCH-MessageType
}

MBMSSessionInfo-r13 ::= SEQUENCE {
   tmgi-r13 [0] TMGI-r9,
   sessionId-r13 [1] OCTET STRING (SIZE (1)) OPTIONAL -- Need OR
}

SC-MTCH-SchedulingInfo-r13 ::= SEQUENCE {
   onDurationTimerSCPTM-r13 [0] ENUMERATED { psf1(0), psf2(1), psf3(2), psf4(3)
      , psf5(4), psf6(5), psf8(6), psf10(7), psf20(8), psf30(9), psf40(10), 
      psf50(11), psf60(12), psf80(13), psf100(14), psf200(15) },
   drx-InactivityTimerSCPTM-r13 [1] ENUMERATED { psf0(0), psf1(1), psf2(2), 
      psf4(3), psf8(4), psf10(5), psf20(6), psf40(7), psf80(8), psf160(9), 
      ps320(10), psf640(11), psf960(12), psf1280(13), psf1920(14), psf2560(15)
       },
   schedulingPeriodStartOffsetSCPTM-r13 [2] EXPLICIT CHOICE {
      sf10 [0] INTEGER (0..9),
      sf20 [1] INTEGER (0..19),
      sf32 [2] INTEGER (0..31),
      sf40 [3] INTEGER (0..39),
      sf64 [4] INTEGER (0..63),
      sf80 [5] INTEGER (0..79),
      sf128 [6] INTEGER (0..127),
      sf160 [7] INTEGER (0..159),
      sf256 [8] INTEGER (0..255),
      sf320 [9] INTEGER (0..319),
      sf512 [10] INTEGER (0..511),
      sf640 [11] INTEGER (0..639),
      sf1024 [12] INTEGER (0..1023),
      sf2048 [13] INTEGER (0..2048),
      sf4096 [14] INTEGER (0..4096),
      sf8192 [15] INTEGER (0..8192)
   },
   ...
}

SC-MTCH-Info-r13 ::= SEQUENCE {
   mbmsSessionInfo-r13 [0] MBMSSessionInfo-r13,
   g-RNTI-r13 [1] BIT STRING  (SIZE (16)),
   sc-mtch-schedulingInfo-r13 [2] SC-MTCH-SchedulingInfo-r13 OPTIONAL, -- Need OP
   sc-mtch-neighbourCell-r13 [3] BIT STRING  (SIZE (maxNeighCell-SCPTM-r13)) OPTIONAL,
   ...,
   [[
      p-a-r13 [4] ENUMERATED { dB-6(0), dB-4dot77(1), dB-3(2), dB-1dot77(3), 
         dB0(4), dB1(5), dB2(6), dB3(7) } OPTIONAL
   ]]
}

SC-MTCH-InfoList-r13 ::= SEQUENCE (SIZE (0..maxSC-MTCH-r13)) OF SC-MTCH-Info-r13

PCI-ARFCN-r13 ::= SEQUENCE {
   physCellId-r13 [0] PhysCellId,
   carrierFreq-r13 [1] ARFCN-ValueEUTRA-r9 OPTIONAL
}

SCPTM-NeighbourCellList-r13 ::= SEQUENCE (SIZE (1..maxNeighCell-SCPTM-r13)) OF PCI-ARFCN-r13

SCPTMConfiguration-v1340 ::= SEQUENCE {
   p-b-r13 [0] INTEGER (0..3) OPTIONAL, -- Need ON
   nonCriticalExtension [1] SEQUENCE {

   } OPTIONAL
}

SCPTMConfiguration-r13 ::= SEQUENCE {
   sc-mtch-InfoList-r13 [0] SC-MTCH-InfoList-r13,
   scptm-NeighbourCellList-r13 [1] SCPTM-NeighbourCellList-r13 OPTIONAL, -- Need OP
   lateNonCriticalExtension [2] OCTET STRING OPTIONAL,
   nonCriticalExtension [3] SCPTMConfiguration-v1340 OPTIONAL
}

SC-MTCH-SchedulingInfo-BR-r14 ::= SEQUENCE {
   onDurationTimerSCPTM-r14 [0] ENUMERATED { psf300(0), psf400(1), psf500(2), 
      psf600(3), psf800(4), psf1000(5), psf1200(6), psf1600(7) },
   drx-InactivityTimerSCPTM-r14 [1] ENUMERATED { psf0(0), psf1(1), psf2(2), 
      psf4(3), psf8(4), psf16(5), psf32(6), psf64(7), psf128(8), psf256(9), 
      ps512(10), psf1024(11), psf2048(12), psf4096(13), psf8192(14), 
      psf16384(15) },
   schedulingPeriodStartOffsetSCPTM-r14 [2] EXPLICIT CHOICE {
      sf10 [0] INTEGER (0..9),
      sf20 [1] INTEGER (0..19),
      sf32 [2] INTEGER (0..31),
      sf40 [3] INTEGER (0..39),
      sf64 [4] INTEGER (0..63),
      sf80 [5] INTEGER (0..79),
      sf128 [6] INTEGER (0..127),
      sf160 [7] INTEGER (0..159),
      sf256 [8] INTEGER (0..255),
      sf320 [9] INTEGER (0..319),
      sf512 [10] INTEGER (0..511),
      sf640 [11] INTEGER (0..639),
      sf1024 [12] INTEGER (0..1023),
      sf2048 [13] INTEGER (0..2047),
      sf4096 [14] INTEGER (0..4095),
      sf8192 [15] INTEGER (0..8191)
   },
   ...
}

SC-MTCH-Info-BR-r14 ::= SEQUENCE {
   sc-mtch-CarrierFreq-r14 [0] ARFCN-ValueEUTRA-r9,
   mbmsSessionInfo-r14 [1] MBMSSessionInfo-r13,
   g-RNTI-r14 [2] BIT STRING  (SIZE (16)),
   sc-mtch-schedulingInfo-r14 [3] SC-MTCH-SchedulingInfo-BR-r14 OPTIONAL, -- Need OP
   sc-mtch-neighbourCell-r14 [4] BIT STRING  (SIZE (maxNeighCell-SCPTM-r13)) OPTIONAL, -- Need OP
   mpdcch-Narrowband-SC-MTCH-r14 [5] INTEGER (1..maxAvailNarrowBands-r13),
   mpdcch-NumRepetition-SC-MTCH-r14 [6] ENUMERATED { r1(0), r2(1), r4(2), r8(3)
      , r16(4), r32(5), r64(6), r128(7), r256(8) },
   mpdcch-StartSF-SC-MTCH-r14 [7] EXPLICIT CHOICE {
      fdd-r14 [0] ENUMERATED { v1(0), v1dot5(1), v2(2), v2dot5(3), v4(4), v5(5)
         , v8(6), v10(7) },
      tdd-r14 [1] ENUMERATED { v1(0), v2(1), v4(2), v5(3), v8(4), v10(5), 
         v20(6) }
   },
   mpdcch-PDSCH-HoppingConfig-SC-MTCH-r14 [8] ENUMERATED { on(0), off(1) },
   mpdcch-PDSCH-CEmodeConfig-SC-MTCH-r14 [9] ENUMERATED { ce-ModeA(0), 
      ce-ModeB(1) },
   mpdcch-PDSCH-MaxBandwidth-SC-MTCH-r14 [10] ENUMERATED { bw1dot4(0), bw5(1) }
      ,
   mpdcch-Offset-SC-MTCH-r14 [11] ENUMERATED { zero(0), oneEighth(1), 
      oneQuarter(2), threeEighth(3), oneHalf(4), fiveEighth(5), threeQuarter(6)
      , sevenEighth(7) },
   p-a-r14 [12] ENUMERATED { dB-6(0), dB-4dot77(1), dB-3(2), dB-1dot77(3), 
      dB0(4), dB1(5), dB2(6), dB3(7) } OPTIONAL,
   ...
}

SC-MTCH-InfoList-BR-r14 ::= SEQUENCE (SIZE (0..maxSC-MTCH-BR-r14)) OF SC-MTCH-Info-BR-r14

SCPTMConfiguration-BR-r14 ::= SEQUENCE {
   sc-mtch-InfoList-r14 [0] SC-MTCH-InfoList-BR-r14,
   scptm-NeighbourCellList-r14 [1] SCPTM-NeighbourCellList-r13 OPTIONAL, -- Need OP
   p-b-r14 [2] INTEGER (0..3) OPTIONAL, -- Need OR
   lateNonCriticalExtension [3] OCTET STRING OPTIONAL,
   nonCriticalExtension [4] SEQUENCE {

   } OPTIONAL
}

SC-MCCH-MessageType-r13 ::= CHOICE {
   c1 [0] EXPLICIT CHOICE {
      scptmConfiguration-r13 [0] SCPTMConfiguration-r13
   },
   messageClassExtension [1] EXPLICIT CHOICE {
      c2 [0] EXPLICIT CHOICE {
         scptmConfiguration-BR-r14 [0] SCPTMConfiguration-BR-r14,
         spare [1] NULL
      },
      messageClassExtensionFuture-r14 [1] SEQUENCE {

      }
   }
}

SC-MCCH-Message-r13 ::= SEQUENCE {
   message [0] EXPLICIT SC-MCCH-MessageType-r13
}

TDD-ConfigSL-r12 ::= SEQUENCE {
   subframeAssignmentSL-r12 [0] ENUMERATED { none(0), sa0(1), sa1(2), sa2(3), 
      sa3(4), sa4(5), sa5(6), sa6(7) }
}

MeasResult3EUTRA-r15 ::= SEQUENCE {
   carrierFreq-r15 [0] ARFCN-ValueEUTRA-r9,
   measResultServingCell-r15 [1] MeasResultEUTRA OPTIONAL,
   measResultNeighCellList-r15 [2] MeasResultListEUTRA OPTIONAL,
   ...
}

MeasResultList3EUTRA-r15 ::= SEQUENCE (SIZE (1..maxFreq)) OF MeasResult3EUTRA-r15

MeasResultSCG-FailureMRDC-r15 ::= SEQUENCE {
   measResultFreqListEUTRA-r15 [0] MeasResultList3EUTRA-r15,
   ...
}

ROHC-ProfileSupportList-r15 ::= SEQUENCE {
   profile0x0001-r15 [0] BOOLEAN,
   profile0x0002-r15 [1] BOOLEAN,
   profile0x0003-r15 [2] BOOLEAN,
   profile0x0004-r15 [3] BOOLEAN,
   profile0x0006-r15 [4] BOOLEAN,
   profile0x0101-r15 [5] BOOLEAN,
   profile0x0102-r15 [6] BOOLEAN,
   profile0x0103-r15 [7] BOOLEAN,
   profile0x0104-r15 [8] BOOLEAN
}

PDCP-Parameters ::= SEQUENCE {
   supportedROHC-Profiles [0] ROHC-ProfileSupportList-r15,
   maxNumberROHC-ContextSessions [1] ENUMERATED { cs2(0), cs4(1), cs8(2), 
      cs12(3), cs16(4), cs24(5), cs32(6), cs48(7), cs64(8), cs128(9), cs256(10)
      , cs512(11), cs1024(12), cs16384(13), spare2(14), spare1(15) } DEFAULT cs16,
   ...
}

PhyLayerParameters ::= SEQUENCE {
   ue-TxAntennaSelectionSupported [0] BOOLEAN,
   ue-SpecificRefSigsSupported [1] BOOLEAN
}

SupportedBandEUTRA ::= SEQUENCE {
   bandEUTRA [0] FreqBandIndicator,
   halfDuplex [1] BOOLEAN
}

SupportedBandListEUTRA ::= SEQUENCE (SIZE (1..maxBands)) OF SupportedBandEUTRA

RF-Parameters ::= SEQUENCE {
   supportedBandListEUTRA [0] SupportedBandListEUTRA
}

InterFreqBandInfo ::= SEQUENCE {
   interFreqNeedForGaps [0] BOOLEAN
}

InterFreqBandList ::= SEQUENCE (SIZE (1..maxBands)) OF InterFreqBandInfo

InterRAT-BandInfo ::= SEQUENCE {
   interRAT-NeedForGaps [0] BOOLEAN
}

InterRAT-BandList ::= SEQUENCE (SIZE (1..maxBands)) OF InterRAT-BandInfo

BandInfoEUTRA ::= SEQUENCE {
   interFreqBandList [0] InterFreqBandList,
   interRAT-BandList [1] InterRAT-BandList OPTIONAL
}

BandListEUTRA ::= SEQUENCE (SIZE (1..maxBands)) OF BandInfoEUTRA

MeasParameters ::= SEQUENCE {
   bandListEUTRA [0] BandListEUTRA
}

SupportedBandListUTRA-FDD ::= SEQUENCE (SIZE (1..maxBands)) OF SupportedBandUTRA-FDD

IRAT-ParametersUTRA-FDD ::= SEQUENCE {
   supportedBandListUTRA-FDD [0] SupportedBandListUTRA-FDD
}

SupportedBandListUTRA-TDD128 ::= SEQUENCE (SIZE (1..maxBands)) OF 
   SupportedBandUTRA-TDD128

IRAT-ParametersUTRA-TDD128 ::= SEQUENCE {
   supportedBandListUTRA-TDD128 [0] SupportedBandListUTRA-TDD128
}

SupportedBandListUTRA-TDD384 ::= SEQUENCE (SIZE (1..maxBands)) OF 
   SupportedBandUTRA-TDD384

IRAT-ParametersUTRA-TDD384 ::= SEQUENCE {
   supportedBandListUTRA-TDD384 [0] SupportedBandListUTRA-TDD384
}

SupportedBandListUTRA-TDD768 ::= SEQUENCE (SIZE (1..maxBands)) OF 
   SupportedBandUTRA-TDD768

IRAT-ParametersUTRA-TDD768 ::= SEQUENCE {
   supportedBandListUTRA-TDD768 [0] SupportedBandListUTRA-TDD768
}

SupportedBandListGERAN ::= SEQUENCE (SIZE (1..maxBands)) OF SupportedBandGERAN

IRAT-ParametersGERAN ::= SEQUENCE {
   supportedBandListGERAN [0] SupportedBandListGERAN,
   interRAT-PS-HO-ToGERAN [1] BOOLEAN
}

SupportedBandListHRPD ::= SEQUENCE (SIZE (1..maxCDMA-BandClass)) OF BandclassCDMA2000

IRAT-ParametersCDMA2000-HRPD ::= SEQUENCE {
   supportedBandListHRPD [0] SupportedBandListHRPD,
   tx-ConfigHRPD [1] ENUMERATED { single(0), dual(1) },
   rx-ConfigHRPD [2] ENUMERATED { single(0), dual(1) }
}

SupportedBandList1XRTT ::= SEQUENCE (SIZE (1..maxCDMA-BandClass)) OF BandclassCDMA2000

IRAT-ParametersCDMA2000-1XRTT ::= SEQUENCE {
   supportedBandList1XRTT [0] SupportedBandList1XRTT,
   tx-Config1XRTT [1] ENUMERATED { single(0), dual(1) },
   rx-Config1XRTT [2] ENUMERATED { single(0), dual(1) }
}

PhyLayerParameters-v920 ::= SEQUENCE {
   enhancedDualLayerFDD-r9 [0] ENUMERATED { supported(0) } OPTIONAL,
   enhancedDualLayerTDD-r9 [1] ENUMERATED { supported(0) } OPTIONAL
}

IRAT-ParametersGERAN-v920 ::= SEQUENCE {
   dtm-r9 [0] ENUMERATED { supported(0) } OPTIONAL,
   e-RedirectionGERAN-r9 [1] ENUMERATED { supported(0) } OPTIONAL
}

IRAT-ParametersUTRA-v920 ::= SEQUENCE {
   e-RedirectionUTRA-r9 [0] ENUMERATED { supported(0) }
}

IRAT-ParametersCDMA2000-1XRTT-v920 ::= SEQUENCE {
   e-CSFB-1XRTT-r9 [0] ENUMERATED { supported(0) },
   e-CSFB-ConcPS-Mob1XRTT-r9 [1] ENUMERATED { supported(0) } OPTIONAL
}

CSG-ProximityIndicationParameters-r9 ::= SEQUENCE {
   intraFreqProximityIndication-r9 [0] ENUMERATED { supported(0) } OPTIONAL,
   interFreqProximityIndication-r9 [1] ENUMERATED { supported(0) } OPTIONAL,
   utran-ProximityIndication-r9 [2] ENUMERATED { supported(0) } OPTIONAL
}

NeighCellSI-AcquisitionParameters-r9 ::= SEQUENCE {
   intraFreqSI-AcquisitionForHO-r9 [0] ENUMERATED { supported(0) } OPTIONAL,
   interFreqSI-AcquisitionForHO-r9 [1] ENUMERATED { supported(0) } OPTIONAL,
   utran-SI-AcquisitionForHO-r9 [2] ENUMERATED { supported(0) } OPTIONAL
}

SON-Parameters-r9 ::= SEQUENCE {
   rach-Report-r9 [0] ENUMERATED { supported(0) } OPTIONAL
}

UE-EUTRA-CapabilityAddXDD-Mode-r9 ::= SEQUENCE {
   phyLayerParameters-r9 [0] PhyLayerParameters OPTIONAL,
   featureGroupIndicators-r9 [1] BIT STRING  (SIZE (32)) OPTIONAL,
   featureGroupIndRel9Add-r9 [2] BIT STRING  (SIZE (32)) OPTIONAL,
   interRAT-ParametersGERAN-r9 [3] IRAT-ParametersGERAN OPTIONAL,
   interRAT-ParametersUTRA-r9 [4] IRAT-ParametersUTRA-v920 OPTIONAL,
   interRAT-ParametersCDMA2000-r9 [5] IRAT-ParametersCDMA2000-1XRTT-v920
       OPTIONAL,
   neighCellSI-AcquisitionParameters-r9 [6] 
      NeighCellSI-AcquisitionParameters-r9 OPTIONAL,
   ...
}

IRAT-ParametersUTRA-v9c0 ::= SEQUENCE {
   voiceOverPS-HS-UTRA-FDD-r9 [0] ENUMERATED { supported(0) } OPTIONAL,
   voiceOverPS-HS-UTRA-TDD128-r9 [1] ENUMERATED { supported(0) } OPTIONAL,
   srvcc-FromUTRA-FDD-ToUTRA-FDD-r9 [2] ENUMERATED { supported(0) } OPTIONAL,
   srvcc-FromUTRA-FDD-ToGERAN-r9 [3] ENUMERATED { supported(0) } OPTIONAL,
   srvcc-FromUTRA-TDD128-ToUTRA-TDD128-r9 [4] ENUMERATED { supported(0) }
       OPTIONAL,
   srvcc-FromUTRA-TDD128-ToGERAN-r9 [5] ENUMERATED { supported(0) } OPTIONAL
}

PhyLayerParameters-v9d0 ::= SEQUENCE {
   tm5-FDD-r9 [0] ENUMERATED { supported(0) } OPTIONAL,
   tm5-TDD-r9 [1] ENUMERATED { supported(0) } OPTIONAL
}

SupportedBandEUTRA-v9e0 ::= SEQUENCE {
   bandEUTRA-v9e0 [0] FreqBandIndicator-v9e0 OPTIONAL
}

SupportedBandListEUTRA-v9e0 ::= SEQUENCE (SIZE (1..maxBands)) OF SupportedBandEUTRA-v9e0
   

RF-Parameters-v9e0 ::= SEQUENCE {
   supportedBandListEUTRA-v9e0 [0] SupportedBandListEUTRA-v9e0 OPTIONAL
}

IRAT-ParametersUTRA-v9h0 ::= SEQUENCE {
   mfbi-UTRA-r9 [0] ENUMERATED { supported(0) }
}

OTDOA-PositioningCapabilities-r10 ::= SEQUENCE {
   otdoa-UE-Assisted-r10 [0] ENUMERATED { supported(0) },
   interFreqRSTD-Measurement-r10 [1] ENUMERATED { supported(0) } OPTIONAL
}

RF-Parameters-v10f0 ::= SEQUENCE {
   modifiedMPR-Behavior-r10 [0] BIT STRING  (SIZE (32)) OPTIONAL
}

CA-MIMO-ParametersDL-v10i0 ::= SEQUENCE {
   fourLayerTM3-TM4-r10 [0] ENUMERATED { supported(0) } OPTIONAL
}

BandParameters-v10i0 ::= SEQUENCE {
   bandParametersDL-v10i0 [0] SEQUENCE (SIZE (1..maxBandwidthClass-r10)) OF 
      CA-MIMO-ParametersDL-v10i0
}

BandCombinationParameters-v10i0 ::= SEQUENCE {
   bandParameterList-v10i0 [0] SEQUENCE (SIZE (1..maxSimultaneousBands-r10)) OF BandParameters-v10i0
       OPTIONAL
}

SupportedBandCombination-v10i0 ::= SEQUENCE (SIZE (1..maxBandComb-r10)) OF 
   BandCombinationParameters-v10i0

RF-Parameters-v10i0 ::= SEQUENCE {
   supportedBandCombination-v10i0 [0] SupportedBandCombination-v10i0 OPTIONAL
}

RF-Parameters-v10j0 ::= SEQUENCE {
   multiNS-Pmax-r10 [0] ENUMERATED { supported(0) } OPTIONAL
}

UE-EUTRA-Capability-v10j0-IEs ::= SEQUENCE {
   rf-Parameters-v10j0 [0] RF-Parameters-v10j0 OPTIONAL,
   nonCriticalExtension [1] SEQUENCE {

   } OPTIONAL
}

SupportedBandCombinationAdd-v11d0 ::= SEQUENCE (SIZE (1..maxBandComb-r11)) OF 
   BandCombinationParameters-v10i0

RF-Parameters-v11d0 ::= SEQUENCE {
   supportedBandCombinationAdd-v11d0 [0] SupportedBandCombinationAdd-v11d0
       OPTIONAL
}

Other-Parameters-v11d0 ::= SEQUENCE {
   inDeviceCoexInd-UL-CA-r11 [0] ENUMERATED { supported(0) } OPTIONAL
}

RF-Parameters-v12b0 ::= SEQUENCE {
   maxLayersMIMO-Indication-r12 [0] ENUMERATED { supported(0) } OPTIONAL
}

CE-Parameters-v1370 ::= SEQUENCE {
   tm9-CE-ModeA-r13 [0] ENUMERATED { supported(0) } OPTIONAL,
   tm9-CE-ModeB-r13 [1] ENUMERATED { supported(0) } OPTIONAL
}

UE-EUTRA-CapabilityAddXDD-Mode-v1370 ::= SEQUENCE {
   ce-Parameters-v1370 [0] CE-Parameters-v1370 OPTIONAL
}

BandParameters-v1380 ::= SEQUENCE {
   txAntennaSwitchDL-r13 [0] INTEGER (1..32) OPTIONAL,
   txAntennaSwitchUL-r13 [1] INTEGER (1..32) OPTIONAL
}

BandCombinationParameters-v1380 ::= SEQUENCE {
   bandParameterList-v1380 [0] SEQUENCE (SIZE (1..maxSimultaneousBands-r10)) OF BandParameters-v1380
       OPTIONAL
}

SupportedBandCombination-v1380 ::= SEQUENCE (SIZE (1..maxBandComb-r10)) OF 
   BandCombinationParameters-v1380

SupportedBandCombinationAdd-v1380 ::= SEQUENCE (SIZE (1..maxBandComb-r11)) OF 
   BandCombinationParameters-v1380

SupportedBandCombinationReduced-v1380 ::= SEQUENCE (SIZE (1..maxBandComb-r13)) OF 
   BandCombinationParameters-v1380

RF-Parameters-v1380 ::= SEQUENCE {
   supportedBandCombination-v1380 [0] SupportedBandCombination-v1380 OPTIONAL,
   supportedBandCombinationAdd-v1380 [1] SupportedBandCombinationAdd-v1380
       OPTIONAL,
   supportedBandCombinationReduced-v1380 [2] 
      SupportedBandCombinationReduced-v1380 OPTIONAL
}

CE-Parameters-v1380 ::= SEQUENCE {
   tm6-CE-ModeA-r13 [0] ENUMERATED { supported(0) } OPTIONAL
}

UE-EUTRA-CapabilityAddXDD-Mode-v1380 ::= SEQUENCE {
   ce-Parameters-v1380 [0] CE-Parameters-v1380
}

BandCombinationParameters-v1390 ::= SEQUENCE {
   ue-CA-PowerClass-N-r13 [0] ENUMERATED { class2(0) } OPTIONAL
}

SupportedBandCombination-v1390 ::= SEQUENCE (SIZE (1..maxBandComb-r10)) OF 
   BandCombinationParameters-v1390

SupportedBandCombinationAdd-v1390 ::= SEQUENCE (SIZE (1..maxBandComb-r11)) OF 
   BandCombinationParameters-v1390

SupportedBandCombinationReduced-v1390 ::= SEQUENCE (SIZE (1..maxBandComb-r13)) OF 
   BandCombinationParameters-v1390

RF-Parameters-v1390 ::= SEQUENCE {
   supportedBandCombination-v1390 [0] SupportedBandCombination-v1390 OPTIONAL,
   supportedBandCombinationAdd-v1390 [1] SupportedBandCombinationAdd-v1390
       OPTIONAL,
   supportedBandCombinationReduced-v1390 [2] 
      SupportedBandCombinationReduced-v1390 OPTIONAL
}

MIMO-WeightedLayersCapabilities-r13 ::= SEQUENCE {
   relWeightTwoLayers-r13 [0] ENUMERATED { v1(0), v1dot25(1), v1dot5(2), 
      v1dot75(3), v2(4), v2dot5(5), v3(6), v4(7) },
   relWeightFourLayers-r13 [1] ENUMERATED { v1(0), v1dot25(1), v1dot5(2), 
      v1dot75(3), v2(4), v2dot5(5), v3(6), v4(7) } OPTIONAL,
   relWeightEightLayers-r13 [2] ENUMERATED { v1(0), v1dot25(1), v1dot5(2), 
      v1dot75(3), v2(4), v2dot5(5), v3(6), v4(7) } OPTIONAL,
   totalWeightedLayers-r13 [3] INTEGER (2..128)
}

MIMO-UE-Parameters-v13e0 ::= SEQUENCE {
   mimo-WeightedLayersCapabilities-r13 [0] MIMO-WeightedLayersCapabilities-r13
       OPTIONAL
}

PhyLayerParameters-v13e0 ::= SEQUENCE {
   mimo-UE-Parameters-v13e0 [0] MIMO-UE-Parameters-v13e0
}

UE-EUTRA-Capability-v13e0b-IEs ::= SEQUENCE {
   phyLayerParameters-v13e0 [0] PhyLayerParameters-v13e0,
--Following field is only to be used for late REL-13 extensions
   nonCriticalExtension [1] SEQUENCE {

   } OPTIONAL
}

MBMS-Parameters-v1470 ::= SEQUENCE {
   mbms-MaxBW-r14 [0] EXPLICIT CHOICE {
      implicitValue [0] NULL,
      explicitValue [1] INTEGER (2..20)
   },
   mbms-ScalingFactor1dot25-r14 [1] ENUMERATED { n3(0), n6(1), n9(2), n12(3) }
       OPTIONAL,
   mbms-ScalingFactor7dot5-r14 [2] ENUMERATED { n1(0), n2(1), n3(2), n4(3) }
       OPTIONAL
}

MIMO-UE-ParametersPerTM-v1470 ::= SEQUENCE {
   csi-ReportingAdvancedMaxPorts-r14 [0] ENUMERATED { n8(0), n12(1), n16(2), 
      n20(3), n24(4), n28(5) } OPTIONAL
}

MIMO-UE-Parameters-v1470 ::= SEQUENCE {
   parametersTM9-v1470 [0] MIMO-UE-ParametersPerTM-v1470,
   parametersTM10-v1470 [1] MIMO-UE-ParametersPerTM-v1470
}

PhyLayerParameters-v1470 ::= SEQUENCE {
   mimo-UE-Parameters-v1470 [0] MIMO-UE-Parameters-v1470 OPTIONAL,
   srs-UpPTS-6sym-r14 [1] ENUMERATED { supported(0) } OPTIONAL
}

MIMO-CA-ParametersPerBoBCPerTM-v1470 ::= SEQUENCE {
   csi-ReportingAdvancedMaxPorts-r14 [0] ENUMERATED { n8(0), n12(1), n16(2), 
      n20(3), n24(4), n28(5) } OPTIONAL
}

MIMO-CA-ParametersPerBoBC-v1470 ::= SEQUENCE {
   parametersTM9-v1470 [0] MIMO-CA-ParametersPerBoBCPerTM-v1470,
   parametersTM10-v1470 [1] MIMO-CA-ParametersPerBoBCPerTM-v1470
}

BandParameters-v1470 ::= SEQUENCE {
   bandParametersDL-v1470 [0] MIMO-CA-ParametersPerBoBC-v1470 OPTIONAL
}

BandCombinationParameters-v1470 ::= SEQUENCE {
   bandParameterList-v1470 [0] SEQUENCE (SIZE (1..maxSimultaneousBands-r10)) OF BandParameters-v1470
       OPTIONAL,
   srs-MaxSimultaneousCCs-r14 [1] INTEGER (1..31) OPTIONAL
}

SupportedBandCombination-v1470 ::= SEQUENCE (SIZE (1..maxBandComb-r10)) OF 
   BandCombinationParameters-v1470

SupportedBandCombinationAdd-v1470 ::= SEQUENCE (SIZE (1..maxBandComb-r11)) OF 
   BandCombinationParameters-v1470

SupportedBandCombinationReduced-v1470 ::= SEQUENCE (SIZE (1..maxBandComb-r13)) OF 
   BandCombinationParameters-v1470

RF-Parameters-v1470 ::= SEQUENCE {
   supportedBandCombination-v1470 [0] SupportedBandCombination-v1470 OPTIONAL,
   supportedBandCombinationAdd-v1470 [1] SupportedBandCombinationAdd-v1470
       OPTIONAL,
   supportedBandCombinationReduced-v1470 [2] 
      SupportedBandCombinationReduced-v1470 OPTIONAL
}

PhyLayerParameters-v14a0 ::= SEQUENCE {
   ssp10-TDD-Only-r14 [0] ENUMERATED { supported(0) } OPTIONAL
}

SRS-CapabilityPerBandPair-v14b0 ::= SEQUENCE {
   srs-FlexibleTiming-r14 [0] ENUMERATED { supported(0) } OPTIONAL,
   srs-HARQ-ReferenceConfig-r14 [1] ENUMERATED { supported(0) } OPTIONAL
}

BandParameters-v14b0 ::= SEQUENCE {
   srs-CapabilityPerBandPairList-v14b0 [0] SEQUENCE (SIZE (1..maxSimultaneousBands-r10)) OF 
      SRS-CapabilityPerBandPair-v14b0 OPTIONAL
}

BandCombinationParameters-v14b0 ::= SEQUENCE {
   bandParameterList-v14b0 [0] SEQUENCE (SIZE (1..maxSimultaneousBands-r10)) OF BandParameters-v14b0
       OPTIONAL
}

SupportedBandCombination-v14b0 ::= SEQUENCE (SIZE (1..maxBandComb-r10)) OF 
   BandCombinationParameters-v14b0

SupportedBandCombinationAdd-v14b0 ::= SEQUENCE (SIZE (1..maxBandComb-r11)) OF 
   BandCombinationParameters-v14b0

SupportedBandCombinationReduced-v14b0 ::= SEQUENCE (SIZE (1..maxBandComb-r13)) OF 
   BandCombinationParameters-v14b0

RF-Parameters-v14b0 ::= SEQUENCE {
   supportedBandCombination-v14b0 [0] SupportedBandCombination-v14b0 OPTIONAL,
   supportedBandCombinationAdd-v14b0 [1] SupportedBandCombinationAdd-v14b0
       OPTIONAL,
   supportedBandCombinationReduced-v14b0 [2] 
      SupportedBandCombinationReduced-v14b0 OPTIONAL
}

UE-EUTRA-Capability-v14b0-IEs ::= SEQUENCE {
   rf-Parameters-v14b0 [0] RF-Parameters-v14b0 OPTIONAL,
   nonCriticalExtension [1] SEQUENCE {

   } OPTIONAL
}

UE-EUTRA-Capability-v14a0-IEs ::= SEQUENCE {
   phyLayerParameters-v14a0 [0] PhyLayerParameters-v14a0,
--Following field is only to be used for late REL-14 extensions
   nonCriticalExtension [1] UE-EUTRA-Capability-v14b0-IEs OPTIONAL
}

UE-EUTRA-Capability-v1470-IEs ::= SEQUENCE {
   mbms-Parameters-v1470 [0] MBMS-Parameters-v1470 OPTIONAL,
   phyLayerParameters-v1470 [1] PhyLayerParameters-v1470 OPTIONAL,
   rf-Parameters-v1470 [2] RF-Parameters-v1470 OPTIONAL,
   nonCriticalExtension [3] UE-EUTRA-Capability-v14a0-IEs OPTIONAL
}

UE-EUTRA-Capability-v13e0a-IEs ::= SEQUENCE {
   lateNonCriticalExtension [0] OCTET STRING (CONTAINING 
      UE-EUTRA-Capability-v13e0b-IEs) OPTIONAL,
   nonCriticalExtension [1] UE-EUTRA-Capability-v1470-IEs OPTIONAL
}

UE-EUTRA-Capability-v1390-IEs ::= SEQUENCE {
   rf-Parameters-v1390 [0] RF-Parameters-v1390 OPTIONAL,
   nonCriticalExtension [1] UE-EUTRA-Capability-v13e0a-IEs OPTIONAL
}

UE-EUTRA-Capability-v1380-IEs ::= SEQUENCE {
   rf-Parameters-v1380 [0] RF-Parameters-v1380 OPTIONAL,
   ce-Parameters-v1380 [1] CE-Parameters-v1380,
   fdd-Add-UE-EUTRA-Capabilities-v1380 [2] UE-EUTRA-CapabilityAddXDD-Mode-v1380
      ,
   tdd-Add-UE-EUTRA-Capabilities-v1380 [3] UE-EUTRA-CapabilityAddXDD-Mode-v1380
      ,
   nonCriticalExtension [4] UE-EUTRA-Capability-v1390-IEs OPTIONAL
}

UE-EUTRA-Capability-v1370-IEs ::= SEQUENCE {
   ce-Parameters-v1370 [0] CE-Parameters-v1370 OPTIONAL,
   fdd-Add-UE-EUTRA-Capabilities-v1370 [1] UE-EUTRA-CapabilityAddXDD-Mode-v1370
       OPTIONAL,
   tdd-Add-UE-EUTRA-Capabilities-v1370 [2] UE-EUTRA-CapabilityAddXDD-Mode-v1370
       OPTIONAL,
   nonCriticalExtension [3] UE-EUTRA-Capability-v1380-IEs OPTIONAL
}

UE-EUTRA-Capability-v12x0-IEs ::= SEQUENCE {
--Following field is only to be used for late REL-12 extensions
   lateNonCriticalExtension [0] OCTET STRING OPTIONAL,
   nonCriticalExtension [1] UE-EUTRA-Capability-v1370-IEs OPTIONAL
}

UE-EUTRA-Capability-v12b0-IEs ::= SEQUENCE {
   rf-Parameters-v12b0 [0] RF-Parameters-v12b0 OPTIONAL,
   nonCriticalExtension [1] UE-EUTRA-Capability-v12x0-IEs OPTIONAL
}

UE-EUTRA-Capability-v11x0-IEs ::= SEQUENCE {
--Following field is only to be used for late REL-11 extensions
   lateNonCriticalExtension [0] OCTET STRING OPTIONAL,
   nonCriticalExtension [1] UE-EUTRA-Capability-v12b0-IEs OPTIONAL
}

UE-EUTRA-Capability-v11d0-IEs ::= SEQUENCE {
   rf-Parameters-v11d0 [0] RF-Parameters-v11d0 OPTIONAL,
   otherParameters-v11d0 [1] Other-Parameters-v11d0 OPTIONAL,
   nonCriticalExtension [2] UE-EUTRA-Capability-v11x0-IEs OPTIONAL
}

UE-EUTRA-Capability-v10i0-IEs ::= SEQUENCE {
   rf-Parameters-v10i0 [0] RF-Parameters-v10i0 OPTIONAL,
--Following field is only to be used for late REL-10 extensions
   lateNonCriticalExtension [1] OCTET STRING (CONTAINING 
      UE-EUTRA-Capability-v10j0-IEs) OPTIONAL,
   nonCriticalExtension [2] UE-EUTRA-Capability-v11d0-IEs OPTIONAL
}

UE-EUTRA-Capability-v10f0-IEs ::= SEQUENCE {
   rf-Parameters-v10f0 [0] RF-Parameters-v10f0 OPTIONAL,
   nonCriticalExtension [1] UE-EUTRA-Capability-v10i0-IEs OPTIONAL
}

UE-EUTRA-Capability-v10c0-IEs ::= SEQUENCE {
   otdoa-PositioningCapabilities-r10 [0] OTDOA-PositioningCapabilities-r10
       OPTIONAL,
   nonCriticalExtension [1] UE-EUTRA-Capability-v10f0-IEs OPTIONAL
}

UE-EUTRA-Capability-v9h0-IEs ::= SEQUENCE {
   interRAT-ParametersUTRA-v9h0 [0] IRAT-ParametersUTRA-v9h0 OPTIONAL,
--Following field is only to be used for late REL-9 extensions
   lateNonCriticalExtension [1] OCTET STRING OPTIONAL,
   nonCriticalExtension [2] UE-EUTRA-Capability-v10c0-IEs OPTIONAL
}

UE-EUTRA-Capability-v9e0-IEs ::= SEQUENCE {
   rf-Parameters-v9e0 [0] RF-Parameters-v9e0 OPTIONAL,
   nonCriticalExtension [1] UE-EUTRA-Capability-v9h0-IEs OPTIONAL
}

UE-EUTRA-Capability-v9d0-IEs ::= SEQUENCE {
   phyLayerParameters-v9d0 [0] PhyLayerParameters-v9d0 OPTIONAL,
   nonCriticalExtension [1] UE-EUTRA-Capability-v9e0-IEs OPTIONAL
}

UE-EUTRA-Capability-v9c0-IEs ::= SEQUENCE {
   interRAT-ParametersUTRA-v9c0 [0] IRAT-ParametersUTRA-v9c0 OPTIONAL,
   nonCriticalExtension [1] UE-EUTRA-Capability-v9d0-IEs OPTIONAL
}

-- Late non critical extensions
UE-EUTRA-Capability-v9a0-IEs ::= SEQUENCE {
   featureGroupIndRel9Add-r9 [0] BIT STRING  (SIZE (32)) OPTIONAL,
   fdd-Add-UE-EUTRA-Capabilities-r9 [1] UE-EUTRA-CapabilityAddXDD-Mode-r9
       OPTIONAL,
   tdd-Add-UE-EUTRA-Capabilities-r9 [2] UE-EUTRA-CapabilityAddXDD-Mode-r9
       OPTIONAL,
   nonCriticalExtension [3] UE-EUTRA-Capability-v9c0-IEs OPTIONAL
}

NonContiguousUL-RA-WithinCC-r10 ::= SEQUENCE {
   nonContiguousUL-RA-WithinCC-Info-r10 [0] ENUMERATED { supported(0) }
       OPTIONAL
}

NonContiguousUL-RA-WithinCC-List-r10 ::= SEQUENCE (SIZE (1..maxBands)) OF 
   NonContiguousUL-RA-WithinCC-r10

PhyLayerParameters-v1020 ::= SEQUENCE {
   twoAntennaPortsForPUCCH-r10 [0] ENUMERATED { supported(0) } OPTIONAL,
   tm9-With-8Tx-FDD-r10 [1] ENUMERATED { supported(0) } OPTIONAL,
   pmi-Disabling-r10 [2] ENUMERATED { supported(0) } OPTIONAL,
   crossCarrierScheduling-r10 [3] ENUMERATED { supported(0) } OPTIONAL,
   simultaneousPUCCH-PUSCH-r10 [4] ENUMERATED { supported(0) } OPTIONAL,
   multiClusterPUSCH-WithinCC-r10 [5] ENUMERATED { supported(0) } OPTIONAL,
   nonContiguousUL-RA-WithinCC-List-r10 [6] 
      NonContiguousUL-RA-WithinCC-List-r10 OPTIONAL
}

BandParametersUL-r10 ::= SEQUENCE (SIZE (1..maxBandwidthClass-r10)) OF CA-MIMO-ParametersUL-r10

CA-MIMO-ParametersDL-r10 ::= SEQUENCE {
   ca-BandwidthClassDL-r10 [0] CA-BandwidthClass-r10,
   supportedMIMO-CapabilityDL-r10 [1] MIMO-CapabilityDL-r10 OPTIONAL
}

BandParametersDL-r10 ::= SEQUENCE (SIZE (1..maxBandwidthClass-r10)) OF CA-MIMO-ParametersDL-r10

BandParameters-r10 ::= SEQUENCE {
   bandEUTRA-r10 [0] FreqBandIndicator,
   bandParametersUL-r10 [1] BandParametersUL-r10 OPTIONAL,
   bandParametersDL-r10 [2] BandParametersDL-r10 OPTIONAL
}

BandCombinationParameters-r10 ::= SEQUENCE (SIZE (1..maxSimultaneousBands-r10)) OF BandParameters-r10

SupportedBandCombination-r10 ::= SEQUENCE (SIZE (1..maxBandComb-r10)) OF 
   BandCombinationParameters-r10

RF-Parameters-v1020 ::= SEQUENCE {
   supportedBandCombination-r10 [0] SupportedBandCombination-r10
}

BandCombinationListEUTRA-r10 ::= SEQUENCE (SIZE (1..maxBandComb-r10)) OF BandInfoEUTRA

MeasParameters-v1020 ::= SEQUENCE {
   bandCombinationListEUTRA-r10 [0] BandCombinationListEUTRA-r10
}

IRAT-ParametersCDMA2000-1XRTT-v1020 ::= SEQUENCE {
   e-CSFB-dual-1XRTT-r10 [0] ENUMERATED { supported(0) }
}

UE-BasedNetwPerfMeasParameters-r10 ::= SEQUENCE {
   loggedMeasurementsIdle-r10 [0] ENUMERATED { supported(0) } OPTIONAL,
   standaloneGNSS-Location-r10 [1] ENUMERATED { supported(0) } OPTIONAL
}

IRAT-ParametersUTRA-TDD-v1020 ::= SEQUENCE {
   e-RedirectionUTRA-TDD-r10 [0] ENUMERATED { supported(0) }
}

UE-EUTRA-CapabilityAddXDD-Mode-v1060 ::= SEQUENCE {
   phyLayerParameters-v1060 [0] PhyLayerParameters-v1020 OPTIONAL,
   featureGroupIndRel10-v1060 [1] BIT STRING  (SIZE (32)) OPTIONAL,
   interRAT-ParametersCDMA2000-v1060 [2] IRAT-ParametersCDMA2000-1XRTT-v1020
       OPTIONAL,
   interRAT-ParametersUTRA-TDD-v1060 [3] IRAT-ParametersUTRA-TDD-v1020 OPTIONAL
      ,
   ...,
   [[
      otdoa-PositioningCapabilities-r10 [4] OTDOA-PositioningCapabilities-r10
          OPTIONAL
   ]]
}

BandCombinationParametersExt-r10 ::= SEQUENCE {
   supportedBandwidthCombinationSet-r10 [0] 
      SupportedBandwidthCombinationSet-r10 OPTIONAL
}

SupportedBandCombinationExt-r10 ::= SEQUENCE (SIZE (1..maxBandComb-r10)) OF 
   BandCombinationParametersExt-r10

RF-Parameters-v1060 ::= SEQUENCE {
   supportedBandCombinationExt-r10 [0] SupportedBandCombinationExt-r10
}

BandParameters-v1090 ::= SEQUENCE {
   bandEUTRA-v1090 [0] FreqBandIndicator-v9e0 OPTIONAL,
   ...
}

BandCombinationParameters-v1090 ::= SEQUENCE (SIZE (1..maxSimultaneousBands-r10)) OF 
   BandParameters-v1090

SupportedBandCombination-v1090 ::= SEQUENCE (SIZE (1..maxBandComb-r10)) OF 
   BandCombinationParameters-v1090

RF-Parameters-v1090 ::= SEQUENCE {
   supportedBandCombination-v1090 [0] SupportedBandCombination-v1090 OPTIONAL
}

PDCP-Parameters-v1130 ::= SEQUENCE {
   pdcp-SN-Extension-r11 [0] ENUMERATED { supported(0) } OPTIONAL,
   supportRohcContextContinue-r11 [1] ENUMERATED { supported(0) } OPTIONAL
}

PhyLayerParameters-v1130 ::= SEQUENCE {
   crs-InterfHandl-r11 [0] ENUMERATED { supported(0) } OPTIONAL,
   ePDCCH-r11 [1] ENUMERATED { supported(0) } OPTIONAL,
   multiACK-CSI-Reporting-r11 [2] ENUMERATED { supported(0) } OPTIONAL,
   ss-CCH-InterfHandl-r11 [3] ENUMERATED { supported(0) } OPTIONAL,
   tdd-SpecialSubframe-r11 [4] ENUMERATED { supported(0) } OPTIONAL,
   txDiv-PUCCH1b-ChSelect-r11 [5] ENUMERATED { supported(0) } OPTIONAL,
   ul-CoMP-r11 [6] ENUMERATED { supported(0) } OPTIONAL
}

BandParameters-v1130 ::= SEQUENCE {
   supportedCSI-Proc-r11 [0] ENUMERATED { n1(0), n3(1), n4(2) }
}

BandCombinationParameters-v1130 ::= SEQUENCE {
   multipleTimingAdvance-r11 [0] ENUMERATED { supported(0) } OPTIONAL,
   simultaneousRx-Tx-r11 [1] ENUMERATED { supported(0) } OPTIONAL,
   bandParameterList-r11 [2] SEQUENCE (SIZE (1..maxSimultaneousBands-r10)) OF BandParameters-v1130
       OPTIONAL,
   ...
}

SupportedBandCombination-v1130 ::= SEQUENCE (SIZE (1..maxBandComb-r10)) OF 
   BandCombinationParameters-v1130

RF-Parameters-v1130 ::= SEQUENCE {
   supportedBandCombination-v1130 [0] SupportedBandCombination-v1130 OPTIONAL
}

MeasParameters-v1130 ::= SEQUENCE {
   rsrqMeasWideband-r11 [0] ENUMERATED { supported(0) } OPTIONAL
}

IRAT-ParametersCDMA2000-v1130 ::= SEQUENCE {
   cdma2000-NW-Sharing-r11 [0] ENUMERATED { supported(0) } OPTIONAL
}

Other-Parameters-r11 ::= SEQUENCE {
   inDeviceCoexInd-r11 [0] ENUMERATED { supported(0) } OPTIONAL,
   powerPrefInd-r11 [1] ENUMERATED { supported(0) } OPTIONAL,
   ue-Rx-TxTimeDiffMeasurements-r11 [2] ENUMERATED { supported(0) } OPTIONAL
}

UE-EUTRA-CapabilityAddXDD-Mode-v1130 ::= SEQUENCE {
   phyLayerParameters-v1130 [0] PhyLayerParameters-v1130 OPTIONAL,
   measParameters-v1130 [1] MeasParameters-v1130 OPTIONAL,
   otherParameters-r11 [2] Other-Parameters-r11 OPTIONAL,
   ...
}

PhyLayerParameters-v1170 ::= SEQUENCE {
   interBandTDD-CA-WithDifferentConfig-r11 [0] BIT STRING  (SIZE (2)) OPTIONAL
}

BandParameters-r11 ::= SEQUENCE {
   bandEUTRA-r11 [0] FreqBandIndicator-r11,
   bandParametersUL-r11 [1] BandParametersUL-r10 OPTIONAL,
   bandParametersDL-r11 [2] BandParametersDL-r10 OPTIONAL,
   supportedCSI-Proc-r11 [3] ENUMERATED { n1(0), n3(1), n4(2) } OPTIONAL
}

BandCombinationParameters-r11 ::= SEQUENCE {
   bandParameterList-r11 [0] SEQUENCE (SIZE (1..maxSimultaneousBands-r10)) OF BandParameters-r11,
   supportedBandwidthCombinationSet-r11 [1] 
      SupportedBandwidthCombinationSet-r10 OPTIONAL,
   multipleTimingAdvance-r11 [2] ENUMERATED { supported(0) } OPTIONAL,
   simultaneousRx-Tx-r11 [3] ENUMERATED { supported(0) } OPTIONAL,
   bandInfoEUTRA-r11 [4] BandInfoEUTRA,
   ...
}

SupportedBandCombinationAdd-r11 ::= SEQUENCE (SIZE (1..maxBandComb-r11)) OF 
   BandCombinationParameters-r11

RF-Parameters-v1180 ::= SEQUENCE {
   freqBandRetrieval-r11 [0] ENUMERATED { supported(0) } OPTIONAL,
   requestedBands-r11 [1] SEQUENCE (SIZE (1..maxBands)) OF FreqBandIndicator-r11
       OPTIONAL,
   supportedBandCombinationAdd-r11 [2] SupportedBandCombinationAdd-r11 OPTIONAL
}

MBMS-Parameters-r11 ::= SEQUENCE {
   mbms-SCell-r11 [0] ENUMERATED { supported(0) } OPTIONAL,
   mbms-NonServingCell-r11 [1] ENUMERATED { supported(0) } OPTIONAL
}

UE-EUTRA-CapabilityAddXDD-Mode-v1180 ::= SEQUENCE {
   mbms-Parameters-r11 [0] MBMS-Parameters-r11
}

MeasParameters-v11a0 ::= SEQUENCE {
   benefitsFromInterruption-r11 [0] ENUMERATED { true(0) } OPTIONAL
}

NAICS-Capability-Entry-r12 ::= SEQUENCE {
   numberOfNAICS-CapableCC-r12 [0] INTEGER (1..5),
   numberOfAggregatedPRB-r12 [1] ENUMERATED { n50(0), n75(1), n100(2), n125(3)
      , n150(4), n175(5), n200(6), n225(7), n250(8), n275(9), n300(10), 
      n350(11), n400(12), n450(13), n500(14), spare(15) },
   ...
}

NAICS-Capability-List-r12 ::= SEQUENCE (SIZE (1..maxNAICS-Entries-r12)) OF 
   NAICS-Capability-Entry-r12

PhyLayerParameters-v1250 ::= SEQUENCE {
   e-HARQ-Pattern-FDD-r12 [0] ENUMERATED { supported(0) } OPTIONAL,
   enhanced-4TxCodebook-r12 [1] ENUMERATED { supported(0) } OPTIONAL,
   tdd-FDD-CA-PCellDuplex-r12 [2] BIT STRING  (SIZE (2)) OPTIONAL,
   phy-TDD-ReConfig-TDD-PCell-r12 [3] ENUMERATED { supported(0) } OPTIONAL,
   phy-TDD-ReConfig-FDD-PCell-r12 [4] ENUMERATED { supported(0) } OPTIONAL,
   pusch-FeedbackMode-r12 [5] ENUMERATED { supported(0) } OPTIONAL,
   pusch-SRS-PowerControl-SubframeSet-r12 [6] ENUMERATED { supported(0) }
       OPTIONAL,
   csi-SubframeSet-r12 [7] ENUMERATED { supported(0) } OPTIONAL,
   noResourceRestrictionForTTIBundling-r12 [8] ENUMERATED { supported(0) }
       OPTIONAL,
   discoverySignalsInDeactSCell-r12 [9] ENUMERATED { supported(0) } OPTIONAL,
   naics-Capability-List-r12 [10] NAICS-Capability-List-r12 OPTIONAL
}

SupportedBandEUTRA-v1250 ::= SEQUENCE {
   dl-256QAM-r12 [0] ENUMERATED { supported(0) } OPTIONAL,
   ul-64QAM-r12 [1] ENUMERATED { supported(0) } OPTIONAL
}

SupportedBandListEUTRA-v1250 ::= SEQUENCE (SIZE (1..maxBands)) OF 
   SupportedBandEUTRA-v1250

BandCombinationParameters-v1250 ::= SEQUENCE {
   dc-Support-r12 [0] SEQUENCE {
      asynchronous-r12 [0] ENUMERATED { supported(0) } OPTIONAL,
      supportedCellGrouping-r12 [1] EXPLICIT CHOICE {
         threeEntries-r12 [0] BIT STRING  (SIZE (3)),
         fourEntries-r12 [1] BIT STRING  (SIZE (7)),
         fiveEntries-r12 [2] BIT STRING  (SIZE (15))
      } OPTIONAL
   } OPTIONAL,
   supportedNAICS-2CRS-AP-r12 [1] BIT STRING  (SIZE (1..maxNAICS-Entries-r12)) OPTIONAL,
   commSupportedBandsPerBC-r12 [2] BIT STRING  (SIZE (1..maxBands)) OPTIONAL,
   ...
}

SupportedBandCombination-v1250 ::= SEQUENCE (SIZE (1..maxBandComb-r10)) OF 
   BandCombinationParameters-v1250

SupportedBandCombinationAdd-v1250 ::= SEQUENCE (SIZE (1..maxBandComb-r11)) OF 
   BandCombinationParameters-v1250

RF-Parameters-v1250 ::= SEQUENCE {
   supportedBandListEUTRA-v1250 [0] SupportedBandListEUTRA-v1250 OPTIONAL,
   supportedBandCombination-v1250 [1] SupportedBandCombination-v1250 OPTIONAL,
   supportedBandCombinationAdd-v1250 [2] SupportedBandCombinationAdd-v1250
       OPTIONAL,
   freqBandPriorityAdjustment-r12 [3] ENUMERATED { supported(0) } OPTIONAL
}

RLC-Parameters-r12 ::= SEQUENCE {
   extended-RLC-LI-Field-r12 [0] ENUMERATED { supported(0) }
}

UE-BasedNetwPerfMeasParameters-v1250 ::= SEQUENCE {
   loggedMBSFNMeasurements-r12 [0] ENUMERATED { supported(0) }
}

WLAN-IW-Parameters-r12 ::= SEQUENCE {
   wlan-IW-RAN-Rules-r12 [0] ENUMERATED { supported(0) } OPTIONAL,
   wlan-IW-ANDSF-Policies-r12 [1] ENUMERATED { supported(0) } OPTIONAL
}

MeasParameters-v1250 ::= SEQUENCE {
   timerT312-r12 [0] ENUMERATED { supported(0) } OPTIONAL,
   alternativeTimeToTrigger-r12 [1] ENUMERATED { supported(0) } OPTIONAL,
   incMonEUTRA-r12 [2] ENUMERATED { supported(0) } OPTIONAL,
   incMonUTRA-r12 [3] ENUMERATED { supported(0) } OPTIONAL,
   extendedMaxMeasId-r12 [4] ENUMERATED { supported(0) } OPTIONAL,
   extendedRSRQ-LowerRange-r12 [5] ENUMERATED { supported(0) } OPTIONAL,
   rsrq-OnAllSymbols-r12 [6] ENUMERATED { supported(0) } OPTIONAL,
   crs-DiscoverySignalsMeas-r12 [7] ENUMERATED { supported(0) } OPTIONAL,
   csi-RS-DiscoverySignalsMeas-r12 [8] ENUMERATED { supported(0) } OPTIONAL
}

DC-Parameters-r12 ::= SEQUENCE {
   drb-TypeSplit-r12 [0] ENUMERATED { supported(0) } OPTIONAL,
   drb-TypeSCG-r12 [1] ENUMERATED { supported(0) } OPTIONAL
}

MBMS-Parameters-v1250 ::= SEQUENCE {
   mbms-AsyncDC-r12 [0] ENUMERATED { supported(0) } OPTIONAL
}

MAC-Parameters-r12 ::= SEQUENCE {
   logicalChannelSR-ProhibitTimer-r12 [0] ENUMERATED { supported(0) } OPTIONAL,
   longDRX-Command-r12 [1] ENUMERATED { supported(0) } OPTIONAL
}

UE-EUTRA-CapabilityAddXDD-Mode-v1250 ::= SEQUENCE {
   phyLayerParameters-v1250 [0] PhyLayerParameters-v1250 OPTIONAL,
   measParameters-v1250 [1] MeasParameters-v1250 OPTIONAL
}

FreqBandIndicatorListEUTRA-r12 ::= SEQUENCE (SIZE (1..maxBands)) OF 
   FreqBandIndicator-r11

SupportedBandInfo-r12 ::= SEQUENCE {
   support-r12 [0] ENUMERATED { supported(0) } OPTIONAL
}

SupportedBandInfoList-r12 ::= SEQUENCE (SIZE (1..maxBands)) OF SupportedBandInfo-r12

SL-Parameters-r12 ::= SEQUENCE {
   commSimultaneousTx-r12 [0] ENUMERATED { supported(0) } OPTIONAL,
   commSupportedBands-r12 [1] FreqBandIndicatorListEUTRA-r12 OPTIONAL,
   discSupportedBands-r12 [2] SupportedBandInfoList-r12 OPTIONAL,
   discScheduledResourceAlloc-r12 [3] ENUMERATED { supported(0) } OPTIONAL,
   disc-UE-SelectedResourceAlloc-r12 [4] ENUMERATED { supported(0) } OPTIONAL,
   disc-SLSS-r12 [5] ENUMERATED { supported(0) } OPTIONAL,
   discSupportedProc-r12 [6] ENUMERATED { n50(0), n400(1) } OPTIONAL
}

CA-MIMO-ParametersDL-v1270 ::= SEQUENCE {
   intraBandContiguousCC-InfoList-r12 [0] SEQUENCE (SIZE (1..maxServCell-r10)) OF 
      IntraBandContiguousCC-Info-r12
}

BandParameters-v1270 ::= SEQUENCE {
   bandParametersDL-v1270 [0] SEQUENCE (SIZE (1..maxBandwidthClass-r10)) OF 
      CA-MIMO-ParametersDL-v1270
}

BandCombinationParameters-v1270 ::= SEQUENCE {
   bandParameterList-v1270 [0] SEQUENCE (SIZE (1..maxSimultaneousBands-r10)) OF BandParameters-v1270
       OPTIONAL
}

SupportedBandCombination-v1270 ::= SEQUENCE (SIZE (1..maxBandComb-r10)) OF 
   BandCombinationParameters-v1270

SupportedBandCombinationAdd-v1270 ::= SEQUENCE (SIZE (1..maxBandComb-r11)) OF 
   BandCombinationParameters-v1270

RF-Parameters-v1270 ::= SEQUENCE {
   supportedBandCombination-v1270 [0] SupportedBandCombination-v1270 OPTIONAL,
   supportedBandCombinationAdd-v1270 [1] SupportedBandCombinationAdd-v1270
       OPTIONAL
}

PhyLayerParameters-v1280 ::= SEQUENCE {
   alternativeTBS-Indices-r12 [0] ENUMERATED { supported(0) } OPTIONAL
}

PDCP-Parameters-v1310 ::= SEQUENCE {
   pdcp-SN-Extension-18bits-r13 [0] ENUMERATED { supported(0) } OPTIONAL
}

RLC-Parameters-v1310 ::= SEQUENCE {
   extendedRLC-SN-SO-Field-r13 [0] ENUMERATED { supported(0) } OPTIONAL
}

MAC-Parameters-v1310 ::= SEQUENCE {
   extendedMAC-LengthField-r13 [0] ENUMERATED { supported(0) } OPTIONAL,
   extendedLongDRX-r13 [1] ENUMERATED { supported(0) } OPTIONAL
}

PhyLayerParameters-v1310 ::= SEQUENCE {
   aperiodicCSI-Reporting-r13 [0] BIT STRING  (SIZE (2)) OPTIONAL,
   codebook-HARQ-ACK-r13 [1] BIT STRING  (SIZE (2)) OPTIONAL,
   crossCarrierScheduling-B5C-r13 [2] ENUMERATED { supported(0) } OPTIONAL,
   fdd-HARQ-TimingTDD-r13 [3] ENUMERATED { supported(0) } OPTIONAL,
   maxNumberUpdatedCSI-Proc-r13 [4] INTEGER (5..32) OPTIONAL,
   pucch-Format4-r13 [5] ENUMERATED { supported(0) } OPTIONAL,
   pucch-Format5-r13 [6] ENUMERATED { supported(0) } OPTIONAL,
   pucch-SCell-r13 [7] ENUMERATED { supported(0) } OPTIONAL,
   spatialBundling-HARQ-ACK-r13 [8] ENUMERATED { supported(0) } OPTIONAL,
   supportedBlindDecoding-r13 [9] SEQUENCE {
      maxNumberDecoding-r13 [0] INTEGER (1..32) OPTIONAL,
      pdcch-CandidateReductions-r13 [1] ENUMERATED { supported(0) } OPTIONAL,
      skipMonitoringDCI-Format0-1A-r13 [2] ENUMERATED { supported(0) } OPTIONAL
   } OPTIONAL,
   uci-PUSCH-Ext-r13 [10] ENUMERATED { supported(0) } OPTIONAL,
   crs-InterfMitigationTM10-r13 [11] ENUMERATED { supported(0) } OPTIONAL,
   pdsch-CollisionHandling-r13 [12] ENUMERATED { supported(0) } OPTIONAL
}

SupportedBandEUTRA-v1310 ::= SEQUENCE {
   ue-PowerClass-5-r13 [0] ENUMERATED { supported(0) } OPTIONAL
}

SupportedBandListEUTRA-v1310 ::= SEQUENCE (SIZE (1..maxBands)) OF 
   SupportedBandEUTRA-v1310

BandParameters-r13 ::= SEQUENCE {
   bandEUTRA-r13 [0] FreqBandIndicator-r11,
   bandParametersUL-r13 [1] BandParametersUL-r13 OPTIONAL,
   bandParametersDL-r13 [2] BandParametersDL-r13 OPTIONAL,
   supportedCSI-Proc-r13 [3] ENUMERATED { n1(0), n3(1), n4(2) } OPTIONAL
}

BandCombinationParameters-r13 ::= SEQUENCE {
   differentFallbackSupported-r13 [0] ENUMERATED { true(0) } OPTIONAL,
   bandParameterList-r13 [1] SEQUENCE (SIZE (1..maxSimultaneousBands-r10)) OF BandParameters-r13,
   supportedBandwidthCombinationSet-r13 [2] 
      SupportedBandwidthCombinationSet-r10 OPTIONAL,
   multipleTimingAdvance-r13 [3] ENUMERATED { supported(0) } OPTIONAL,
   simultaneousRx-Tx-r13 [4] ENUMERATED { supported(0) } OPTIONAL,
   bandInfoEUTRA-r13 [5] BandInfoEUTRA,
   dc-Support-r13 [6] SEQUENCE {
      asynchronous-r13 [0] ENUMERATED { supported(0) } OPTIONAL,
      supportedCellGrouping-r13 [1] EXPLICIT CHOICE {
         threeEntries-r13 [0] BIT STRING  (SIZE (3)),
         fourEntries-r13 [1] BIT STRING  (SIZE (7)),
         fiveEntries-r13 [2] BIT STRING  (SIZE (15))
      } OPTIONAL
   } OPTIONAL,
   supportedNAICS-2CRS-AP-r13 [7] BIT STRING  (SIZE (1..maxNAICS-Entries-r12)) OPTIONAL,
   commSupportedBandsPerBC-r13 [8] BIT STRING  (SIZE (1..maxBands)) OPTIONAL
}

SupportedBandCombinationReduced-r13 ::= SEQUENCE (SIZE (1..maxBandComb-r13)) OF 
   BandCombinationParameters-r13

RF-Parameters-v1310 ::= SEQUENCE {
   eNB-RequestedParameters-r13 [0] SEQUENCE {
      reducedIntNonContCombRequested-r13 [0] ENUMERATED { true(0) } OPTIONAL,
      requestedCCsDL-r13 [1] INTEGER (2..32) OPTIONAL,
      requestedCCsUL-r13 [2] INTEGER (2..32) OPTIONAL,
      skipFallbackCombRequested-r13 [3] ENUMERATED { true(0) } OPTIONAL
   } OPTIONAL,
   maximumCCsRetrieval-r13 [1] ENUMERATED { supported(0) } OPTIONAL,
   skipFallbackCombinations-r13 [2] ENUMERATED { supported(0) } OPTIONAL,
   reducedIntNonContComb-r13 [3] ENUMERATED { supported(0) } OPTIONAL,
   supportedBandListEUTRA-v1310 [4] SupportedBandListEUTRA-v1310 OPTIONAL,
   supportedBandCombinationReduced-r13 [5] SupportedBandCombinationReduced-r13
       OPTIONAL
}

MeasParameters-v1310 ::= SEQUENCE {
   rs-SINR-Meas-r13 [0] ENUMERATED { supported(0) } OPTIONAL,
   whiteCellList-r13 [1] ENUMERATED { supported(0) } OPTIONAL,
   extendedMaxObjectId-r13 [2] ENUMERATED { supported(0) } OPTIONAL,
   ul-PDCP-Delay-r13 [3] ENUMERATED { supported(0) } OPTIONAL,
   extendedFreqPriorities-r13 [4] ENUMERATED { supported(0) } OPTIONAL,
   multiBandInfoReport-r13 [5] ENUMERATED { supported(0) } OPTIONAL,
   rssi-AndChannelOccupancyReporting-r13 [6] ENUMERATED { supported(0) }
       OPTIONAL
}

DC-Parameters-v1310 ::= SEQUENCE {
   pdcp-TransferSplitUL-r13 [0] ENUMERATED { supported(0) } OPTIONAL,
   ue-SSTD-Meas-r13 [1] ENUMERATED { supported(0) } OPTIONAL
}

SL-Parameters-v1310 ::= SEQUENCE {
   discSysInfoReporting-r13 [0] ENUMERATED { supported(0) } OPTIONAL,
   commMultipleTx-r13 [1] ENUMERATED { supported(0) } OPTIONAL,
   discInterFreqTx-r13 [2] ENUMERATED { supported(0) } OPTIONAL,
   discPeriodicSLSS-r13 [3] ENUMERATED { supported(0) } OPTIONAL
}

SCPTM-Parameters-r13 ::= SEQUENCE {
   scptm-ParallelReception-r13 [0] ENUMERATED { supported(0) } OPTIONAL,
   scptm-SCell-r13 [1] ENUMERATED { supported(0) } OPTIONAL,
   scptm-NonServingCell-r13 [2] ENUMERATED { supported(0) } OPTIONAL,
   scptm-AsyncDC-r13 [3] ENUMERATED { supported(0) } OPTIONAL
}

CE-Parameters-r13 ::= SEQUENCE {
   ce-ModeA-r13 [0] ENUMERATED { supported(0) } OPTIONAL,
   ce-ModeB-r13 [1] ENUMERATED { supported(0) } OPTIONAL
}

IRAT-ParametersWLAN-r13 ::= SEQUENCE {
   supportedBandListWLAN-r13 [0] SEQUENCE (SIZE (1..maxWLAN-Bands-r13)) OF WLAN-BandIndicator-r13
       OPTIONAL
}

LAA-Parameters-r13 ::= SEQUENCE {
   crossCarrierSchedulingLAA-DL-r13 [0] ENUMERATED { supported(0) } OPTIONAL,
   csi-RS-DRS-RRM-MeasurementsLAA-r13 [1] ENUMERATED { supported(0) } OPTIONAL,
   downlinkLAA-r13 [2] ENUMERATED { supported(0) } OPTIONAL,
   endingDwPTS-r13 [3] ENUMERATED { supported(0) } OPTIONAL,
   secondSlotStartingPosition-r13 [4] ENUMERATED { supported(0) } OPTIONAL,
   tm9-LAA-r13 [5] ENUMERATED { supported(0) } OPTIONAL,
   tm10-LAA-r13 [6] ENUMERATED { supported(0) } OPTIONAL
}

LWA-Parameters-r13 ::= SEQUENCE {
   lwa-r13 [0] ENUMERATED { supported(0) } OPTIONAL,
   lwa-SplitBearer-r13 [1] ENUMERATED { supported(0) } OPTIONAL,
   wlan-MAC-Address-r13 [2] OCTET STRING (SIZE (6)) OPTIONAL,
   lwa-BufferSize-r13 [3] ENUMERATED { supported(0) } OPTIONAL
}

WLAN-IW-Parameters-v1310 ::= SEQUENCE {
   rclwi-r13 [0] ENUMERATED { supported(0) } OPTIONAL
}

LWIP-Parameters-r13 ::= SEQUENCE {
   lwip-r13 [0] ENUMERATED { supported(0) } OPTIONAL
}

UE-EUTRA-CapabilityAddXDD-Mode-v1310 ::= SEQUENCE {
   phyLayerParameters-v1310 [0] PhyLayerParameters-v1310 OPTIONAL
}

CE-Parameters-v1320 ::= SEQUENCE {
   intraFreqA3-CE-ModeA-r13 [0] ENUMERATED { supported(0) } OPTIONAL,
   intraFreqA3-CE-ModeB-r13 [1] ENUMERATED { supported(0) } OPTIONAL,
   intraFreqHO-CE-ModeA-r13 [2] ENUMERATED { supported(0) } OPTIONAL,
   intraFreqHO-CE-ModeB-r13 [3] ENUMERATED { supported(0) } OPTIONAL
}

MIMO-NonPrecodedCapabilities-r13 ::= SEQUENCE {
   config1-r13 [0] ENUMERATED { supported(0) } OPTIONAL,
   config2-r13 [1] ENUMERATED { supported(0) } OPTIONAL,
   config3-r13 [2] ENUMERATED { supported(0) } OPTIONAL,
   config4-r13 [3] ENUMERATED { supported(0) } OPTIONAL
}

MIMO-BeamformedCapabilities-r13 ::= SEQUENCE {
   k-Max-r13 [0] INTEGER (1..8),
   n-MaxList-r13 [1] BIT STRING  (SIZE (1..7)) OPTIONAL
}

MIMO-BeamformedCapabilityList-r13 ::= SEQUENCE (SIZE (1..maxCSI-Proc-r11)) OF 
   MIMO-BeamformedCapabilities-r13

MIMO-UE-BeamformedCapabilities-r13 ::= SEQUENCE {
   altCodebook-r13 [0] ENUMERATED { supported(0) } OPTIONAL,
   mimo-BeamformedCapabilities-r13 [1] MIMO-BeamformedCapabilityList-r13
}

MIMO-UE-ParametersPerTM-r13 ::= SEQUENCE {
   nonPrecoded-r13 [0] MIMO-NonPrecodedCapabilities-r13 OPTIONAL,
   beamformed-r13 [1] MIMO-UE-BeamformedCapabilities-r13 OPTIONAL,
   channelMeasRestriction-r13 [2] ENUMERATED { supported(0) } OPTIONAL,
   dmrs-Enhancements-r13 [3] ENUMERATED { supported(0) } OPTIONAL,
   csi-RS-EnhancementsTDD-r13 [4] ENUMERATED { supported(0) } OPTIONAL
}

MIMO-UE-Parameters-r13 ::= SEQUENCE {
   parametersTM9-r13 [0] MIMO-UE-ParametersPerTM-r13 OPTIONAL,
   parametersTM10-r13 [1] MIMO-UE-ParametersPerTM-r13 OPTIONAL,
   srs-EnhancementsTDD-r13 [2] ENUMERATED { supported(0) } OPTIONAL,
   srs-Enhancements-r13 [3] ENUMERATED { supported(0) } OPTIONAL,
   interferenceMeasRestriction-r13 [4] ENUMERATED { supported(0) } OPTIONAL
}

PhyLayerParameters-v1320 ::= SEQUENCE {
   mimo-UE-Parameters-r13 [0] MIMO-UE-Parameters-r13 OPTIONAL
}

SupportedBandEUTRA-v1320 ::= SEQUENCE {
   intraFreq-CE-NeedForGaps-r13 [0] ENUMERATED { supported(0) } OPTIONAL,
   ue-PowerClass-N-r13 [1] ENUMERATED { class1(0), class2(1), class4(2) }
       OPTIONAL
}

SupportedBandListEUTRA-v1320 ::= SEQUENCE (SIZE (1..maxBands)) OF 
   SupportedBandEUTRA-v1320

MIMO-CA-ParametersPerBoBCPerTM-r13 ::= SEQUENCE {
   nonPrecoded-r13 [0] MIMO-NonPrecodedCapabilities-r13 OPTIONAL,
   beamformed-r13 [1] MIMO-BeamformedCapabilityList-r13 OPTIONAL,
   dmrs-Enhancements-r13 [2] ENUMERATED { different(0) } OPTIONAL
}

MIMO-CA-ParametersPerBoBC-r13 ::= SEQUENCE {
   parametersTM9-r13 [0] MIMO-CA-ParametersPerBoBCPerTM-r13 OPTIONAL,
   parametersTM10-r13 [1] MIMO-CA-ParametersPerBoBCPerTM-r13 OPTIONAL
}

BandParameters-v1320 ::= SEQUENCE {
   bandParametersDL-v1320 [0] MIMO-CA-ParametersPerBoBC-r13
}

BandCombinationParameters-v1320 ::= SEQUENCE {
   bandParameterList-v1320 [0] SEQUENCE (SIZE (1..maxSimultaneousBands-r10)) OF BandParameters-v1320
       OPTIONAL,
   additionalRx-Tx-PerformanceReq-r13 [1] ENUMERATED { supported(0) } OPTIONAL
}

SupportedBandCombination-v1320 ::= SEQUENCE (SIZE (1..maxBandComb-r10)) OF 
   BandCombinationParameters-v1320

SupportedBandCombinationAdd-v1320 ::= SEQUENCE (SIZE (1..maxBandComb-r11)) OF 
   BandCombinationParameters-v1320

SupportedBandCombinationReduced-v1320 ::= SEQUENCE (SIZE (1..maxBandComb-r13)) OF 
   BandCombinationParameters-v1320

RF-Parameters-v1320 ::= SEQUENCE {
   supportedBandListEUTRA-v1320 [0] SupportedBandListEUTRA-v1320 OPTIONAL,
   supportedBandCombination-v1320 [1] SupportedBandCombination-v1320 OPTIONAL,
   supportedBandCombinationAdd-v1320 [2] SupportedBandCombinationAdd-v1320
       OPTIONAL,
   supportedBandCombinationReduced-v1320 [3] 
      SupportedBandCombinationReduced-v1320 OPTIONAL
}

UE-EUTRA-CapabilityAddXDD-Mode-v1320 ::= SEQUENCE {
   phyLayerParameters-v1320 [0] PhyLayerParameters-v1320 OPTIONAL,
   scptm-Parameters-r13 [1] SCPTM-Parameters-r13 OPTIONAL
}

PhyLayerParameters-v1330 ::= SEQUENCE {
   cch-InterfMitigation-RefRecTypeA-r13 [0] ENUMERATED { supported(0) }
       OPTIONAL,
   cch-InterfMitigation-RefRecTypeB-r13 [1] ENUMERATED { supported(0) }
       OPTIONAL,
   cch-InterfMitigation-MaxNumCCs-r13 [2] INTEGER (1..maxServCell-r13) OPTIONAL,
   crs-InterfMitigationTM1toTM9-r13 [3] INTEGER (1..maxServCell-r13) OPTIONAL
}

CE-Parameters-v1350 ::= SEQUENCE {
   unicastFrequencyHopping-r13 [0] ENUMERATED { supported(0) } OPTIONAL
}

Other-Parameters-v1360 ::= SEQUENCE {
   inDeviceCoexInd-HardwareSharingInd-r13 [0] ENUMERATED { supported(0) }
       OPTIONAL
}

MIMO-UE-ParametersPerTM-v1430 ::= SEQUENCE {
   nzp-CSI-RS-AperiodicInfo-r14 [0] SEQUENCE {
      nMaxProc-r14 [0] INTEGER (5..32),
      nMaxResource-r14 [1] ENUMERATED { ffs1(0), ffs2(1), ffs3(2), ffs4(3) }
   } OPTIONAL,
   nzp-CSI-RS-PeriodicInfo-r14 [1] SEQUENCE {
      nMaxResource-r14 [0] ENUMERATED { ffs1(0), ffs2(1), ffs3(2), ffs4(3) }
   } OPTIONAL,
   zp-CSI-RS-AperiodicInfo-r14 [2] ENUMERATED { supported(0) } OPTIONAL,
   ul-dmrs-Enhancements-r14 [3] ENUMERATED { supported(0) } OPTIONAL,
   densityReductionNP-r14 [4] ENUMERATED { supported(0) } OPTIONAL,
   densityReductionBF-r14 [5] ENUMERATED { supported(0) } OPTIONAL,
   hybridCSI-r14 [6] ENUMERATED { supported(0) } OPTIONAL,
   semiOL-r14 [7] ENUMERATED { supported(0) } OPTIONAL,
   csi-ReportingNP-r14 [8] ENUMERATED { supported(0) } OPTIONAL,
   csi-ReportingAdvanced-r14 [9] ENUMERATED { supported(0) } OPTIONAL
}

MIMO-UE-Parameters-v1430 ::= SEQUENCE {
   parametersTM9-v1430 [0] MIMO-UE-ParametersPerTM-v1430 OPTIONAL,
   parametersTM10-v1430 [1] MIMO-UE-ParametersPerTM-v1430 OPTIONAL
}

FeMBMS-Unicast-Parameters-r14 ::= SEQUENCE {
   unicast-fembmsMixedSCell-r14 [0] ENUMERATED { supported(0) } OPTIONAL,
   emptyUnicastRegion-r14 [1] ENUMERATED { supported(0) } OPTIONAL
}

PhyLayerParameters-v1430 ::= SEQUENCE {
   ce-PUSCH-NB-MaxTBS-r14 [0] ENUMERATED { supported(0) } OPTIONAL,
   ce-PDSCH-PUSCH-MaxBandwidth-r14 [1] ENUMERATED { bw5(0), bw20(1) } OPTIONAL,
   ce-HARQ-AckBundling-r14 [2] ENUMERATED { supported(0) } OPTIONAL,
   ce-PDSCH-TenProcesses-r14 [3] ENUMERATED { supported(0) } OPTIONAL,
   ce-RetuningSymbols-r14 [4] ENUMERATED { n0(0), n1(1) } OPTIONAL,
   ce-PDSCH-PUSCH-Enhancement-r14 [5] ENUMERATED { supported(0) } OPTIONAL,
   ce-SchedulingEnhancement-r14 [6] ENUMERATED { supported(0) } OPTIONAL,
   ce-SRS-Enhancement-r14 [7] ENUMERATED { supported(0) } OPTIONAL,
   ce-PUCCH-Enhancement-r14 [8] ENUMERATED { supported(0) } OPTIONAL,
   ce-ClosedLoopTxAntennaSelection-r14 [9] ENUMERATED { supported(0) } OPTIONAL
      ,
   tdd-SpecialSubframe-r14 [10] ENUMERATED { supported(0) } OPTIONAL,
   tdd-TTI-Bundling-r14 [11] ENUMERATED { supported(0) } OPTIONAL,
   dmrs-LessUpPTS-r14 [12] ENUMERATED { supported(0) } OPTIONAL,
   mimo-UE-Parameters-v1430 [13] MIMO-UE-Parameters-v1430 OPTIONAL,
   alternativeTBS-Index-r14 [14] ENUMERATED { supported(0) } OPTIONAL,
   feMBMS-Unicast-Parameters-r14 [15] FeMBMS-Unicast-Parameters-r14 OPTIONAL
}

MAC-Parameters-v1430 ::= SEQUENCE {
   shortSPS-IntervalFDD-r14 [0] ENUMERATED { supported(0) } OPTIONAL,
   shortSPS-IntervalTDD-r14 [1] ENUMERATED { supported(0) } OPTIONAL,
   skipUplinkDynamic-r14 [2] ENUMERATED { supported(0) } OPTIONAL,
   skipUplinkSPS-r14 [3] ENUMERATED { supported(0) } OPTIONAL,
   multipleUplinkSPS-r14 [4] ENUMERATED { supported(0) } OPTIONAL,
   dataInactMon-r14 [5] ENUMERATED { supported(0) } OPTIONAL
}

MeasParameters-v1430 ::= SEQUENCE {
   ceMeasurements-r14 [0] ENUMERATED { supported(0) } OPTIONAL,
   ncsg-r14 [1] ENUMERATED { supported(0) } OPTIONAL,
   shortMeasurementGap-r14 [2] ENUMERATED { supported(0) } OPTIONAL,
   perServingCellMeasurementGap-r14 [3] ENUMERATED { supported(0) } OPTIONAL,
   nonUniformGap-r14 [4] ENUMERATED { supported(0) } OPTIONAL
}

PDCP-Parameters-v1430 ::= SEQUENCE {
   supportedUplinkOnlyROHC-Profiles-r14 [0] SEQUENCE {
      profile0x0006-r14 [0] BOOLEAN
   },
   maxNumberROHC-ContextSessions-r14 [1] ENUMERATED { cs2(0), cs4(1), cs8(2), 
      cs12(3), cs16(4), cs24(5), cs32(6), cs48(7), cs64(8), cs128(9), cs256(10)
      , cs512(11), cs1024(12), cs16384(13), spare2(14), spare1(15) } DEFAULT cs16
}

RLC-Parameters-v1430 ::= SEQUENCE {
   extendedPollByte-r14 [0] ENUMERATED { supported(0) } OPTIONAL
}

MIMO-CA-ParametersPerBoBCPerTM-v1430 ::= SEQUENCE {
   csi-ReportingNP-r14 [0] ENUMERATED { different(0) } OPTIONAL,
   csi-ReportingAdvanced-r14 [1] ENUMERATED { different(0) } OPTIONAL
}

MIMO-CA-ParametersPerBoBC-v1430 ::= SEQUENCE {
   parametersTM9-v1430 [0] MIMO-CA-ParametersPerBoBCPerTM-v1430 OPTIONAL,
   parametersTM10-v1430 [1] MIMO-CA-ParametersPerBoBCPerTM-v1430 OPTIONAL
}

UL-256QAM-perCC-Info-r14 ::= SEQUENCE {
   ul-256QAM-perCC-r14 [0] ENUMERATED { supported(0) } OPTIONAL
}

SRS-CapabilityPerBandPair-r14 ::= SEQUENCE {
   retuningInfo [0] SEQUENCE {
      rf-RetuningTimeDL-r14 [0] ENUMERATED { n0(0), n0dot5(1), n1(2), n1dot5(3)
         , n2(4), n2dot5(5), n3(6), n3dot5(7), n4(8), n4dot5(9), n5(10), 
         n5dot5(11), n6(12), n6dot5(13), n7(14), spare1(15) } OPTIONAL,
      rf-RetuningTimeUL-r14 [1] ENUMERATED { n0(0), n0dot5(1), n1(2), n1dot5(3)
         , n2(4), n2dot5(5), n3(6), n3dot5(7), n4(8), n4dot5(9), n5(10), 
         n5dot5(11), n6(12), n6dot5(13), n7(14), spare1(15) } OPTIONAL
   }
}

BandParameters-v1430 ::= SEQUENCE {
   bandParametersDL-v1430 [0] MIMO-CA-ParametersPerBoBC-v1430 OPTIONAL,
   ul-256QAM-r14 [1] ENUMERATED { supported(0) } OPTIONAL,
   ul-256QAM-perCC-InfoList-r14 [2] SEQUENCE (SIZE (2..maxServCell-r13)) OF 
      UL-256QAM-perCC-Info-r14 OPTIONAL,
   srs-CapabilityPerBandPairList-r14 [3] SEQUENCE (SIZE (1..maxSimultaneousBands-r10)) OF 
      SRS-CapabilityPerBandPair-r14 OPTIONAL
}

BandCombinationParameters-v1430 ::= SEQUENCE {
   bandParameterList-v1430 [0] SEQUENCE (SIZE (1..maxSimultaneousBands-r10)) OF BandParameters-v1430
       OPTIONAL,
   v2x-SupportedTxBandCombListPerBC-r14 [1] BIT STRING  (SIZE (1..maxBandComb-r13)) OPTIONAL,
   v2x-SupportedRxBandCombListPerBC-r14 [2] BIT STRING  (SIZE (1..maxBandComb-r13)) OPTIONAL
}

SupportedBandCombination-v1430 ::= SEQUENCE (SIZE (1..maxBandComb-r10)) OF 
   BandCombinationParameters-v1430

SupportedBandCombinationAdd-v1430 ::= SEQUENCE (SIZE (1..maxBandComb-r11)) OF 
   BandCombinationParameters-v1430

SupportedBandCombinationReduced-v1430 ::= SEQUENCE (SIZE (1..maxBandComb-r13)) OF 
   BandCombinationParameters-v1430

RF-Parameters-v1430 ::= SEQUENCE {
   supportedBandCombination-v1430 [0] SupportedBandCombination-v1430 OPTIONAL,
   supportedBandCombinationAdd-v1430 [1] SupportedBandCombinationAdd-v1430
       OPTIONAL,
   supportedBandCombinationReduced-v1430 [2] 
      SupportedBandCombinationReduced-v1430 OPTIONAL,
   eNB-RequestedParameters-v1430 [3] SEQUENCE {
      requestedDiffFallbackCombList-r14 [0] BandCombinationList-r14
   } OPTIONAL,
   diffFallbackCombReport-r14 [4] ENUMERATED { supported(0) } OPTIONAL
}

LAA-Parameters-v1430 ::= SEQUENCE {
   crossCarrierSchedulingLAA-UL-r14 [0] ENUMERATED { supported(0) } OPTIONAL,
   uplinkLAA-r14 [1] ENUMERATED { supported(0) } OPTIONAL,
   twoStepSchedulingTimingInfo-r14 [2] ENUMERATED { nPlus1(0), nPlus2(1), 
      nPlus3(2) } OPTIONAL,
   uss-BlindDecodingAdjustment-r14 [3] ENUMERATED { supported(0) } OPTIONAL,
   uss-BlindDecodingReduction-r14 [4] ENUMERATED { supported(0) } OPTIONAL,
   outOfSequenceGrantHandling-r14 [5] ENUMERATED { supported(0) } OPTIONAL
}

LWA-Parameters-v1430 ::= SEQUENCE {
   lwa-HO-WithoutWT-Change-r14 [0] ENUMERATED { supported(0) } OPTIONAL,
   lwa-UL-r14 [1] ENUMERATED { supported(0) } OPTIONAL,
   wlan-PeriodicMeas-r14 [2] ENUMERATED { supported(0) } OPTIONAL,
   wlan-ReportAnyWLAN-r14 [3] ENUMERATED { supported(0) } OPTIONAL,
   wlan-SupportedDataRate-r14 [4] INTEGER (1..2048) OPTIONAL
}

LWIP-Parameters-v1430 ::= SEQUENCE {
   lwip-Aggregation-DL-r14 [0] ENUMERATED { supported(0) } OPTIONAL,
   lwip-Aggregation-UL-r14 [1] ENUMERATED { supported(0) } OPTIONAL
}

Other-Parameters-v1430 ::= SEQUENCE {
   bwPrefInd-r14 [0] ENUMERATED { supported(0) } OPTIONAL,
   rlm-ReportSupport-r14 [1] ENUMERATED { supported(0) } OPTIONAL
}

MMTEL-Parameters-r14 ::= SEQUENCE {
   delayBudgetReporting-r14 [0] ENUMERATED { supported(0) } OPTIONAL,
   pusch-Enhancements-r14 [1] ENUMERATED { supported(0) } OPTIONAL,
   recommendedBitRate-r14 [2] ENUMERATED { supported(0) } OPTIONAL,
   recommendedBitRateQuery-r14 [3] ENUMERATED { supported(0) } OPTIONAL
}

MobilityParameters-r14 ::= SEQUENCE {
   makeBeforeBreak-r14 [0] ENUMERATED { supported(0) } OPTIONAL,
   rach-Less-r14 [1] ENUMERATED { supported(0) } OPTIONAL
}

CE-Parameters-v1430 ::= SEQUENCE {
   ce-SwitchWithoutHO-r14 [0] ENUMERATED { supported(0) } OPTIONAL
}

UE-EUTRA-CapabilityAddXDD-Mode-v1430 ::= SEQUENCE {
   phyLayerParameters-v1430 [0] PhyLayerParameters-v1430 OPTIONAL,
   mmtel-Parameters-r14 [1] MMTEL-Parameters-r14 OPTIONAL
}

MBMS-Parameters-v1430 ::= SEQUENCE {
   fembmsDedicatedCell-r14 [0] ENUMERATED { supported(0) } OPTIONAL,
   fembmsMixedCell-r14 [1] ENUMERATED { supported(0) } OPTIONAL,
   subcarrierSpacingMBMS-khz7dot5-r14 [2] ENUMERATED { supported(0) } OPTIONAL,
   subcarrierSpacingMBMS-khz1dot25-r14 [3] ENUMERATED { supported(0) } OPTIONAL
}

V2X-BandwidthClassSL-r14 ::= SEQUENCE (SIZE (1..maxBandwidthClass-r10)) OF V2X-BandwidthClass-r14

BandParametersTxSL-r14 ::= SEQUENCE {
   v2x-BandwidthClassTxSL-r14 [0] V2X-BandwidthClassSL-r14,
   v2x-eNB-Scheduled-r14 [1] ENUMERATED { supported(0) } OPTIONAL,
   v2x-HighPower-r14 [2] ENUMERATED { supported(0) } OPTIONAL
}

BandParametersRxSL-r14 ::= SEQUENCE {
   v2x-BandwidthClassRxSL-r14 [0] V2X-BandwidthClassSL-r14,
   v2x-HighReception-r14 [1] ENUMERATED { supported(0) } OPTIONAL
}

V2X-BandParameters-r14 ::= SEQUENCE {
   v2x-FreqBandEUTRA-r14 [0] FreqBandIndicator-r11,
   bandParametersTxSL-r14 [1] BandParametersTxSL-r14 OPTIONAL,
   bandParametersRxSL-r14 [2] BandParametersRxSL-r14 OPTIONAL
}

V2X-BandCombinationParameters-r14 ::= SEQUENCE (SIZE (1..maxSimultaneousBands-r10)) OF 
   V2X-BandParameters-r14

V2X-SupportedBandCombination-r14 ::= SEQUENCE (SIZE (1..maxBandComb-r13)) OF 
   V2X-BandCombinationParameters-r14

SL-Parameters-v1430 ::= SEQUENCE {
   zoneBasedPoolSelection-r14 [0] ENUMERATED { supported(0) } OPTIONAL,
   ue-AutonomousWithFullSensing-r14 [1] ENUMERATED { supported(0) } OPTIONAL,
   ue-AutonomousWithPartialSensing-r14 [2] ENUMERATED { supported(0) } OPTIONAL
      ,
   sl-CongestionControl-r14 [3] ENUMERATED { supported(0) } OPTIONAL,
   v2x-TxWithShortResvInterval-r14 [4] ENUMERATED { supported(0) } OPTIONAL,
   v2x-numberTxRxTiming-r14 [5] INTEGER (1..16) OPTIONAL,
   v2x-nonAdjacentPSCCH-PSSCH-r14 [6] ENUMERATED { supported(0) } OPTIONAL,
   slss-TxRx-r14 [7] ENUMERATED { supported(0) } OPTIONAL,
   v2x-SupportedBandCombinationList-r14 [8] V2X-SupportedBandCombination-r14
       OPTIONAL
}

UE-BasedNetwPerfMeasParameters-v1430 ::= SEQUENCE {
   locationReport-r14 [0] ENUMERATED { supported(0) } OPTIONAL
}

HighSpeedEnhParameters-r14 ::= SEQUENCE {
   measurementEnhancements-r14 [0] ENUMERATED { supported(0) } OPTIONAL,
   demodulationEnhancements-r14 [1] ENUMERATED { supported(0) } OPTIONAL,
   prach-Enhancements-r14 [2] ENUMERATED { supported(0) } OPTIONAL
}

LWA-Parameters-v1440 ::= SEQUENCE {
   lwa-RLC-UM-r14 [0] ENUMERATED { supported(0) } OPTIONAL
}

MAC-Parameters-v1440 ::= SEQUENCE {
   rai-Support-r14 [0] ENUMERATED { supported(0) } OPTIONAL
}

PhyLayerParameters-v1450 ::= SEQUENCE {
   ce-SRS-EnhancementWithoutComb4-r14 [0] ENUMERATED { supported(0) } OPTIONAL,
   crs-LessDwPTS-r14 [1] ENUMERATED { supported(0) } OPTIONAL
}

MUST-Parameters-r14 ::= SEQUENCE {
   must-TM234-UpTo2Tx-r14 [0] ENUMERATED { supported(0) } OPTIONAL,
   must-TM89-UpToOneInterferingLayer-r14 [1] ENUMERATED { supported(0) }
       OPTIONAL,
   must-TM10-UpToOneInterferingLayer-r14 [2] ENUMERATED { supported(0) }
       OPTIONAL,
   must-TM89-UpToThreeInterferingLayers-r14 [3] ENUMERATED { supported(0) }
       OPTIONAL,
   must-TM10-UpToThreeInterferingLayers-r14 [4] ENUMERATED { supported(0) }
       OPTIONAL
}

BandParameters-v1450 ::= SEQUENCE {
   must-CapabilityPerBand-r14 [0] MUST-Parameters-r14 OPTIONAL
}

BandCombinationParameters-v1450 ::= SEQUENCE {
   bandParameterList-v1450 [0] SEQUENCE (SIZE (1..maxSimultaneousBands-r10)) OF BandParameters-v1450
       OPTIONAL
}

SupportedBandCombination-v1450 ::= SEQUENCE (SIZE (1..maxBandComb-r10)) OF 
   BandCombinationParameters-v1450

SupportedBandCombinationAdd-v1450 ::= SEQUENCE (SIZE (1..maxBandComb-r11)) OF 
   BandCombinationParameters-v1450

SupportedBandCombinationReduced-v1450 ::= SEQUENCE (SIZE (1..maxBandComb-r13)) OF 
   BandCombinationParameters-v1450

RF-Parameters-v1450 ::= SEQUENCE {
   supportedBandCombination-v1450 [0] SupportedBandCombination-v1450 OPTIONAL,
   supportedBandCombinationAdd-v1450 [1] SupportedBandCombinationAdd-v1450
       OPTIONAL,
   supportedBandCombinationReduced-v1450 [2] 
      SupportedBandCombinationReduced-v1450 OPTIONAL
}

OtherParameters-v1450 ::= SEQUENCE {
   overheatingInd-r14 [0] ENUMERATED { supported(0) } OPTIONAL
}

Other-Parameters-v1460 ::= SEQUENCE {
   nonCSG-SI-Reporting-r14 [0] ENUMERATED { supported(0) } OPTIONAL
}

SupportedBandNR-r15 ::= SEQUENCE {
   bandNR-r15 [0] FreqBandIndicatorNR-r15
}

SupportedBandListNR-r15 ::= SEQUENCE (SIZE (1..maxBandsNR-r15)) OF SupportedBandNR-r15

IRAT-ParametersNR-r15 ::= SEQUENCE {
   en-DC-r15 [0] ENUMERATED { supported(0) } OPTIONAL,
   eventB2-r15 [1] ENUMERATED { supported(0) } OPTIONAL,
   supportedBandListEN-DC-r15 [2] SupportedBandListNR-r15 OPTIONAL
}

MIMO-CA-ParametersPerBoBCPerTM-r15 ::= SEQUENCE {
   nonPrecoded-r13 [0] MIMO-NonPrecodedCapabilities-r13 OPTIONAL,
   beamformed-r13 [1] MIMO-BeamformedCapabilityList-r13 OPTIONAL,
   dmrs-Enhancements-r13 [2] ENUMERATED { different(0) } OPTIONAL,
   csi-ReportingNP-r14 [3] ENUMERATED { different(0) } OPTIONAL,
   csi-ReportingAdvanced-r14 [4] ENUMERATED { different(0) } OPTIONAL
}

MIMO-CA-ParametersPerBoBC-r15 ::= SEQUENCE {
   parametersTM9-r15 [0] MIMO-CA-ParametersPerBoBCPerTM-r15 OPTIONAL,
   parametersTM10-r15 [1] MIMO-CA-ParametersPerBoBCPerTM-r15 OPTIONAL
}

FeatureSetDL-r15 ::= SEQUENCE {
   mimo-CA-ParametersPerBoBC-r15 [0] MIMO-CA-ParametersPerBoBC-r15 OPTIONAL,
   featureSetPerCC-ListDL-r15 [1] SEQUENCE (SIZE (1..maxServCell-r13)) OF 
      FeatureSetDL-PerCC-Id-r15
}

FeatureSetDL-PerCC-r15 ::= SEQUENCE {
   fourLayerTM3-TM4-r15 [0] ENUMERATED { supported(0) } OPTIONAL,
   supportedMIMO-CapabilityDL-MRDC-r15 [1] MIMO-CapabilityDL-r10 OPTIONAL,
   supportedCSI-Proc-r15 [2] ENUMERATED { n1(0), n3(1), n4(2) } OPTIONAL
}

FeatureSetUL-r15 ::= SEQUENCE {
   featureSetPerCC-ListUL-r15 [0] SEQUENCE (SIZE (1..maxServCell-r13)) OF 
      FeatureSetUL-PerCC-Id-r15
}

FeatureSetUL-PerCC-r15 ::= SEQUENCE {
   supportedMIMO-CapabilityUL-r15 [0] MIMO-CapabilityUL-r10 OPTIONAL,
   ul-256QAM-r15 [1] ENUMERATED { supported(0) } OPTIONAL
}

FeatureSetDL-v1550 ::= SEQUENCE {
   dl-1024QAM-r15 [0] ENUMERATED { supported(0) } OPTIONAL
}

FeatureSetsEUTRA-r15 ::= SEQUENCE {
   featureSetsDL-r15 [0] SEQUENCE (SIZE (1..maxFeatureSets-r15)) OF FeatureSetDL-r15 OPTIONAL,
   featureSetsDL-PerCC-r15 [1] SEQUENCE (SIZE (1..maxPerCC-FeatureSets-r15)) OF FeatureSetDL-PerCC-r15
       OPTIONAL,
   featureSetsUL-r15 [2] SEQUENCE (SIZE (1..maxFeatureSets-r15)) OF FeatureSetUL-r15 OPTIONAL,
   featureSetsUL-PerCC-r15 [3] SEQUENCE (SIZE (1..maxPerCC-FeatureSets-r15)) OF FeatureSetUL-PerCC-r15
       OPTIONAL,
   ...,
   [[
      featureSetsDL-v1550 [4] SEQUENCE (SIZE (1..maxFeatureSets-r15)) OF FeatureSetDL-v1550
          OPTIONAL
   ]]
}

PDCP-ParametersNR-r15 ::= SEQUENCE {
   rohc-Profiles-r15 [0] ROHC-ProfileSupportList-r15,
   rohc-ContextMaxSessions-r15 [1] ENUMERATED { cs2(0), cs4(1), cs8(2), cs12(3)
      , cs16(4), cs24(5), cs32(6), cs48(7), cs64(8), cs128(9), cs256(10), 
      cs512(11), cs1024(12), cs16384(13), spare2(14), spare1(15) } DEFAULT cs16,
   rohc-ProfilesUL-Only-r15 [2] SEQUENCE {
      profile0x0006-r15 [0] BOOLEAN
   },
   rohc-ContextContinue-r15 [3] ENUMERATED { supported(0) } OPTIONAL,
   outOfOrderDelivery-r15 [4] ENUMERATED { supported(0) } OPTIONAL,
   sn-SizeLo-r15 [5] ENUMERATED { supported(0) } OPTIONAL,
   ims-VoiceOverNR-PDCP-MCG-Bearer-r15 [6] ENUMERATED { supported(0) } OPTIONAL
      ,
   ims-VoiceOverNR-PDCP-SCG-Bearer-r15 [7] ENUMERATED { supported(0) } OPTIONAL
}

UE-EUTRA-CapabilityAddXDD-Mode-v1510 ::= SEQUENCE {
   pdcp-ParametersNR-r15 [0] PDCP-ParametersNR-r15 OPTIONAL
}

MeasParameters-v1520 ::= SEQUENCE {
   measGapPatterns-r15 [0] BIT STRING  (SIZE (8)) OPTIONAL
}

MeasParameters-v1530 ::= SEQUENCE {
   qoe-MeasReport-r15 [0] ENUMERATED { supported(0) } OPTIONAL,
   qoe-MTSI-MeasReport-r15 [1] ENUMERATED { supported(0) } OPTIONAL,
   ca-IdleModeMeasurements-r15 [2] ENUMERATED { supported(0) } OPTIONAL,
   ca-IdleModeValidityArea-r15 [3] ENUMERATED { supported(0) } OPTIONAL,
   heightMeas-r15 [4] ENUMERATED { supported(0) } OPTIONAL,
   multipleCellsMeasExtension-r15 [5] ENUMERATED { supported(0) } OPTIONAL
}

Other-Parameters-v1530 ::= SEQUENCE {
   assistInfoBitForLC-r15 [0] ENUMERATED { supported(0) } OPTIONAL,
   timeReferenceProvision-r15 [1] ENUMERATED { supported(0) } OPTIONAL,
   flightPathPlan-r15 [2] ENUMERATED { supported(0) } OPTIONAL
}

NeighCellSI-AcquisitionParameters-v1530 ::= SEQUENCE {
   reportCGI-NR-EN-DC-r15 [0] ENUMERATED { supported(0) } OPTIONAL,
   reportCGI-NR-NoEN-DC-r15 [1] ENUMERATED { supported(0) } OPTIONAL
}

SkipSubframeProcessing-r15 ::= SEQUENCE {
   skipProcessingDL-Slot-r15 [0] INTEGER (0..3) OPTIONAL,
   skipProcessingDL-SubSlot-r15 [1] INTEGER (0..3) OPTIONAL,
   skipProcessingUL-Slot-r15 [2] INTEGER (0..3) OPTIONAL,
   skipProcessingUL-SubSlot-r15 [3] INTEGER (0..3) OPTIONAL
}

MAC-Parameters-v1530 ::= SEQUENCE {
   min-Proc-TimelineSubslot-r15 [0] SEQUENCE (SIZE (1..3)) OF 
      ProcessingTimelineSet-r15 OPTIONAL,
   skipSubframeProcessing-r15 [1] SkipSubframeProcessing-r15 OPTIONAL,
   earlyData-UP-r15 [2] ENUMERATED { supported(0) } OPTIONAL,
   dormantSCellState-r15 [3] ENUMERATED { supported(0) } OPTIONAL,
   directSCellActivation-r15 [4] ENUMERATED { supported(0) } OPTIONAL,
   directSCellHibernation-r15 [5] ENUMERATED { supported(0) } OPTIONAL,
   extendedLCID-Duplication-r15 [6] ENUMERATED { supported(0) } OPTIONAL,
   sps-ServingCell-r15 [7] ENUMERATED { supported(0) } OPTIONAL
}

PhyLayerParameters-v1530 ::= SEQUENCE {
   stti-SPT-Capabilities-r15 [0] SEQUENCE {
      aperiodicCsi-ReportingSTTI-r15 [0] ENUMERATED { supported(0) } OPTIONAL,
      dmrs-BasedSPDCCH-MBSFN-r15 [1] ENUMERATED { supported(0) } OPTIONAL,
      dmrs-BasedSPDCCH-nonMBSFN-r15 [2] ENUMERATED { supported(0) } OPTIONAL,
      dmrs-PositionPattern-r15 [3] ENUMERATED { supported(0) } OPTIONAL,
      dmrs-SharingSubslotPDSCH-r15 [4] ENUMERATED { supported(0) } OPTIONAL,
      dmrs-RepetitionSubslotPDSCH-r15 [5] ENUMERATED { supported(0) } OPTIONAL,
      epdcch-SPT-differentCells-r15 [6] ENUMERATED { supported(0) } OPTIONAL,
      epdcch-STTI-differentCells-r15 [7] ENUMERATED { supported(0) } OPTIONAL,
      maxLayersSlotOrSubslotPUSCH-r15 [8] ENUMERATED { oneLayer(0), 
         twoLayers(1), fourLayers(2) } OPTIONAL,
      maxNumberUpdatedCSI-Proc-SPT-r15 [9] INTEGER (5..32) OPTIONAL,
      maxNumberUpdatedCSI-Proc-STTI-Comb77-r15 [10] INTEGER (1..32) OPTIONAL,
      maxNumberUpdatedCSI-Proc-STTI-Comb27-r15 [11] INTEGER (1..32) OPTIONAL,
      maxNumberUpdatedCSI-Proc-STTI-Comb22-Set1-r15 [12] INTEGER (1..32) OPTIONAL,
      maxNumberUpdatedCSI-Proc-STTI-Comb22-Set2-r15 [13] INTEGER (1..32) OPTIONAL,
      mimo-UE-ParametersSTTI-r15 [14] MIMO-UE-Parameters-r13 OPTIONAL,
      mimo-UE-ParametersSTTI-v1530 [15] MIMO-UE-Parameters-v1430 OPTIONAL,
      numberOfBlindDecodesUSS-r15 [16] INTEGER (4..32) OPTIONAL,
      pdsch-SlotSubslotPDSCH-Decoding-r15 [17] ENUMERATED { supported(0) }
          OPTIONAL,
      powerUCI-SlotPUSCH [18] ENUMERATED { supported(0) } OPTIONAL,
      powerUCI-SubslotPUSCH [19] ENUMERATED { supported(0) } OPTIONAL,
      slotPDSCH-TxDiv-TM9and10 [20] ENUMERATED { supported(0) } OPTIONAL,
      subslotPDSCH-TxDiv-TM9and10 [21] ENUMERATED { supported(0) } OPTIONAL,
      spdcch-differentRS-types-r15 [22] ENUMERATED { supported(0) } OPTIONAL,
      srs-DCI7-TriggeringFS2-r15 [23] ENUMERATED { supported(0) } OPTIONAL,
      sps-cyclicShift-r15 [24] ENUMERATED { supported(0) } OPTIONAL,
      spdcch-Reuse-r15 [25] ENUMERATED { supported(0) } OPTIONAL,
      sps-STTI-r15 [26] ENUMERATED { slot(0), subslot(1), slotAndSubslot(2) }
          OPTIONAL,
      tm8-slotPDSCH-r15 [27] ENUMERATED { supported(0) } OPTIONAL,
      tm9-slotSubslot-r15 [28] ENUMERATED { supported(0) } OPTIONAL,
      tm9-slotSubslotMBSFN-r15 [29] ENUMERATED { supported(0) } OPTIONAL,
      tm10-slotSubslot-r15 [30] ENUMERATED { supported(0) } OPTIONAL,
      tm10-slotSubslotMBSFN-r15 [31] ENUMERATED { supported(0) } OPTIONAL,
      txDiv-SPUCCH-r15 [32] ENUMERATED { supported(0) } OPTIONAL,
      ul-AsyncHarqSharingDiff-TTI-Lengths-r15 [33] ENUMERATED { supported(0) }
          OPTIONAL
   } OPTIONAL,
   ce-Capabilities-r15 [1] SEQUENCE {
      ce-CRS-IntfMitig-r15 [0] ENUMERATED { supported(0) } OPTIONAL,
      ce-CQI-AlternativeTable-r15 [1] ENUMERATED { supported(0) } OPTIONAL,
      ce-PDSCH-FlexibleStartPRB-CE-ModeA-r15 [2] ENUMERATED { supported(0) }
          OPTIONAL,
      ce-PDSCH-FlexibleStartPRB-CE-ModeB-r15 [3] ENUMERATED { supported(0) }
          OPTIONAL,
      ce-PDSCH-64QAM-r15 [4] ENUMERATED { supported(0) } OPTIONAL,
      ce-PUSCH-FlexibleStartPRB-CE-ModeA-r15 [5] ENUMERATED { supported(0) }
          OPTIONAL,
      ce-PUSCH-FlexibleStartPRB-CE-ModeB-r15 [6] ENUMERATED { supported(0) }
          OPTIONAL,
      ce-PUSCH-SubPRB-Allocation-r15 [7] ENUMERATED { supported(0) } OPTIONAL,
      ce-UL-HARQ-ACK-Feedback-r15 [8] ENUMERATED { supported(0) } OPTIONAL
   } OPTIONAL,
   shortCQI-ForSCellActivation-r15 [2] ENUMERATED { supported(0) } OPTIONAL,
   mimo-CBSR-AdvancedCSI-r15 [3] ENUMERATED { supported(0) } OPTIONAL,
   crs-IntfMitig-r15 [4] ENUMERATED { supported(0) } OPTIONAL,
   ul-PowerControlEnhancements-r15 [5] ENUMERATED { supported(0) } OPTIONAL,
   urllc-Capabilities-r15 [6] SEQUENCE {
      pdsch-RepSubframe-r15 [0] ENUMERATED { supported(0) } OPTIONAL,
      pdsch-RepSlot-r15 [1] ENUMERATED { supported(0) } OPTIONAL,
      pdsch-RepSubslot-r15 [2] ENUMERATED { supported(0) } OPTIONAL,
      pusch-SPS-MultiConfigSubframe-r15 [3] INTEGER (0..6) OPTIONAL,
      pusch-SPS-MaxConfigSubframe-r15 [4] INTEGER (0..31) OPTIONAL,
      pusch-SPS-MultiConfigSlot-r15 [5] INTEGER (0..6) OPTIONAL,
      pusch-SPS-MaxConfigSlot-r15 [6] INTEGER (0..31) OPTIONAL,
      pusch-SPS-MultiConfigSubslot-r15 [7] INTEGER (0..6) OPTIONAL,
      pusch-SPS-MaxConfigSubslot-r15 [8] INTEGER (0..31) OPTIONAL,
      pusch-SPS-SlotRepPCell-r15 [9] ENUMERATED { supported(0) } OPTIONAL,
      pusch-SPS-SlotRepPSCell-r15 [10] ENUMERATED { supported(0) } OPTIONAL,
      pusch-SPS-SlotRepSCell-r15 [11] ENUMERATED { supported(0) } OPTIONAL,
      pusch-SPS-SubframeRepPCell-r15 [12] ENUMERATED { supported(0) } OPTIONAL,
      pusch-SPS-SubframeRepPSCell-r15 [13] ENUMERATED { supported(0) } OPTIONAL
         ,
      pusch-SPS-SubframeRepSCell-r15 [14] ENUMERATED { supported(0) } OPTIONAL,
      pusch-SPS-SubslotRepPCell-r15 [15] ENUMERATED { supported(0) } OPTIONAL,
      pusch-SPS-SubslotRepPSCell-r15 [16] ENUMERATED { supported(0) } OPTIONAL,
      pusch-SPS-SubslotRepSCell-r15 [17] ENUMERATED { supported(0) } OPTIONAL,
      semiStaticCFI-r15 [18] ENUMERATED { supported(0) } OPTIONAL,
      semiStaticCFI-Pattern-r15 [19] ENUMERATED { supported(0) } OPTIONAL
   } OPTIONAL,
   altMCS-Table-r15 [7] ENUMERATED { supported(0) } OPTIONAL
}

CA-MIMO-ParametersDL-r15 ::= SEQUENCE {
   supportedMIMO-CapabilityDL-r15 [0] MIMO-CapabilityDL-r10 OPTIONAL,
   fourLayerTM3-TM4-r15 [1] ENUMERATED { supported(0) } OPTIONAL,
   intraBandContiguousCC-InfoList-r15 [2] SEQUENCE (SIZE (1..maxServCell-r13)) OF 
      IntraBandContiguousCC-Info-r12 OPTIONAL
}

CA-MIMO-ParametersUL-r15 ::= SEQUENCE {
   supportedMIMO-CapabilityUL-r15 [0] MIMO-CapabilityUL-r10 OPTIONAL
}

DL-UL-CCs-r15 ::= SEQUENCE {
   maxNumberDL-CCs-r15 [0] INTEGER (1..32) OPTIONAL,
   maxNumberUL-CCs-r15 [1] INTEGER (1..32) OPTIONAL
}

STTI-SupportedCombinations-r15 ::= SEQUENCE {
   combination-22-r15 [0] DL-UL-CCs-r15 OPTIONAL,
   combination-77-r15 [1] DL-UL-CCs-r15 OPTIONAL,
   combination-27-r15 [2] DL-UL-CCs-r15 OPTIONAL,
   combination-22-27-r15 [3] SEQUENCE (SIZE (1..2)) OF DL-UL-CCs-r15 OPTIONAL,
   combination-77-22-r15 [4] SEQUENCE (SIZE (1..2)) OF DL-UL-CCs-r15 OPTIONAL,
   combination-77-27-r15 [5] SEQUENCE (SIZE (1..2)) OF DL-UL-CCs-r15 OPTIONAL
}

STTI-SPT-BandParameters-r15 ::= SEQUENCE {
   dl-1024QAM-Slot-r15 [0] ENUMERATED { supported(0) } OPTIONAL,
   dl-1024QAM-SubslotTA-1-r15 [1] ENUMERATED { supported(0) } OPTIONAL,
   dl-1024QAM-SubslotTA-2-r15 [2] ENUMERATED { supported(0) } OPTIONAL,
   simultaneousTx-differentTx-duration-r15 [3] ENUMERATED { supported(0) }
       OPTIONAL,
   sTTI-CA-MIMO-ParametersDL-r15 [4] CA-MIMO-ParametersDL-r15 OPTIONAL,
   sTTI-CA-MIMO-ParametersUL-r15 [5] CA-MIMO-ParametersUL-r15,
   sTTI-FD-MIMO-Coexistence [6] ENUMERATED { supported(0) } OPTIONAL,
   sTTI-MIMO-CA-ParametersPerBoBCs-r15 [7] MIMO-CA-ParametersPerBoBC-r13
       OPTIONAL,
   sTTI-MIMO-CA-ParametersPerBoBCs-v1530 [8] MIMO-CA-ParametersPerBoBC-v1430
       OPTIONAL,
   sTTI-SupportedCombinations-r15 [9] STTI-SupportedCombinations-r15 OPTIONAL,
   sTTI-SupportedCSI-Proc-r15 [10] ENUMERATED { n1(0), n3(1), n4(2) } OPTIONAL,
   ul-256QAM-Slot-r15 [11] ENUMERATED { supported(0) } OPTIONAL,
   ul-256QAM-Subslot-r15 [12] ENUMERATED { supported(0) } OPTIONAL,
   ...
}

BandParameters-v1530 ::= SEQUENCE {
   ue-TxAntennaSelection-SRS-1T4R-r15 [0] ENUMERATED { supported(0) } OPTIONAL,
   ue-TxAntennaSelection-SRS-2T4R-2Pairs-r15 [1] ENUMERATED { supported(0) }
       OPTIONAL,
   ue-TxAntennaSelection-SRS-2T4R-3Pairs-r15 [2] ENUMERATED { supported(0) }
       OPTIONAL,
   dl-1024QAM-r15 [3] ENUMERATED { supported(0) } OPTIONAL,
   qcl-TypeC-Operation-r15 [4] ENUMERATED { supported(0) } OPTIONAL,
   qcl-CRI-BasedCSI-Reporting-r15 [5] ENUMERATED { supported(0) } OPTIONAL,
   stti-SPT-BandParameters-r15 [6] STTI-SPT-BandParameters-r15 OPTIONAL
}

SPT-Parameters-r15 ::= SEQUENCE {
   frameStructureType-SPT-r15 [0] BIT STRING  (SIZE (3)) OPTIONAL,
   maxNumberCCs-SPT-r15 [1] INTEGER (1..32) OPTIONAL
}

BandCombinationParameters-v1530 ::= SEQUENCE {
   bandParameterList-v1530 [0] SEQUENCE (SIZE (1..maxSimultaneousBands-r10)) OF BandParameters-v1530
       OPTIONAL,
   spt-Parameters-r15 [1] SPT-Parameters-r15 OPTIONAL
}

SupportedBandCombination-v1530 ::= SEQUENCE (SIZE (1..maxBandComb-r10)) OF 
   BandCombinationParameters-v1530

SupportedBandCombinationAdd-v1530 ::= SEQUENCE (SIZE (1..maxBandComb-r11)) OF 
   BandCombinationParameters-v1530

SupportedBandCombinationReduced-v1530 ::= SEQUENCE (SIZE (1..maxBandComb-r13)) OF 
   BandCombinationParameters-v1530

RF-Parameters-v1530 ::= SEQUENCE {
   sTTI-SPT-Supported-r15 [0] ENUMERATED { supported(0) } OPTIONAL,
   supportedBandCombination-v1530 [1] SupportedBandCombination-v1530 OPTIONAL,
   supportedBandCombinationAdd-v1530 [2] SupportedBandCombinationAdd-v1530
       OPTIONAL,
   supportedBandCombinationReduced-v1530 [3] 
      SupportedBandCombinationReduced-v1530 OPTIONAL,
   powerClass-14dBm-r15 [4] ENUMERATED { supported(0) } OPTIONAL
}

SupportedOperatorDic-r15 ::= SEQUENCE {
   versionOfDictionary-r15 [0] INTEGER (0..15),
   associatedPLMN-ID-r15 [1] PLMN-Identity
}

SupportedUDC-r15 ::= SEQUENCE {
   supportedStandardDic-r15 [0] ENUMERATED { supported(0) } OPTIONAL,
   supportedOperatorDic-r15 [1] SupportedOperatorDic-r15 OPTIONAL
}

PDCP-Parameters-v1530 ::= SEQUENCE {
   supportedUDC-r15 [0] SupportedUDC-r15 OPTIONAL,
   pdcp-Duplication-r15 [1] ENUMERATED { supported(0) } OPTIONAL
}

UE-BasedNetwPerfMeasParameters-v1530 ::= SEQUENCE {
   loggedMeasBT-r15 [0] ENUMERATED { supported(0) } OPTIONAL,
   loggedMeasWLAN-r15 [1] ENUMERATED { supported(0) } OPTIONAL,
   immMeasBT-r15 [2] ENUMERATED { supported(0) } OPTIONAL,
   immMeasWLAN-r15 [3] ENUMERATED { supported(0) } OPTIONAL
}

RLC-Parameters-v1530 ::= SEQUENCE {
   flexibleUM-AM-Combinations-r15 [0] ENUMERATED { supported(0) } OPTIONAL,
   rlc-AM-Ooo-Delivery-r15 [1] ENUMERATED { supported(0) } OPTIONAL,
   rlc-UM-Ooo-Delivery-r15 [2] ENUMERATED { supported(0) } OPTIONAL
}

UE-CategorySL-r15 ::= SEQUENCE {
   ue-CategorySL-C-TX-r15 [0] INTEGER (1..5),
   ue-CategorySL-C-RX-r15 [1] INTEGER (1..4)
}

V2X-BandParameters-v1530 ::= SEQUENCE {
   v2x-EnhancedHighReception-r15 [0] ENUMERATED { supported(0) } OPTIONAL
}

V2X-BandCombinationParameters-v1530 ::= SEQUENCE (SIZE (1..maxSimultaneousBands-r10)) OF 
   V2X-BandParameters-v1530

V2X-SupportedBandCombination-v1530 ::= SEQUENCE (SIZE (1..maxBandComb-r13)) OF 
   V2X-BandCombinationParameters-v1530

SL-Parameters-v1530 ::= SEQUENCE {
   slss-SupportedTxFreq-r15 [0] ENUMERATED { single(0), multiple(1) } OPTIONAL,
   sl-64QAM-Tx-r15 [1] ENUMERATED { supported(0) } OPTIONAL,
   sl-TxDiversity-r15 [2] ENUMERATED { supported(0) } OPTIONAL,
   ue-CategorySL-r15 [3] UE-CategorySL-r15 OPTIONAL,
   v2x-SupportedBandCombinationList-v1530 [4] 
      V2X-SupportedBandCombination-v1530 OPTIONAL
}

LAA-Parameters-v1530 ::= SEQUENCE {
   aul-r15 [0] ENUMERATED { supported(0) } OPTIONAL,
   laa-PUSCH-Mode1-r15 [1] ENUMERATED { supported(0) } OPTIONAL,
   laa-PUSCH-Mode2-r15 [2] ENUMERATED { supported(0) } OPTIONAL,
   laa-PUSCH-Mode3-r15 [3] ENUMERATED { supported(0) } OPTIONAL
}

UE-EUTRA-CapabilityAddXDD-Mode-v1530 ::= SEQUENCE {
   neighCellSI-AcquisitionParameters-v1530 [0] 
      NeighCellSI-AcquisitionParameters-v1530 OPTIONAL,
   reducedCP-Latency-r15 [1] ENUMERATED { supported(0) } OPTIONAL
}

PhyLayerParameters-v1540 ::= SEQUENCE {
   stti-SPT-Capabilities-v1540 [0] SEQUENCE {
      slotPDSCH-TxDiv-TM8-r15 [0] ENUMERATED { supported(0) }
   } OPTIONAL,
   crs-IM-TM1-toTM9-OneRX-Port-v1540 [1] ENUMERATED { supported(0) } OPTIONAL,
   cch-IM-RefRecTypeA-OneRX-Port-v1540 [2] ENUMERATED { supported(0) } OPTIONAL
}

Other-Parameters-v1540 ::= SEQUENCE {
   inDeviceCoexInd-ENDC-r15 [0] ENUMERATED { supported(0) } OPTIONAL
}

EUTRA-5GC-Parameters-r15 ::= SEQUENCE {
   eutra-5GC-r15 [0] ENUMERATED { supported(0) } OPTIONAL,
   eutra-EPC-HO-EUTRA-5GC-r15 [1] ENUMERATED { supported(0) } OPTIONAL,
   ho-EUTRA-5GC-FDD-TDD-r15 [2] ENUMERATED { supported(0) } OPTIONAL,
   ho-InterfreqEUTRA-5GC-r15 [3] ENUMERATED { supported(0) } OPTIONAL,
   ims-VoiceOverMCG-BearerEUTRA-5GC-r15 [4] ENUMERATED { supported(0) }
       OPTIONAL,
   inactiveState-r15 [5] ENUMERATED { supported(0) } OPTIONAL,
   reflectiveQoS-r15 [6] ENUMERATED { supported(0) } OPTIONAL
}

IRAT-ParametersNR-v1540 ::= SEQUENCE {
   eutra-5GC-HO-ToNR-FDD-FR1-r15 [0] ENUMERATED { supported(0) } OPTIONAL,
   eutra-5GC-HO-ToNR-TDD-FR1-r15 [1] ENUMERATED { supported(0) } OPTIONAL,
   eutra-5GC-HO-ToNR-FDD-FR2-r15 [2] ENUMERATED { supported(0) } OPTIONAL,
   eutra-5GC-HO-ToNR-TDD-FR2-r15 [3] ENUMERATED { supported(0) } OPTIONAL,
   eutra-EPC-HO-ToNR-FDD-FR1-r15 [4] ENUMERATED { supported(0) } OPTIONAL,
   eutra-EPC-HO-ToNR-TDD-FR1-r15 [5] ENUMERATED { supported(0) } OPTIONAL,
   eutra-EPC-HO-ToNR-FDD-FR2-r15 [6] ENUMERATED { supported(0) } OPTIONAL,
   eutra-EPC-HO-ToNR-TDD-FR2-r15 [7] ENUMERATED { supported(0) } OPTIONAL,
   ims-VoiceOverNR-FR1-r15 [8] ENUMERATED { supported(0) } OPTIONAL,
   ims-VoiceOverNR-FR2-r15 [9] ENUMERATED { supported(0) } OPTIONAL,
   sa-NR-r15 [10] ENUMERATED { supported(0) } OPTIONAL,
   supportedBandListNR-SA-r15 [11] SupportedBandListNR-r15 OPTIONAL
}

UE-EUTRA-CapabilityAddXDD-Mode-v1540 ::= SEQUENCE {
   eutra-5GC-Parameters-r15 [0] EUTRA-5GC-Parameters-r15 OPTIONAL,
   irat-ParametersNR-v1540 [1] IRAT-ParametersNR-v1540 OPTIONAL
}

SL-Parameters-v1540 ::= SEQUENCE {
   sl-64QAM-Rx-r15 [0] ENUMERATED { supported(0) } OPTIONAL,
   sl-RateMatchingTBSScaling-r15 [1] ENUMERATED { supported(0) } OPTIONAL,
   sl-LowT2min-r15 [2] ENUMERATED { supported(0) } OPTIONAL,
   v2x-SensingReportingMode3-r15 [3] ENUMERATED { supported(0) } OPTIONAL
}

NeighCellSI-AcquisitionParameters-v1550 ::= SEQUENCE {
   eutra-CGI-Reporting-ENDC-r15 [0] ENUMERATED { supported(0) } OPTIONAL,
   utra-GERAN-CGI-Reporting-ENDC-r15 [1] ENUMERATED { supported(0) } OPTIONAL
}

PhyLayerParameters-v1550 ::= SEQUENCE {
   dmrs-OverheadReduction-r15 [0] ENUMERATED { supported(0) } OPTIONAL
}

MAC-Parameters-v1550 ::= SEQUENCE {
   eLCID-Support-r15 [0] ENUMERATED { supported(0) } OPTIONAL
}

UE-EUTRA-CapabilityAddXDD-Mode-v1550 ::= SEQUENCE {
   neighCellSI-AcquisitionParameters-v1550 [0] 
      NeighCellSI-AcquisitionParameters-v1550 OPTIONAL
}

PDCP-ParametersNR-v1560 ::= SEQUENCE {
   ims-VoNR-PDCP-SCG-NGENDC-r15 [0] ENUMERATED { supported(0) } OPTIONAL
}

IRAT-ParametersNR-v1560 ::= SEQUENCE {
   ng-EN-DC-r15 [0] ENUMERATED { supported(0) } OPTIONAL
}

UE-EUTRA-CapabilityAddXDD-Mode-v1560 ::= SEQUENCE {
   pdcp-ParametersNR-v1560 [0] PDCP-ParametersNR-v1560
}

RF-Parameters-v1570 ::= SEQUENCE {
   dl-1024QAM-ScalingFactor-r15 [0] ENUMERATED { v1(0), v1dot2(1), v1dot25(2) }
      ,
   dl-1024QAM-TotalWeightedLayers-r15 [1] INTEGER (0..10)
}

IRAT-ParametersNR-v1570 ::= SEQUENCE {
   ss-SINR-Meas-NR-FR1-r15 [0] ENUMERATED { supported(0) } OPTIONAL,
   ss-SINR-Meas-NR-FR2-r15 [1] ENUMERATED { supported(0) } OPTIONAL
}

UE-EUTRA-Capability-v1570-IEs ::= SEQUENCE {
   rf-Parameters-v1570 [0] RF-Parameters-v1570 OPTIONAL,
   irat-ParametersNR-v1570 [1] IRAT-ParametersNR-v1570 OPTIONAL,
   nonCriticalExtension [2] SEQUENCE {

   } OPTIONAL
}

UE-EUTRA-Capability-v1560-IEs ::= SEQUENCE {
   pdcp-ParametersNR-v1560 [0] PDCP-ParametersNR-v1560,
   irat-ParametersNR-v1560 [1] IRAT-ParametersNR-v1560,
   appliedCapabilityFilterCommon-r15 [2] OCTET STRING OPTIONAL,
   fdd-Add-UE-EUTRA-Capabilities-v1560 [3] UE-EUTRA-CapabilityAddXDD-Mode-v1560
      ,
   tdd-Add-UE-EUTRA-Capabilities-v1560 [4] UE-EUTRA-CapabilityAddXDD-Mode-v1560
      ,
   nonCriticalExtension [5] UE-EUTRA-Capability-v1570-IEs OPTIONAL
}

UE-EUTRA-Capability-v1550-IEs ::= SEQUENCE {
   neighCellSI-AcquisitionParameters-v1550 [0] 
      NeighCellSI-AcquisitionParameters-v1550 OPTIONAL,
   phyLayerParameters-v1550 [1] PhyLayerParameters-v1550,
   mac-Parameters-v1550 [2] MAC-Parameters-v1550,
   fdd-Add-UE-EUTRA-Capabilities-v1550 [3] UE-EUTRA-CapabilityAddXDD-Mode-v1550
      ,
   tdd-Add-UE-EUTRA-Capabilities-v1550 [4] UE-EUTRA-CapabilityAddXDD-Mode-v1550
      ,
   nonCriticalExtension [5] UE-EUTRA-Capability-v1560-IEs OPTIONAL
}

UE-EUTRA-Capability-v1540-IEs ::= SEQUENCE {
   phyLayerParameters-v1540 [0] PhyLayerParameters-v1540 OPTIONAL,
   otherParameters-v1540 [1] Other-Parameters-v1540,
   fdd-Add-UE-EUTRA-Capabilities-v1540 [2] UE-EUTRA-CapabilityAddXDD-Mode-v1540
       OPTIONAL,
   tdd-Add-UE-EUTRA-Capabilities-v1540 [3] UE-EUTRA-CapabilityAddXDD-Mode-v1540
       OPTIONAL,
   sl-Parameters-v1540 [4] SL-Parameters-v1540 OPTIONAL,
   irat-ParametersNR-v1540 [5] IRAT-ParametersNR-v1540 OPTIONAL,
   nonCriticalExtension [6] UE-EUTRA-Capability-v1550-IEs OPTIONAL
}

UE-EUTRA-Capability-v1530-IEs ::= SEQUENCE {
   measParameters-v1530 [0] MeasParameters-v1530 OPTIONAL,
   otherParameters-v1530 [1] Other-Parameters-v1530 OPTIONAL,
   neighCellSI-AcquisitionParameters-v1530 [2] 
      NeighCellSI-AcquisitionParameters-v1530 OPTIONAL,
   mac-Parameters-v1530 [3] MAC-Parameters-v1530 OPTIONAL,
   phyLayerParameters-v1530 [4] PhyLayerParameters-v1530 OPTIONAL,
   rf-Parameters-v1530 [5] RF-Parameters-v1530 OPTIONAL,
   pdcp-Parameters-v1530 [6] PDCP-Parameters-v1530 OPTIONAL,
   ue-CategoryDL-v1530 [7] INTEGER (22..26) OPTIONAL,
   ue-BasedNetwPerfMeasParameters-v1530 [8] 
      UE-BasedNetwPerfMeasParameters-v1530 OPTIONAL,
   rlc-Parameters-v1530 [9] RLC-Parameters-v1530 OPTIONAL,
   sl-Parameters-v1530 [10] SL-Parameters-v1530 OPTIONAL,
   extendedNumberOfDRBs-r15 [11] ENUMERATED { supported(0) } OPTIONAL,
   reducedCP-Latency-r15 [12] ENUMERATED { supported(0) } OPTIONAL,
   laa-Parameters-v1530 [13] LAA-Parameters-v1530 OPTIONAL,
   ue-CategoryUL-v1530 [14] INTEGER (22..26) OPTIONAL,
   fdd-Add-UE-EUTRA-Capabilities-v1530 [15] 
      UE-EUTRA-CapabilityAddXDD-Mode-v1530 OPTIONAL,
   tdd-Add-UE-EUTRA-Capabilities-v1530 [16] 
      UE-EUTRA-CapabilityAddXDD-Mode-v1530 OPTIONAL,
   nonCriticalExtension [17] UE-EUTRA-Capability-v1540-IEs OPTIONAL
}

UE-EUTRA-Capability-v1520-IEs ::= SEQUENCE {
   measParameters-v1520 [0] MeasParameters-v1520,
   nonCriticalExtension [1] UE-EUTRA-Capability-v1530-IEs OPTIONAL
}

UE-EUTRA-Capability-v1510-IEs ::= SEQUENCE {
   irat-ParametersNR-r15 [0] IRAT-ParametersNR-r15 OPTIONAL,
   featureSetsEUTRA-r15 [1] FeatureSetsEUTRA-r15 OPTIONAL,
   pdcp-ParametersNR-r15 [2] PDCP-ParametersNR-r15 OPTIONAL,
   fdd-Add-UE-EUTRA-Capabilities-v1510 [3] UE-EUTRA-CapabilityAddXDD-Mode-v1510
       OPTIONAL,
   tdd-Add-UE-EUTRA-Capabilities-v1510 [4] UE-EUTRA-CapabilityAddXDD-Mode-v1510
       OPTIONAL,
   nonCriticalExtension [5] UE-EUTRA-Capability-v1520-IEs OPTIONAL
}

UE-EUTRA-Capability-v1460-IEs ::= SEQUENCE {
   ue-CategoryDL-v1460 [0] INTEGER (21) OPTIONAL,
   otherParameters-v1460 [1] Other-Parameters-v1460,
   nonCriticalExtension [2] UE-EUTRA-Capability-v1510-IEs OPTIONAL
}

UE-EUTRA-Capability-v1450-IEs ::= SEQUENCE {
   phyLayerParameters-v1450 [0] PhyLayerParameters-v1450 OPTIONAL,
   rf-Parameters-v1450 [1] RF-Parameters-v1450 OPTIONAL,
   otherParameters-v1450 [2] OtherParameters-v1450,
   ue-CategoryDL-v1450 [3] INTEGER (20) OPTIONAL,
   nonCriticalExtension [4] UE-EUTRA-Capability-v1460-IEs OPTIONAL
}

UE-EUTRA-Capability-v1440-IEs ::= SEQUENCE {
   lwa-Parameters-v1440 [0] LWA-Parameters-v1440,
   mac-Parameters-v1440 [1] MAC-Parameters-v1440,
   nonCriticalExtension [2] UE-EUTRA-Capability-v1450-IEs OPTIONAL
}

UE-EUTRA-Capability-v1430-IEs ::= SEQUENCE {
   phyLayerParameters-v1430 [0] PhyLayerParameters-v1430,
   ue-CategoryDL-v1430 [1] ENUMERATED { m2(0) } OPTIONAL,
   ue-CategoryUL-v1430 [2] ENUMERATED { n16(0), n17(1), n18(2), n19(3), n20(4)
      , m2(5) } OPTIONAL,
   ue-CategoryUL-v1430b [3] ENUMERATED { n21(0) } OPTIONAL,
   mac-Parameters-v1430 [4] MAC-Parameters-v1430 OPTIONAL,
   measParameters-v1430 [5] MeasParameters-v1430 OPTIONAL,
   pdcp-Parameters-v1430 [6] PDCP-Parameters-v1430 OPTIONAL,
   rlc-Parameters-v1430 [7] RLC-Parameters-v1430,
   rf-Parameters-v1430 [8] RF-Parameters-v1430 OPTIONAL,
   laa-Parameters-v1430 [9] LAA-Parameters-v1430 OPTIONAL,
   lwa-Parameters-v1430 [10] LWA-Parameters-v1430 OPTIONAL,
   lwip-Parameters-v1430 [11] LWIP-Parameters-v1430 OPTIONAL,
   otherParameters-v1430 [12] Other-Parameters-v1430,
   mmtel-Parameters-r14 [13] MMTEL-Parameters-r14 OPTIONAL,
   mobilityParameters-r14 [14] MobilityParameters-r14 OPTIONAL,
   ce-Parameters-v1430 [15] CE-Parameters-v1430,
   fdd-Add-UE-EUTRA-Capabilities-v1430 [16] 
      UE-EUTRA-CapabilityAddXDD-Mode-v1430 OPTIONAL,
   tdd-Add-UE-EUTRA-Capabilities-v1430 [17] 
      UE-EUTRA-CapabilityAddXDD-Mode-v1430 OPTIONAL,
   mbms-Parameters-v1430 [18] MBMS-Parameters-v1430 OPTIONAL,
   sl-Parameters-v1430 [19] SL-Parameters-v1430 OPTIONAL,
   ue-BasedNetwPerfMeasParameters-v1430 [20] 
      UE-BasedNetwPerfMeasParameters-v1430 OPTIONAL,
   highSpeedEnhParameters-r14 [21] HighSpeedEnhParameters-r14 OPTIONAL,
   nonCriticalExtension [22] UE-EUTRA-Capability-v1440-IEs OPTIONAL
}

UE-EUTRA-Capability-v1360-IEs ::= SEQUENCE {
   other-Parameters-v1360 [0] Other-Parameters-v1360 OPTIONAL,
   nonCriticalExtension [1] UE-EUTRA-Capability-v1430-IEs OPTIONAL
}

UE-EUTRA-Capability-v1350-IEs ::= SEQUENCE {
   ue-CategoryDL-v1350 [0] ENUMERATED { oneBis(0) } OPTIONAL,
   ue-CategoryUL-v1350 [1] ENUMERATED { oneBis(0) } OPTIONAL,
   ce-Parameters-v1350 [2] CE-Parameters-v1350,
   nonCriticalExtension [3] UE-EUTRA-Capability-v1360-IEs OPTIONAL
}

UE-EUTRA-Capability-v1340-IEs ::= SEQUENCE {
   ue-CategoryUL-v1340 [0] INTEGER (15) OPTIONAL,
   nonCriticalExtension [1] UE-EUTRA-Capability-v1350-IEs OPTIONAL
}

UE-EUTRA-Capability-v1330-IEs ::= SEQUENCE {
   ue-CategoryDL-v1330 [0] INTEGER (18..19) OPTIONAL,
   phyLayerParameters-v1330 [1] PhyLayerParameters-v1330 OPTIONAL,
   ue-CE-NeedULGaps-r13 [2] ENUMERATED { true(0) } OPTIONAL,
   nonCriticalExtension [3] UE-EUTRA-Capability-v1340-IEs OPTIONAL
}

UE-EUTRA-Capability-v1320-IEs ::= SEQUENCE {
   ce-Parameters-v1320 [0] CE-Parameters-v1320 OPTIONAL,
   phyLayerParameters-v1320 [1] PhyLayerParameters-v1320 OPTIONAL,
   rf-Parameters-v1320 [2] RF-Parameters-v1320 OPTIONAL,
   fdd-Add-UE-EUTRA-Capabilities-v1320 [3] UE-EUTRA-CapabilityAddXDD-Mode-v1320
       OPTIONAL,
   tdd-Add-UE-EUTRA-Capabilities-v1320 [4] UE-EUTRA-CapabilityAddXDD-Mode-v1320
       OPTIONAL,
   nonCriticalExtension [5] UE-EUTRA-Capability-v1330-IEs OPTIONAL
}

UE-EUTRA-Capability-v1310-IEs ::= SEQUENCE {
   ue-CategoryDL-v1310 [0] ENUMERATED { n17(0), m1(1) } OPTIONAL,
   ue-CategoryUL-v1310 [1] ENUMERATED { n14(0), m1(1) } OPTIONAL,
   pdcp-Parameters-v1310 [2] PDCP-Parameters-v1310,
   rlc-Parameters-v1310 [3] RLC-Parameters-v1310,
   mac-Parameters-v1310 [4] MAC-Parameters-v1310 OPTIONAL,
   phyLayerParameters-v1310 [5] PhyLayerParameters-v1310 OPTIONAL,
   rf-Parameters-v1310 [6] RF-Parameters-v1310 OPTIONAL,
   measParameters-v1310 [7] MeasParameters-v1310 OPTIONAL,
   dc-Parameters-v1310 [8] DC-Parameters-v1310 OPTIONAL,
   sl-Parameters-v1310 [9] SL-Parameters-v1310 OPTIONAL,
   scptm-Parameters-r13 [10] SCPTM-Parameters-r13 OPTIONAL,
   ce-Parameters-r13 [11] CE-Parameters-r13 OPTIONAL,
   interRAT-ParametersWLAN-r13 [12] IRAT-ParametersWLAN-r13,
   laa-Parameters-r13 [13] LAA-Parameters-r13 OPTIONAL,
   lwa-Parameters-r13 [14] LWA-Parameters-r13 OPTIONAL,
   wlan-IW-Parameters-v1310 [15] WLAN-IW-Parameters-v1310,
   lwip-Parameters-r13 [16] LWIP-Parameters-r13,
   fdd-Add-UE-EUTRA-Capabilities-v1310 [17] 
      UE-EUTRA-CapabilityAddXDD-Mode-v1310 OPTIONAL,
   tdd-Add-UE-EUTRA-Capabilities-v1310 [18] 
      UE-EUTRA-CapabilityAddXDD-Mode-v1310 OPTIONAL,
   nonCriticalExtension [19] UE-EUTRA-Capability-v1320-IEs OPTIONAL
}

UE-EUTRA-Capability-v1280-IEs ::= SEQUENCE {
   phyLayerParameters-v1280 [0] PhyLayerParameters-v1280 OPTIONAL,
   nonCriticalExtension [1] UE-EUTRA-Capability-v1310-IEs OPTIONAL
}

UE-EUTRA-Capability-v1270-IEs ::= SEQUENCE {
   rf-Parameters-v1270 [0] RF-Parameters-v1270 OPTIONAL,
   nonCriticalExtension [1] UE-EUTRA-Capability-v1280-IEs OPTIONAL
}

UE-EUTRA-Capability-v1260-IEs ::= SEQUENCE {
   ue-CategoryDL-v1260 [0] INTEGER (15..16) OPTIONAL,
   nonCriticalExtension [1] UE-EUTRA-Capability-v1270-IEs OPTIONAL
}

UE-EUTRA-Capability-v1250-IEs ::= SEQUENCE {
   phyLayerParameters-v1250 [0] PhyLayerParameters-v1250 OPTIONAL,
   rf-Parameters-v1250 [1] RF-Parameters-v1250 OPTIONAL,
   rlc-Parameters-r12 [2] RLC-Parameters-r12 OPTIONAL,
   ue-BasedNetwPerfMeasParameters-v1250 [3] 
      UE-BasedNetwPerfMeasParameters-v1250 OPTIONAL,
   ue-CategoryDL-r12 [4] INTEGER (0..14) OPTIONAL,
   ue-CategoryUL-r12 [5] INTEGER (0..13) OPTIONAL,
   wlan-IW-Parameters-r12 [6] WLAN-IW-Parameters-r12 OPTIONAL,
   measParameters-v1250 [7] MeasParameters-v1250 OPTIONAL,
   dc-Parameters-r12 [8] DC-Parameters-r12 OPTIONAL,
   mbms-Parameters-v1250 [9] MBMS-Parameters-v1250 OPTIONAL,
   mac-Parameters-r12 [10] MAC-Parameters-r12 OPTIONAL,
   fdd-Add-UE-EUTRA-Capabilities-v1250 [11] 
      UE-EUTRA-CapabilityAddXDD-Mode-v1250 OPTIONAL,
   tdd-Add-UE-EUTRA-Capabilities-v1250 [12] 
      UE-EUTRA-CapabilityAddXDD-Mode-v1250 OPTIONAL,
   sl-Parameters-r12 [13] SL-Parameters-r12 OPTIONAL,
   nonCriticalExtension [14] UE-EUTRA-Capability-v1260-IEs OPTIONAL
}

UE-EUTRA-Capability-v11a0-IEs ::= SEQUENCE {
   ue-Category-v11a0 [0] INTEGER (11..12) OPTIONAL,
   measParameters-v11a0 [1] MeasParameters-v11a0 OPTIONAL,
   nonCriticalExtension [2] UE-EUTRA-Capability-v1250-IEs OPTIONAL
}

UE-EUTRA-Capability-v1180-IEs ::= SEQUENCE {
   rf-Parameters-v1180 [0] RF-Parameters-v1180 OPTIONAL,
   mbms-Parameters-r11 [1] MBMS-Parameters-r11 OPTIONAL,
   fdd-Add-UE-EUTRA-Capabilities-v1180 [2] UE-EUTRA-CapabilityAddXDD-Mode-v1180
       OPTIONAL,
   tdd-Add-UE-EUTRA-Capabilities-v1180 [3] UE-EUTRA-CapabilityAddXDD-Mode-v1180
       OPTIONAL,
   nonCriticalExtension [4] UE-EUTRA-Capability-v11a0-IEs OPTIONAL
}

UE-EUTRA-Capability-v1170-IEs ::= SEQUENCE {
   phyLayerParameters-v1170 [0] PhyLayerParameters-v1170 OPTIONAL,
   ue-Category-v1170 [1] INTEGER (9..10) OPTIONAL,
   nonCriticalExtension [2] UE-EUTRA-Capability-v1180-IEs OPTIONAL
}

UE-EUTRA-Capability-v1130-IEs ::= SEQUENCE {
   pdcp-Parameters-v1130 [0] PDCP-Parameters-v1130,
   phyLayerParameters-v1130 [1] PhyLayerParameters-v1130 OPTIONAL,
   rf-Parameters-v1130 [2] RF-Parameters-v1130,
   measParameters-v1130 [3] MeasParameters-v1130,
   interRAT-ParametersCDMA2000-v1130 [4] IRAT-ParametersCDMA2000-v1130,
   otherParameters-r11 [5] Other-Parameters-r11,
   fdd-Add-UE-EUTRA-Capabilities-v1130 [6] UE-EUTRA-CapabilityAddXDD-Mode-v1130
       OPTIONAL,
   tdd-Add-UE-EUTRA-Capabilities-v1130 [7] UE-EUTRA-CapabilityAddXDD-Mode-v1130
       OPTIONAL,
   nonCriticalExtension [8] UE-EUTRA-Capability-v1170-IEs OPTIONAL
}

UE-EUTRA-Capability-v1090-IEs ::= SEQUENCE {
   rf-Parameters-v1090 [0] RF-Parameters-v1090 OPTIONAL,
   nonCriticalExtension [1] UE-EUTRA-Capability-v1130-IEs OPTIONAL
}

UE-EUTRA-Capability-v1060-IEs ::= SEQUENCE {
   fdd-Add-UE-EUTRA-Capabilities-v1060 [0] UE-EUTRA-CapabilityAddXDD-Mode-v1060
       OPTIONAL,
   tdd-Add-UE-EUTRA-Capabilities-v1060 [1] UE-EUTRA-CapabilityAddXDD-Mode-v1060
       OPTIONAL,
   rf-Parameters-v1060 [2] RF-Parameters-v1060 OPTIONAL,
   nonCriticalExtension [3] UE-EUTRA-Capability-v1090-IEs OPTIONAL
}

UE-EUTRA-Capability-v1020-IEs ::= SEQUENCE {
   ue-Category-v1020 [0] INTEGER (6..8) OPTIONAL,
   phyLayerParameters-v1020 [1] PhyLayerParameters-v1020 OPTIONAL,
   rf-Parameters-v1020 [2] RF-Parameters-v1020 OPTIONAL,
   measParameters-v1020 [3] MeasParameters-v1020 OPTIONAL,
   featureGroupIndRel10-r10 [4] BIT STRING  (SIZE (32)) OPTIONAL,
   interRAT-ParametersCDMA2000-v1020 [5] IRAT-ParametersCDMA2000-1XRTT-v1020
       OPTIONAL,
   ue-BasedNetwPerfMeasParameters-r10 [6] UE-BasedNetwPerfMeasParameters-r10
       OPTIONAL,
   interRAT-ParametersUTRA-TDD-v1020 [7] IRAT-ParametersUTRA-TDD-v1020 OPTIONAL
      ,
   nonCriticalExtension [8] UE-EUTRA-Capability-v1060-IEs OPTIONAL
}

UE-EUTRA-Capability-v940-IEs ::= SEQUENCE {
   lateNonCriticalExtension [0] OCTET STRING (CONTAINING 
      UE-EUTRA-Capability-v9a0-IEs) OPTIONAL,
   nonCriticalExtension [1] UE-EUTRA-Capability-v1020-IEs OPTIONAL
}

-- Regular non critical extensions
UE-EUTRA-Capability-v920-IEs ::= SEQUENCE {
   phyLayerParameters-v920 [0] PhyLayerParameters-v920,
   interRAT-ParametersGERAN-v920 [1] IRAT-ParametersGERAN-v920,
   interRAT-ParametersUTRA-v920 [2] IRAT-ParametersUTRA-v920 OPTIONAL,
   interRAT-ParametersCDMA2000-v920 [3] IRAT-ParametersCDMA2000-1XRTT-v920
       OPTIONAL,
   deviceType-r9 [4] ENUMERATED { noBenFromBatConsumpOpt(0) } OPTIONAL,
   csg-ProximityIndicationParameters-r9 [5] 
      CSG-ProximityIndicationParameters-r9,
   neighCellSI-AcquisitionParameters-r9 [6] 
      NeighCellSI-AcquisitionParameters-r9,
   son-Parameters-r9 [7] SON-Parameters-r9,
   nonCriticalExtension [8] UE-EUTRA-Capability-v940-IEs OPTIONAL
}

UE-EUTRA-Capability ::= SEQUENCE {
   accessStratumRelease [0] AccessStratumRelease,
   ue-Category [1] INTEGER (1..5),
   pdcp-Parameters [2] PDCP-Parameters,
   phyLayerParameters [3] PhyLayerParameters,
   rf-Parameters [4] RF-Parameters,
   measParameters [5] MeasParameters,
   featureGroupIndicators [6] BIT STRING  (SIZE (32)) OPTIONAL,
   interRAT-Parameters [7] SEQUENCE {
      utraFDD [0] IRAT-ParametersUTRA-FDD OPTIONAL,
      utraTDD128 [1] IRAT-ParametersUTRA-TDD128 OPTIONAL,
      utraTDD384 [2] IRAT-ParametersUTRA-TDD384 OPTIONAL,
      utraTDD768 [3] IRAT-ParametersUTRA-TDD768 OPTIONAL,
      geran [4] IRAT-ParametersGERAN OPTIONAL,
      cdma2000-HRPD [5] IRAT-ParametersCDMA2000-HRPD OPTIONAL,
      cdma2000-1xRTT [6] IRAT-ParametersCDMA2000-1XRTT OPTIONAL
   },
   nonCriticalExtension [8] UE-EUTRA-Capability-v920-IEs OPTIONAL
}

-- Value assignments

maxAccessCat-1-r15 INTEGER ::= 63

maxACDC-Cat-r13 INTEGER ::= 16

maxAvailNarrowBands-r13 INTEGER ::= 16

maxBandComb-r10 INTEGER ::= 128

maxBandComb-r11 INTEGER ::= 256

maxBandComb-r13 INTEGER ::= 384

maxBands INTEGER ::= 64

maxBandsNR-r15 INTEGER ::= 1024

maxBandwidthClass-r10 INTEGER ::= 16

maxBandwidthCombSet-r10 INTEGER ::= 32

maxBarringInfoSet-r15 INTEGER ::= 8

maxBT-IdReport-r15 INTEGER ::= 32

maxBT-Name-r15 INTEGER ::= 4

maxCBR-Level-r14 INTEGER ::= 16

maxCBR-Level-1-r14 INTEGER ::= 15

maxCBR-Report-r14 INTEGER ::= 72

maxCDMA-BandClass INTEGER ::= 32

maxCE-Level-r13 INTEGER ::= 4

maxCellBlack INTEGER ::= 16

maxCellHistory-r12 INTEGER ::= 16

maxCellInfoGERAN-r9 INTEGER ::= 32

maxCellInfoUTRA-r9 INTEGER ::= 16

maxCellMeasIdle-r15 INTEGER ::= 8

maxCombIDC-r11 INTEGER ::= 128

maxCSI-IM-r11 INTEGER ::= 3

maxCSI-IM-r12 INTEGER ::= 4

minCSI-IM-r13 INTEGER ::= 5

maxCSI-IM-r13 INTEGER ::= 24

maxCSI-IM-v1310 INTEGER ::= 20

maxCSI-Proc-r11 INTEGER ::= 4

maxCSI-RS-NZP-r11 INTEGER ::= 3

minCSI-RS-NZP-r13 INTEGER ::= 4

maxCSI-RS-NZP-r13 INTEGER ::= 24

maxCSI-RS-NZP-v1310 INTEGER ::= 21

maxCSI-RS-ZP-r11 INTEGER ::= 4

maxCQI-ProcExt-r11 INTEGER ::= 3

maxFreqUTRA-TDD-r10 INTEGER ::= 6

maxCellInter INTEGER ::= 16

maxCellIntra INTEGER ::= 16

maxCellListGERAN INTEGER ::= 3

maxCellMeas INTEGER ::= 32

maxCellReport INTEGER ::= 8

maxCellSFTD INTEGER ::= 3

maxConfigSPS-r14 INTEGER ::= 8

maxConfigSPS-r15 INTEGER ::= 6

maxCSI-RS-Meas-r12 INTEGER ::= 96

maxDRB INTEGER ::= 11

maxDRBExt-r15 INTEGER ::= 4

maxDRB-r15 INTEGER ::= 15

maxDS-Duration-r12 INTEGER ::= 5

maxDS-ZTP-CSI-RS-r12 INTEGER ::= 5

maxEARFCN INTEGER ::= 65535

maxEARFCN-Plus1 INTEGER ::= 65536

maxEARFCN2 INTEGER ::= 262143

maxEPDCCH-Set-r11 INTEGER ::= 2

maxFBI INTEGER ::= 64

maxFBI-NR-r15 INTEGER ::= 1024

maxFBI-Plus1 INTEGER ::= 65

maxFBI2 INTEGER ::= 256

maxFeatureSets-r15 INTEGER ::= 256

maxPerCC-FeatureSets-r15 INTEGER ::= 32

maxFreq INTEGER ::= 8

maxFreqIDC-r11 INTEGER ::= 32

maxFreqIdle-r15 INTEGER ::= 8

maxFreqMBMS-r11 INTEGER ::= 5

maxFreqNR-r15 INTEGER ::= 5

maxFreqV2X-r14 INTEGER ::= 8

maxFreqV2X-1-r14 INTEGER ::= 7

maxGERAN-SI INTEGER ::= 10

maxGNFG INTEGER ::= 16

maxIdleMeasCarriers-r15 INTEGER ::= 3

maxLCG-r13 INTEGER ::= 4

maxLogMeasReport-r10 INTEGER ::= 520

maxMBSFN-Allocations INTEGER ::= 8

maxMBSFN-Area INTEGER ::= 8

maxMBSFN-Area-1 INTEGER ::= 7

maxMBMS-ServiceListPerUE-r13 INTEGER ::= 15

maxMeasId INTEGER ::= 32

maxMeasId-Plus1 INTEGER ::= 33

maxMeasId-r12 INTEGER ::= 64

maxMultiBands INTEGER ::= 8

maxMultiBandsNR-r15 INTEGER ::= 32

maxMultiBandsNR-1-r15 INTEGER ::= 31

maxNS-Pmax-r10 INTEGER ::= 8

maxNAICS-Entries-r12 INTEGER ::= 8

maxNeighCell-r12 INTEGER ::= 8

maxNeighCell-SCPTM-r13 INTEGER ::= 8

maxNrofS-NSSAI-r15 INTEGER ::= 8

maxObjectId INTEGER ::= 32

maxObjectId-Plus1-r13 INTEGER ::= 33

maxObjectId-r13 INTEGER ::= 64

maxP-a-PerNeighCell-r12 INTEGER ::= 3

maxPageRec INTEGER ::= 16

maxPhysCellIdRange-r9 INTEGER ::= 4

maxPLMN-r11 INTEGER ::= 6

maxPLMN-1-r14 INTEGER ::= 5

maxPLMN-r15 INTEGER ::= 8

maxPLMN-NR-r15 INTEGER ::= 12

maxPNOffset INTEGER ::= 511

maxPMCH-PerMBSFN INTEGER ::= 15

maxPSSCH-TxConfig-r14 INTEGER ::= 16

maxQuantSetsNR-r15 INTEGER ::= 2

maxQCI-r13 INTEGER ::= 6

maxRAT-Capabilities INTEGER ::= 8

maxRE-MapQCL-r11 INTEGER ::= 4

maxReportConfigId INTEGER ::= 32

maxReservationPeriod-r14 INTEGER ::= 16

maxRS-Index-r15 INTEGER ::= 64

maxRS-Index-1-r15 INTEGER ::= 63

maxRS-IndexCellQual-r15 INTEGER ::= 16

maxRS-IndexReport-r15 INTEGER ::= 32

maxRSTD-Freq-r10 INTEGER ::= 3

maxSAI-MBMS-r11 INTEGER ::= 64

maxSCell-r10 INTEGER ::= 4

maxSCell-r13 INTEGER ::= 31

maxSCellGroups-r15 INTEGER ::= 4

maxSC-MTCH-r13 INTEGER ::= 1023

maxSC-MTCH-BR-r14 INTEGER ::= 128

maxSL-CommRxPoolNFreq-r13 INTEGER ::= 32

maxSL-CommRxPoolPreconf-v1310 INTEGER ::= 12

maxSL-TxPool-r12Plus1-r13 INTEGER ::= 5

maxSL-TxPool-v1310 INTEGER ::= 4

maxSL-TxPool-r13 INTEGER ::= 8

maxSL-CommTxPoolPreconf-v1310 INTEGER ::= 7

maxSL-Dest-r12 INTEGER ::= 16

maxSL-DiscCells-r13 INTEGER ::= 16

maxSL-DiscPowerClass-r12 INTEGER ::= 3

maxSL-DiscRxPoolPreconf-r13 INTEGER ::= 16

maxSL-DiscSysInfoReportFreq-r13 INTEGER ::= 8

maxSL-DiscTxPoolPreconf-r13 INTEGER ::= 4

maxSL-GP-r13 INTEGER ::= 8

maxSL-PoolToMeasure-r14 INTEGER ::= 72

maxSL-Prio-r13 INTEGER ::= 8

maxSL-RxPool-r12 INTEGER ::= 16

maxSL-Reliability-r15 INTEGER ::= 8

maxSL-SyncConfig-r12 INTEGER ::= 16

maxSL-TF-IndexPair-r12 INTEGER ::= 64

maxSL-TxPool-r12 INTEGER ::= 4

maxSL-V2X-RxPool-r14 INTEGER ::= 16

maxSL-V2X-RxPoolPreconf-r14 INTEGER ::= 16

maxSL-V2X-TxPool-r14 INTEGER ::= 8

maxSL-V2X-TxPoolPreconf-r14 INTEGER ::= 8

maxSL-V2X-SyncConfig-r14 INTEGER ::= 16

maxSL-V2X-CBRConfig-r14 INTEGER ::= 4

maxSL-V2X-CBRConfig-1-r14 INTEGER ::= 3

maxSL-V2X-TxConfig-r14 INTEGER ::= 64

maxSL-V2X-TxConfig-1-r14 INTEGER ::= 63

maxSL-V2X-CBRConfig2-r14 INTEGER ::= 8

maxSL-V2X-CBRConfig2-1-r14 INTEGER ::= 7

maxSL-V2X-TxConfig2-r14 INTEGER ::= 128

maxSL-V2X-TxConfig2-1-r14 INTEGER ::= 127

maxSTAG-r11 INTEGER ::= 3

maxServCell-r10 INTEGER ::= 5

maxServCell-r13 INTEGER ::= 32

maxServCellNR-r15 INTEGER ::= 16

maxServiceCount INTEGER ::= 16

maxServiceCount-1 INTEGER ::= 15

maxSessionPerPMCH INTEGER ::= 29

maxSessionPerPMCH-1 INTEGER ::= 28

maxSIB INTEGER ::= 32

maxSIB-1 INTEGER ::= 31

maxSI-Message INTEGER ::= 32

maxSimultaneousBands-r10 INTEGER ::= 64

maxSubframePatternIDC-r11 INTEGER ::= 8

maxTrafficPattern-r14 INTEGER ::= 8

maxUTRA-FDD-Carrier INTEGER ::= 16

maxUTRA-TDD-Carrier INTEGER ::= 16

maxWayPoint-r15 INTEGER ::= 20

maxWLAN-Id-r12 INTEGER ::= 16

maxWLAN-Bands-r13 INTEGER ::= 8

maxWLAN-Id-r13 INTEGER ::= 32

maxWLAN-Channels-r13 INTEGER ::= 16

maxWLAN-CarrierInfo-r13 INTEGER ::= 8

maxWLAN-Id-Report-r14 INTEGER ::= 32

maxWLAN-Name-r15 INTEGER ::= 4


END
