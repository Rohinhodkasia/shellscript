-- This file was generated by the Objective Systems ASN1C Compiler
-- (http://www.obj-sys.com).  Version: 6.8.A, Date: 15-Nov-2014.

SUPL-NOTIFY DEFINITIONS AUTOMATIC TAGS ::= BEGIN

IMPORTS

Notification
FROM SUPL-INIT ;

-- Productions

Ver2-SUPLNOTIFY ::= SEQUENCE {
   notification [0] Notification,
   ...
}

END
