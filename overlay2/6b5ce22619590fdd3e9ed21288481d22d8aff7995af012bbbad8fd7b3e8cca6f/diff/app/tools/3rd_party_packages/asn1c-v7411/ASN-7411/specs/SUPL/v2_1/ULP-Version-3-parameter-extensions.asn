-- This file was generated by the Objective Systems ASN1C Compiler
-- (http://www.obj-sys.com).  Version: 6.8.A, Date: 15-Nov-2014.

ULP-Version-3-parameter-extensions DEFINITIONS AUTOMATIC TAGS ::= BEGIN

IMPORTS

QoPCapabilities, RelativePositioningCapabilities, CivicPositioningCapabilities
FROM ULP-Version-3-message-extensions ;

-- Productions

PosProtocolVersionOMA ::= SEQUENCE {
   majorVersionField [0] INTEGER (0..255),
   minorVersionField [1] INTEGER (0..255),
   ...
}

SUPLINITRootKeyStatus ::= ENUMERATED { invalidSUPLINITRootKey(0), 
   outofsyncSUPLINITRootKey(1), ... }

Ver3-SETCapabilities-extension ::= SEQUENCE {
   qoPCapabilities [0] QoPCapabilities OPTIONAL,
   civicPositioningCapabilities [1] CivicPositioningCapabilities OPTIONAL,
   relativePositioningCapabilities [2] RelativePositioningCapabilities OPTIONAL
      ,
   d-SLP-Provision-from-H-SLP [3] BOOLEAN,
   e-SLP-Provision-from-H-SLP [4] BOOLEAN,
   d-SLP-Provision-from-Proxy-D-SLP [5] BOOLEAN,
   e-SLP-Provision-from-Proxy-E-SLP [6] BOOLEAN,
   d-SLP-Notification-to-H-SLP [7] BOOLEAN,
   sensorSupport [8] BOOLEAN,
   sUPLINITRootKeyStatus [9] SUPLINITRootKeyStatus OPTIONAL,
   ...
}

END
