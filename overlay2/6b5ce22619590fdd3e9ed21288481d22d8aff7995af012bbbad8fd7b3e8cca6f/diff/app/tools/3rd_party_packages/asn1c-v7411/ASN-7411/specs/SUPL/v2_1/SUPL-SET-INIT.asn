-- This file was generated by the Objective Systems ASN1C Compiler
-- (http://www.obj-sys.com).  Version: 6.8.A, Date: 15-Nov-2014.

SUPL-SET-INIT DEFINITIONS AUTOMATIC TAGS ::= BEGIN

IMPORTS

SETId, QoP
FROM ULP-Components 

ApplicationID
FROM Ver2-ULP-Components 

Ver3-SUPL-SET-INIT-extension
FROM ULP-Version-3-message-extensions ;

-- Productions

Ver2-SUPLSETINIT ::= SEQUENCE {
   targetSETID [0] SETId,
   qoP [1] QoP OPTIONAL,
   applicationID [2] ApplicationID OPTIONAL,
   ...,
   ver3-SUPL-SET-INIT-extension [3] Ver3-SUPL-SET-INIT-extension OPTIONAL
}

END
