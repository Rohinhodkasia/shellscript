-- This file was generated by the Objective Systems ASN1C Compiler
-- (http://www.obj-sys.com).  Version: 6.3.A, Date: 17-Oct-2009.

CSTA-error-definition 
{ iso( 1) identified-organization( 3) icd-ecma( 0012)
		standard( 0) csta( 180) version1( 1) error-definition( 120) }
DEFINITIONS ::= BEGIN

IMPORTS

ERROR
FROM Remote-Operations-Information-Objects 
{joint-iso-itu-t remote-operations(4) informationObjects(5) version1(0)}

CSTAPrivateData
FROM CSTA-extension-types 
{ iso( 1) identified-organization( 3) icd-ecma( 0012)
		standard( 0) csta( 180) version1( 1) extension-types( 129) }
   ;

-- Productions

Operations ::= ENUMERATED { generic(1), requestIncompatibleWithObject(2), 
   valueOutOfRange(3), objectNotKnown(4), invalidCallingDevice(5), 
   invalidCalledDevice(6), invalidForwardingDestination(7), 
   privilegeViolationOnSpecifiedDevice(8), privilegeViolationOnCalledDevice(9)
   , privilegeViolationOnCallingDevice(10), invalidCSTACallIdentifier(11), 
   invalidCSTADeviceIdentifier(12), invalidCSTAConnectionIdentifier(13), 
   invalidDestination(14), invalidFeature(15), invalidAllocationState(16), 
   invalidCrossRefID(17), invalidObjectType(18), securityViolation(19) }

StateIncompatibility ::= ENUMERATED { generic(1), invalidObjectState(2), 
   invalidConnectionID(3), noActiveCall(4), noHeldCall(5), noCallToClear(6), 
   noConnectionToClear(7), noCallToAnswer(8), noCallToComplete(9) }

SystemResourceAvailability ::= ENUMERATED { generic(1), serviceBusy(2), 
   resourceBusy(3), resourceOutOfService(4), networkBusy(5), 
   networkOutOfService(6), overallMonitorLimitExceeded(7), 
   conferenceMemberLimitExceeded(8) }

SubscribedResourceAvailability ::= ENUMERATED { generic(1), 
   objectMonitorLimitExceeded(2), externalTrunkLimitExceeded(3), 
   outstandingRequestLimitExceeded(4) }

PerformanceManagement ::= ENUMERATED { generic(1), performanceLimitExceeded(2)
    }

SecurityError ::= ENUMERATED { unspecified(0), sequenceNumberViolated(1), 
   timeStampViolated(2), pACViolated(3), sealViolated(4) }

UniversalFailure ::= CHOICE {
   nonStandardErrors CSTAPrivateData,
   operationalErrors [1] IMPLICIT Operations,
   stateErrors [2] IMPLICIT StateIncompatibility,
   systemResourceErrors [3] IMPLICIT SystemResourceAvailability,
   subscribedResourceAvailabilityErrors [4] IMPLICIT 
      SubscribedResourceAvailability,
   performanceErrors [5] IMPLICIT PerformanceManagement,
   securityErrors [6] IMPLICIT SecurityError,
   unspecifiedErrors [7] IMPLICIT NULL
}

-- Information Object definitions

universalFailure ERROR ::= {
   &ParameterType UniversalFailure, 
   &errorCode local : 1
}


END
