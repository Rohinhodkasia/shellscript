CSTA-get-call-back
	{ iso( 1) identified-organization( 3) icd-ecma( 12)
		standard( 0) csta3( 285) get-call-back( 378) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
DeviceID FROM CSTA-device-identifiers
	{ iso( 1) identified-organization( 3) icd-ecma( 12)
		standard( 0) csta3( 285) device-identifiers( 123) }
CSTACommonArguments FROM CSTA-extension-types
	{ iso( 1) identified-organization( 3) icd-ecma( 12)
		standard( 0) csta3( 285) extension-types( 129) };

getCallBack OPERATION ::=
{	ARGUMENT 		GetCallBackArgument
	RESULT 			GetCallBackResult
	ERRORS 			{universalFailure }
	CODE			local: 378 }

GetCallBackArgument::= SEQUENCE
{	device 				DeviceID,
	extensions			CSTACommonArguments 			OPTIONAL }

GetCallBackResult ::= SEQUENCE
{	callBackList 			CallBackList,
	extensions			CSTACommonArguments			OPTIONAL }

CallBackList ::= SEQUENCE OF SEQUENCE
{	originatingDevice		DeviceID,
	targetDevice			DeviceID,
	callBackMessageIndicator	BOOLEAN					OPTIONAL }

END -- of CSTA-get-call-back
