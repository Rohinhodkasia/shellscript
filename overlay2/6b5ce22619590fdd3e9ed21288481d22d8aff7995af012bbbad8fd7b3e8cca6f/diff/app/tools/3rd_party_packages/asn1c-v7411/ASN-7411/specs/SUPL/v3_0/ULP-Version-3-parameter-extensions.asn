-- This file was generated by the Objective Systems ASN1C Compiler
-- (http://www.obj-sys.com).  Version: 6.8.A, Date: 18-Nov-2014.

ULP-Version-3-parameter-extensions DEFINITIONS AUTOMATIC TAGS ::= BEGIN

IMPORTS

QoPCapabilities, RelativePositioningCapabilities, CivicPositioningCapabilities
FROM ULP-Version-3-message-extensions 

TrackingAreaCode
FROM Ver2-ULP-Components ;

-- Productions

KeyIdentifierType ::= ENUMERATED { modeAKeyIdentifier(0), 
   temporaryModeAKeyIdentifier(1), modeBKeyIdentifier(2), ... }

Ver3-ProtectionLevel-extension ::= SEQUENCE {
   keyIdentifierType [0] KeyIdentifierType,
   keyIdentifier [1] OCTET STRING (SIZE (8)),
   basicReplayCounter [2] INTEGER (0..65535),
   basicMAC [3] BIT STRING  (SIZE (32)),
   ...
}

PosProtocolVersionOMA ::= SEQUENCE {
   majorVersionField [0] INTEGER (0..255),
   minorVersionField [1] INTEGER (0..255),
   ...
}

Ver3-PosProtocol-extension ::= SEQUENCE {
   posProtocolVersionLPPe [0] PosProtocolVersionOMA OPTIONAL,
   ...
}

Ver3-ServiceSupported-extensions ::= SEQUENCE {
   velocityTrigger [0] BOOLEAN,
   ...
}

SUPLINITRootKeyStatus ::= ENUMERATED { invalidSUPLINITRootKey(0), 
   outofsyncSUPLINITRootKey(1), ... }

Ver3-SETCapabilities-extension ::= SEQUENCE {
   qoPCapabilities [0] QoPCapabilities OPTIONAL,
   civicPositioningCapabilities [1] CivicPositioningCapabilities OPTIONAL,
   relativePositioningCapabilities [2] RelativePositioningCapabilities OPTIONAL
      ,
   d-SLP-Provision-from-H-SLP [3] BOOLEAN,
   e-SLP-Provision-from-H-SLP [4] BOOLEAN,
   d-SLP-Provision-from-Proxy-D-SLP [5] BOOLEAN,
   e-SLP-Provision-from-Proxy-E-SLP [6] BOOLEAN,
   d-SLP-Notification-to-H-SLP [7] BOOLEAN,
   sensorSupport [8] BOOLEAN,
   sUPLINITRootKeyStatus [9] SUPLINITRootKeyStatus OPTIONAL,
   ...
}

Ver3-LTEAreaId-extension ::= SEQUENCE {
   trackingAreaCode [0] TrackingAreaCode OPTIONAL,
   ...
}

VelocityEventType ::= ENUMERATED { increasingAbove(0), above(1), 
   decreasingBelow(2), below(3), ... }

RepeatedReportingParams ::= SEQUENCE {
   minimumIntervalTime [0] INTEGER (1..604800),
   maximumNumberOfReports [1] INTEGER (1..1024),
   ...
}

TargetSpeed ::= INTEGER (1..65536)

VelocityEventParams ::= SEQUENCE {
   velocityEventType [0] VelocityEventType,
   velocityEstimate [1] BOOLEAN,
   repeatedReportingParams [2] RepeatedReportingParams OPTIONAL,
   startTime [3] INTEGER (0..2678400) OPTIONAL,
   stopTime [4] INTEGER (0..11318399) OPTIONAL,
   targetSpeed [5] TargetSpeed OPTIONAL,
   ...
}

Ver3-TriggerParams-extension ::= CHOICE {
   velocityEventParams [0] VelocityEventParams,
   ...
}

PosPayload-rep ::= CHOICE {
   lPPpayload [0] OCTET STRING (SIZE (1..60000)),
   tia801payload [1] OCTET STRING (SIZE (1..600000)),
   ...
}

Ver3-PosPayload-rep-extensions ::= SEQUENCE {
   posPayload-rep [0] PosPayload-rep,
   ...
}

END
