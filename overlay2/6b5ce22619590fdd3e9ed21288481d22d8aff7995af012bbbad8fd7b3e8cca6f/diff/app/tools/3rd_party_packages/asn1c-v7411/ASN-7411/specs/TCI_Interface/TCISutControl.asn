TCI-SutControl

DEFINITIONS AUTOMATIC TAGS ::= BEGIN

IMPORTS
Response,
MsgID, 
Exception FROM TCI-CommonTypes

ResponseInfo FROM TCI-responseInfo
;

TCISutControl ::= CHOICE{
    request         [0] Request,
    response        [1] Response,
    responseInfo    [3] SutResponseInfo,
    exception       [4] Exception,
    ...
    } 

MESSAGE-ID-AND-TYPE ::= CLASS {
   &id    MsgID UNIQUE,
   &Type
   } WITH SYNTAX {&Type IDENTIFIED BY &id}

Request ::=  SEQUENCE {
   messageId   MESSAGE-ID-AND-TYPE.&id({MessageTypes}),
   value       MESSAGE-ID-AND-TYPE.&Type({MessageTypes}{@.messageId}),
   ...
   }

MessageTypes MESSAGE-ID-AND-TYPE ::= {
    { Shutdown  IDENTIFIED BY shutdown } |
    { Restart IDENTIFIED BY restart} |
    { RequestSutAvailability IDENTIFIED BY requestSutAvailability} |
    { RequestSutInfo IDENTIFIED BY requestSutInfo} |
    { SetTestId IDENTIFIED BY setTestId} 
}

shutdown                    MsgID ::= 1
restart                     MsgID ::= 2
requestSutAvailability      MsgID ::= 3
requestSutInfo              MsgID ::= 4
setTestId                   MsgID ::= 5

SetTestId ::= UTF8String(SIZE(1..255))

Shutdown ::= BOOLEAN (TRUE)

Restart ::= BOOLEAN (TRUE)

RequestSutAvailability ::= BOOLEAN (TRUE)

RequestSutInfo ::= BOOLEAN (TRUE)

SutResponseInfo ::= ResponseInfo (WITH COMPONENTS {
    msgID,  
    resultCode,
    info (WITH COMPONENTS {sutInfo}  ) OPTIONAL, -- if exception reported, no InfoContent provided
    exception OPTIONAL
    })

END
