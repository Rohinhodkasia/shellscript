CSTA-route-register-cancel
	{ iso( 1) identified-organization( 3) icd-ecma( 12)
		standard( 0) csta3( 285) route-register-cancel( 250) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
RouteRegisterReqID FROM CSTA-device-feature-types
	{ iso( 1) identified-organization( 3) icd-ecma( 12)
		standard( 0) csta3( 285) device-feature-types( 127) }
CSTACommonArguments FROM CSTA-extension-types 
	{ iso( 1) identified-organization( 3) icd-ecma( 12)
		standard( 0) csta3( 285) extension-types( 129) };

routeRegisterCancel OPERATION ::=
{	ARGUMENT		RouteRegisterCancelArgument
	RESULT			RouteRegisterCancelResult
	ERRORS			{universalFailure }
	CODE			local: 	250 }

RouteRegisterCancelArgument ::= SEQUENCE
{	routeRegisterReqID		RouteRegisterReqID,
	extensions			CSTACommonArguments			OPTIONAL }

RouteRegisterCancelResult  ::= CHOICE
{	extensions 			CSTACommonArguments,
	noData	 			NULL }

END  -- of CSTA-route-register-cancel
