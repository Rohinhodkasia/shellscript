CSTA-location-information-report
	{ iso( 1) identified-organization( 3) icd-ecma( 12)
		standard( 0) csta3( 285) location-information-report(535) }

DEFINITIONS ::=
BEGIN

IMPORTS
OPERATION, ERROR FROM Remote-Operations-Information-Objects 
	{joint-iso-itu-t remote-operations(4) informationObjects(5) version1(0) }

-- Data Types --
universalFailure FROM CSTA-error-definition
	{ iso( 1) identified-organization( 3) icd-ecma( 12)
		standard( 0) csta3( 285) error-definition( 120) }
CSTACommonArguments FROM CSTA-extension-types
	{ iso( 1) identified-organization( 3) icd-ecma( 12)
		standard( 0) csta3( 285) extension-types( 129) }
DeviceID FROM CSTA-device-identifiers
	{ iso( 1) identified-organization( 3) icd-ecma( 12)
		standard( 0) csta3( 285) device-identifiers( 123) }
LocCrossRefID FROM CSTA-device-feature-types
	{ iso( 1) identified-organization( 3) icd-ecma( 12)
		standard( 0) csta3( 285) device-feature-types( 127) }
LocationInfoList FROM CSTA-call-control
	{ iso( 1) identified-organization( 3) icd-ecma( 12)
		standard( 0) csta3( 285) call-control( 130) };

locationInformationReport OPERATION ::=
{ 	ARGUMENT		LocationInformationReportArgument
	RESULT			LocationInformationReportResult
	ERRORS			{universalFailure }
	CODE			local: 535}

LocationInformationReportArgument ::= SEQUENCE
{	locCrossRefID			LocCrossRefID,
	device				DeviceID,
	locationInfoList		LocationInfoList			OPTIONAL,
	extensions			CSTACommonArguments			OPTIONAL }

LocationInformationReportResult ::= SEQUENCE 
{	extensions			CSTACommonArguments			OPTIONAL }

END -- of CSTA-location-information-report
