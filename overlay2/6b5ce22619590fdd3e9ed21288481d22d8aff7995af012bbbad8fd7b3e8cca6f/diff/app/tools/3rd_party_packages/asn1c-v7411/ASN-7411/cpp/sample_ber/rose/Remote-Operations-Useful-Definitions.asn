-- This file was generated by the Objective Systems ASN1C Compiler
-- (http://www.obj-sys.com).  Version: 6.3.A, Date: 10-Oct-2009.

Remote-Operations-Useful-Definitions 
{joint-iso-itu-t remote-operations(4) useful-definitions(7) version1(0)}
DEFINITIONS IMPLICIT TAGS ::= BEGIN

IMPORTS

OPERATION, ERROR, OPERATION_PACKAGE, Code
FROM Remote-Operations-Information-Objects 
{joint-iso-itu-t remote-operations(4) informationObjects(5) version1(0)}

InvokeId, ROS
FROM Remote-Operations-Generic-ROS-PDUs 
{joint-iso-itu-t remote-operations(4) generic-ROS-PDUs(6) version1(0)};

-- Parameterized type assignments

ROS-SingleAS {InvokeId:InvokeIdSet, OPERATION-PACKAGE:package} ::= ROS {
{InvokeIdSet}, {AllOperations{package}}, {AllOperations{package}} }

ROS-ConsumerAS {InvokeId:InvokeIdSet, OPERATION-PACKAGE:package} ::= ROS {
{InvokeIdSet}, {ConsumerPerforms{package}}, {SupplierPerforms{package}} }

ROS-SupplierAS {InvokeId:InvokeIdSet, OPERATION-PACKAGE:package} ::= ROS {
{InvokeIdSet}, {SupplierPerforms{package}}, {ConsumerPerforms{package}} }

-- Parameterized info object assignments

recode {OPERATION:operation, Code:code} OPERATION ::= {&ArgumentType 
   operation.&ArgumentType, &argumentTypeOptional 
   operation.&argumentTypeOptional, &ResultType operation.&ResultType, 
   &resultTypeOptional operation.&resultTypeOptional, &returnResult 
   operation.&returnResult, &Errors {operation.&Errors}, &Linked {operation
   .&Linked}, &synchronous operation.&synchronous, &alwaysReturns 
   operation.&alwaysReturns, , , &operationCode code}
switch_ {OPERATION-PACKAGE:package, id} OPERATION-PACKAGE ::= {&Both {package
   .&Both}, &Supplier {package.&Supplier}, &Consumer {package.&Consumer}, &id 
   id}
combine {OPERATION-PACKAGE:ConsumerConsumes, OPERATION-PACKAGE:ConsumerSupplies
   , OPERATION-PACKAGE:base} OPERATION-PACKAGE ::= {&Both {ConsumerConsumes
   .&Both | ConsumerSupplies.&Both}, &Supplier {ConsumerConsumes.&Supplier | 
   ConsumerSupplies.&Consumer}, &Consumer {ConsumerConsumes.&Consumer | 
   ConsumerSupplies.&Supplier}, &id base.&id}
-- Parameterized info object set assignments

Forward {OPERATION:OperationSet} OPERATION ::= {OperationSet | OperationSet
   .&Linked.&Linked | OperationSet.&Linked.&Linked.&Linked.&Linked}

Reverse {OPERATION:OperationSet} OPERATION ::= {Forward{{OperationSet.&Linked}}
   }

ConsumerPerforms {OPERATION-PACKAGE:package} OPERATION ::= {Forward{
{package.&Consumer}} | Forward{{package.&Both}} | Reverse{{package.&Supplier}}
    | Reverse{{package.&Both}}}

SupplierPerforms {OPERATION-PACKAGE:package} OPERATION ::= {Forward{
{package.&Supplier}} | Forward{{package.&Both}} | Reverse{{package.&Consumer}}
    | Reverse{{package.&Both}}}

AllOperations {OPERATION-PACKAGE:package} OPERATION ::= {ConsumerPerforms{
   package} | SupplierPerforms{package}}

-- Information Object definitions

emptyBind OPERATION ::= {
   &Errors {refuse}, 
   &synchronous TRUE
}

emptyUnbind OPERATION ::= {
   &synchronous TRUE
}

refuse ERROR ::= {
   &errorCode local : -1
}

no-op OPERATION ::= {
   &alwaysReturns FALSE, 
   &operationCode local : -1
}


END
