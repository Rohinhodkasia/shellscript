CSTA-network-capabilities-changed-event
	{ iso( 1) identified-organization( 3) icd-ecma( 12)
	standard( 0) csta3( 285) network-capabilities-changed-event( 226) }

DEFINITIONS ::=
BEGIN

IMPORTS

-- Data Types –-
EventCause FROM CSTA-event-causes
	{ iso( 1) identified-organization( 3) icd-ecma( 12)
		standard( 0) csta3( 285) event-causes( 121) }
SubjectDeviceID, CalledDeviceID FROM CSTA-device-identifiers
	{ iso( 1) identified-organization( 3) icd-ecma( 12)
		standard( 0) csta3( 285) device-identifiers( 123) }
ConnectionID FROM CSTA-call-connection-identifiers
	{ iso( 1) identified-organization( 3) icd-ecma( 12)
		standard( 0) csta3( 285) call-connection-identifiers( 124) }
LocalConnectionState FROM CSTA-connection-states
	{ iso( 1) identified-organization( 3) icd-ecma( 12)
		standard( 0) csta3( 285) connection-states( 125) }
CorrelatorData, UserData FROM CSTA-device-feature-types
	{ iso( 1) identified-organization( 3) icd-ecma( 12)
		standard( 0) csta3( 285) device-feature-types( 127) }
CSTACommonArguments FROM CSTA-extension-types
	{ iso( 1) identified-organization( 3) icd-ecma( 12)
		standard( 0) csta3( 285) extension-types( 129) }
CallCharacteristics, CallLinkageData, NetworkCapability, ProgressIndicator,
ServicesPermitted FROM CSTA-call-control
	{ iso( 1) identified-organization( 3) icd-ecma( 12)
		standard( 0) csta3( 285) call-control( 130) }
LocationInfoList FROM CSTA-call-control
	{ iso( 1) identified-organization( 3) icd-ecma( 12)
		standard( 0) csta3( 285) call-control( 130) }
LanguagePreferences FROM CSTA-device-feature-types
	{ iso( 1) identified-organization( 3) icd-ecma( 12)
		standard( 0) csta3( 285) device-feature-types( 127) }
ConnectionInformation, MediaCallCharacteristics FROM CSTA-media-services
	{ iso( 1) identified-organization( 3) icd-ecma( 12)
		standard( 0) csta3( 285) media-services( 136) };

NetworkCapabilitiesChangedEvent ::= SEQUENCE
{	outboundConnection 		ConnectionID,
	networkInterfaceUsed 		SubjectDeviceID,
	calledDevice 			CalledDeviceID,
	progressIndicator 		ProgressIndicator,
	localConnectionInfo 		LocalConnectionState 			OPTIONAL,
	correlatorData 			CorrelatorData 				OPTIONAL,
	userData 			UserData 				OPTIONAL,
	networkCapability 		[0] IMPLICIT NetworkCapability 		OPTIONAL,
	cause 				EventCause,
	servicesPermitted 		[1] IMPLICIT ServicesPermitted 		OPTIONAL,
	mediaCallCharacteristics 	[2] IMPLICIT MediaCallCharacteristics 	OPTIONAL,
	callCharacteristics 		[3] IMPLICIT CallCharacteristics 	OPTIONAL,
	outboundConnectionInfo 		[4] IMPLICIT ConnectionInformation 	OPTIONAL,
	callLinkageData 		[5] IMPLICIT CallLinkageData 		OPTIONAL,
	languagePreferences		[6] IMPLICIT LanguagePreferences	OPTIONAL,
	locationInfo			[7] IMPLICIT LocationInfoList		OPTIONAL,
	extensions 			CSTACommonArguments 			OPTIONAL }

END -- of CSTA-network-capabilities-changed-event
